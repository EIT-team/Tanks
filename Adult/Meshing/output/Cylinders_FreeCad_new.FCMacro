import FreeCAD
import Part
import Part,PartGui
from FreeCAD import Base
App.ActiveDocument.addObject("Part::Cylinder","C1")
App.ActiveDocument.C1.Radius=0.550004
App.ActiveDocument.C1.Height=20.00
App.ActiveDocument.C1.Angle=360.00 
App.ActiveDocument.C1.Placement=Base.Placement(Base.Vector(0.330971,206.811025,0.635020),Base.Rotation(-0.720430,0.006319,0.000000,0.693499))
App.ActiveDocument.addObject("Part::Cylinder","C2")
App.ActiveDocument.C2.Radius=0.543293
App.ActiveDocument.C2.Height=20.00
App.ActiveDocument.C2.Angle=360.00 
App.ActiveDocument.C2.Placement=Base.Placement(Base.Vector(4.479374,206.602430,0.556465),Base.Rotation(-0.714149,0.071572,0.000000,0.696325))
App.ActiveDocument.addObject("Part::Cylinder","C3")
App.ActiveDocument.C3.Radius=0.536836
App.ActiveDocument.C3.Height=20.00
App.ActiveDocument.C3.Angle=360.00 
App.ActiveDocument.C3.Placement=Base.Placement(Base.Vector(8.543731,206.017017,0.462911),Base.Rotation(-0.702807,0.128514,0.000000,0.699676))
App.ActiveDocument.addObject("Part::Cylinder","C4")
App.ActiveDocument.C4.Radius=0.530308
App.ActiveDocument.C4.Height=20.00
App.ActiveDocument.C4.Angle=360.00 
App.ActiveDocument.C4.Placement=Base.Placement(Base.Vector(12.670905,205.080286,0.358655),Base.Rotation(-0.686539,0.184131,0.000000,0.703391))
App.ActiveDocument.addObject("Part::Cylinder","C5")
App.ActiveDocument.C5.Radius=0.523963
App.ActiveDocument.C5.Height=20.00
App.ActiveDocument.C5.Angle=360.00 
App.ActiveDocument.C5.Placement=Base.Placement(Base.Vector(16.821676,203.828470,0.258055),Base.Rotation(-0.669551,0.227843,0.000000,0.706958))
App.ActiveDocument.addObject("Part::Cylinder","C6")
App.ActiveDocument.C6.Radius=0.517783
App.ActiveDocument.C6.Height=20.00
App.ActiveDocument.C6.Angle=360.00 
App.ActiveDocument.C6.Placement=Base.Placement(Base.Vector(20.723508,202.323829,0.192739),Base.Rotation(-0.646791,0.280367,0.000000,0.709264))
App.ActiveDocument.addObject("Part::Cylinder","C7")
App.ActiveDocument.C7.Radius=0.511878
App.ActiveDocument.C7.Height=20.00
App.ActiveDocument.C7.Angle=360.00 
App.ActiveDocument.C7.Placement=Base.Placement(Base.Vector(24.651388,200.481465,0.164207),Base.Rotation(-0.628648,0.316732,0.000000,0.710269))
App.ActiveDocument.addObject("Part::Cylinder","C8")
App.ActiveDocument.C8.Radius=0.505905
App.ActiveDocument.C8.Height=20.00
App.ActiveDocument.C8.Angle=360.00 
App.ActiveDocument.C8.Placement=Base.Placement(Base.Vector(28.745703,198.292352,0.147953),Base.Rotation(-0.612873,0.345097,0.000000,0.710841))
App.ActiveDocument.addObject("Part::Cylinder","C9")
App.ActiveDocument.C9.Radius=0.500255
App.ActiveDocument.C9.Height=20.00
App.ActiveDocument.C9.Angle=360.00 
App.ActiveDocument.C9.Placement=Base.Placement(Base.Vector(32.471351,196.073386,0.078320),Base.Rotation(-0.588104,0.381258,0.000000,0.713286))
App.ActiveDocument.addObject("Part::Cylinder","C10")
App.ActiveDocument.C10.Radius=0.494750
App.ActiveDocument.C10.Height=20.00
App.ActiveDocument.C10.Angle=360.00 
App.ActiveDocument.C10.Placement=Base.Placement(Base.Vector(35.729880,193.749157,0.040130),Base.Rotation(-0.541502,0.442821,0.000000,0.714623))
App.ActiveDocument.addObject("Part::Cylinder","C11")
App.ActiveDocument.C11.Radius=0.489891
App.ActiveDocument.C11.Height=20.00
App.ActiveDocument.C11.Angle=360.00 
App.ActiveDocument.C11.Placement=Base.Placement(Base.Vector(38.644153,191.089053,0.001897),Base.Rotation(-0.493107,0.494215,0.000000,0.715959))
App.ActiveDocument.addObject("Part::Cylinder","C12")
App.ActiveDocument.C12.Radius=0.485535
App.ActiveDocument.C12.Height=20.00
App.ActiveDocument.C12.Angle=360.00 
App.ActiveDocument.C12.Placement=Base.Placement(Base.Vector(41.280787,188.181785,-0.028820),Base.Rotation(-0.442594,0.538495,0.000000,0.717031))
App.ActiveDocument.addObject("Part::Cylinder","C13")
App.ActiveDocument.C13.Radius=0.481501
App.ActiveDocument.C13.Height=20.00
App.ActiveDocument.C13.Angle=360.00 
App.ActiveDocument.C13.Placement=Base.Placement(Base.Vector(43.827391,184.755762,-0.071340),Base.Rotation(-0.396015,0.571763,0.000000,0.718512))
App.ActiveDocument.addObject("Part::Cylinder","C14")
App.ActiveDocument.C14.Radius=0.477954
App.ActiveDocument.C14.Height=20.00
App.ActiveDocument.C14.Angle=360.00 
App.ActiveDocument.C14.Placement=Base.Placement(Base.Vector(46.193787,181.143818,-0.109764),Base.Rotation(-0.362431,0.591999,0.000000,0.719848))
App.ActiveDocument.addObject("Part::Cylinder","C15")
App.ActiveDocument.C15.Radius=0.474759
App.ActiveDocument.C15.Height=20.00
App.ActiveDocument.C15.Angle=360.00 
App.ActiveDocument.C15.Placement=Base.Placement(Base.Vector(48.207248,177.555281,-0.160569),Base.Rotation(-0.312273,0.617871,0.000000,0.721610))
App.ActiveDocument.addObject("Part::Cylinder","C16")
App.ActiveDocument.C16.Radius=0.472260
App.ActiveDocument.C16.Height=20.00
App.ActiveDocument.C16.Angle=360.00 
App.ActiveDocument.C16.Placement=Base.Placement(Base.Vector(49.521153,174.312799,-0.219434),Base.Rotation(-0.216008,0.655497,0.000000,0.723646))
App.ActiveDocument.addObject("Part::Cylinder","C17")
App.ActiveDocument.C17.Radius=0.470620
App.ActiveDocument.C17.Height=20.00
App.ActiveDocument.C17.Angle=360.00 
App.ActiveDocument.C17.Placement=Base.Placement(Base.Vector(50.454946,170.597159,-0.177104),Base.Rotation(-0.138380,0.677719,0.000000,0.722182))
App.ActiveDocument.addObject("Part::Cylinder","C18")
App.ActiveDocument.C18.Radius=0.469478
App.ActiveDocument.C18.Height=20.00
App.ActiveDocument.C18.Angle=360.00 
App.ActiveDocument.C18.Placement=Base.Placement(Base.Vector(51.199380,166.172648,-0.015870),Base.Rotation(-0.094027,0.691139,0.000000,0.716579))
App.ActiveDocument.addObject("Part::Cylinder","C19")
App.ActiveDocument.C19.Radius=0.468739
App.ActiveDocument.C19.Height=20.00
App.ActiveDocument.C19.Angle=360.00 
App.ActiveDocument.C19.Placement=Base.Placement(Base.Vector(51.697848,161.670527,0.176041),Base.Rotation(-0.060125,0.701780,0.000000,0.709852))
App.ActiveDocument.addObject("Part::Cylinder","C20")
App.ActiveDocument.C20.Radius=0.468368
App.ActiveDocument.C20.Height=20.00
App.ActiveDocument.C20.Angle=360.00 
App.ActiveDocument.C20.Placement=Base.Placement(Base.Vector(51.944146,157.236288,0.321782),Base.Rotation(-0.017708,0.709284,0.000000,0.704701))
App.ActiveDocument.addObject("Part::Cylinder","C21")
App.ActiveDocument.C21.Radius=0.468454
App.ActiveDocument.C21.Height=20.00
App.ActiveDocument.C21.Angle=360.00 
App.ActiveDocument.C21.Placement=Base.Placement(Base.Vector(51.893141,153.229900,0.260778),Base.Rotation(0.041043,0.706160,0.000000,0.706862))
App.ActiveDocument.addObject("Part::Cylinder","C22")
App.ActiveDocument.C22.Radius=0.469055
App.ActiveDocument.C22.Height=20.00
App.ActiveDocument.C22.Angle=360.00 
App.ActiveDocument.C22.Placement=Base.Placement(Base.Vector(51.505285,148.856707,-0.029682),Base.Rotation(0.087051,0.691553,0.000000,0.717061))
App.ActiveDocument.addObject("Part::Cylinder","C23")
App.ActiveDocument.C23.Radius=0.469902
App.ActiveDocument.C23.Height=20.00
App.ActiveDocument.C23.Angle=360.00 
App.ActiveDocument.C23.Placement=Base.Placement(Base.Vector(50.803908,143.253747,-0.077318),Base.Rotation(0.035751,0.694380,0.000000,0.718720))
App.ActiveDocument.addObject("Part::Cylinder","C24")
App.ActiveDocument.C24.Radius=0.469247
App.ActiveDocument.C24.Height=20.00
App.ActiveDocument.C24.Angle=360.00 
App.ActiveDocument.C24.Placement=Base.Placement(Base.Vector(51.518990,135.681082,0.729075),Base.Rotation(-0.154257,0.707083,0.000000,0.690100))
App.ActiveDocument.addObject("Part::Cylinder","C25")
App.ActiveDocument.C25.Radius=0.468059
App.ActiveDocument.C25.Height=20.00
App.ActiveDocument.C25.Angle=360.00 
App.ActiveDocument.C25.Placement=Base.Placement(Base.Vector(52.196571,132.274155,0.482802),Base.Rotation(-0.045445,0.713710,0.000000,0.698965))
App.ActiveDocument.addObject("Part::Cylinder","C26")
App.ActiveDocument.C26.Radius=0.468618
App.ActiveDocument.C26.Height=20.00
App.ActiveDocument.C26.Angle=360.00 
App.ActiveDocument.C26.Placement=Base.Placement(Base.Vector(51.881141,129.343540,0.195469),Base.Rotation(0.112563,0.695996,0.000000,0.709168))
App.ActiveDocument.addObject("Part::Cylinder","C27")
App.ActiveDocument.C27.Radius=0.469990
App.ActiveDocument.C27.Height=20.00
App.ActiveDocument.C27.Angle=360.00 
App.ActiveDocument.C27.Placement=Base.Placement(Base.Vector(51.002246,125.282767,0.203345),Base.Rotation(0.166853,0.685299,0.000000,0.708890))
App.ActiveDocument.addObject("Part::Cylinder","C28")
App.ActiveDocument.C28.Radius=0.471668
App.ActiveDocument.C28.Height=20.00
App.ActiveDocument.C28.Angle=360.00 
App.ActiveDocument.C28.Placement=Base.Placement(Base.Vector(49.814914,120.821647,0.099070),Base.Rotation(0.186536,0.676362,0.000000,0.712558))
App.ActiveDocument.addObject("Part::Cylinder","C29")
App.ActiveDocument.C29.Radius=0.473328
App.ActiveDocument.C29.Height=20.00
App.ActiveDocument.C29.Angle=360.00 
App.ActiveDocument.C29.Placement=Base.Placement(Base.Vector(48.448013,115.462467,0.056911),Base.Rotation(0.153574,0.683058,0.000000,0.714036))
App.ActiveDocument.addObject("Part::Cylinder","C30")
App.ActiveDocument.C30.Radius=0.474828
App.ActiveDocument.C30.Height=20.00
App.ActiveDocument.C30.Angle=360.00 
App.ActiveDocument.C30.Placement=Base.Placement(Base.Vector(48.960080,114.298537,0.035258),Base.Rotation(0.408718,0.567468,0.000000,0.714793))
App.ActiveDocument.addObject("Part::Cylinder","C31")
App.ActiveDocument.C31.Radius=0.561288
App.ActiveDocument.C31.Height=20.00
App.ActiveDocument.C31.Angle=360.00 
App.ActiveDocument.C31.Placement=Base.Placement(Base.Vector(0.328264,206.930940,5.478506),Base.Rotation(-0.710621,0.006421,0.000000,0.703546))
App.ActiveDocument.addObject("Part::Cylinder","C32")
App.ActiveDocument.C32.Radius=0.572662
App.ActiveDocument.C32.Height=20.00
App.ActiveDocument.C32.Angle=360.00 
App.ActiveDocument.C32.Placement=Base.Placement(Base.Vector(0.301984,206.920135,10.376124),Base.Rotation(-0.701144,0.008179,0.000000,0.712972))
App.ActiveDocument.addObject("Part::Cylinder","C33")
App.ActiveDocument.C33.Radius=0.584073
App.ActiveDocument.C33.Height=20.00
App.ActiveDocument.C33.Angle=360.00 
App.ActiveDocument.C33.Placement=Base.Placement(Base.Vector(0.308363,206.776000,15.298505),Base.Rotation(-0.691842,0.007635,0.000000,0.722008))
App.ActiveDocument.addObject("Part::Cylinder","C34")
App.ActiveDocument.C34.Radius=0.594924
App.ActiveDocument.C34.Height=20.00
App.ActiveDocument.C34.Angle=360.00 
App.ActiveDocument.C34.Placement=Base.Placement(Base.Vector(0.317652,206.519597,19.955674),Base.Rotation(-0.682034,0.006903,0.000000,0.731288))
App.ActiveDocument.addObject("Part::Cylinder","C35")
App.ActiveDocument.C35.Radius=0.605589
App.ActiveDocument.C35.Height=20.00
App.ActiveDocument.C35.Angle=360.00 
App.ActiveDocument.C35.Placement=Base.Placement(Base.Vector(0.288749,206.138416,24.496798),Base.Rotation(-0.670859,0.008757,0.000000,0.741533))
App.ActiveDocument.addObject("Part::Cylinder","C36")
App.ActiveDocument.C36.Radius=0.616904
App.ActiveDocument.C36.Height=20.00
App.ActiveDocument.C36.Angle=360.00 
App.ActiveDocument.C36.Placement=Base.Placement(Base.Vector(0.327925,205.576700,29.242881),Base.Rotation(-0.656128,0.006009,0.000000,0.754625))
App.ActiveDocument.addObject("Part::Cylinder","C37")
App.ActiveDocument.C37.Radius=0.628096
App.ActiveDocument.C37.Height=20.00
App.ActiveDocument.C37.Angle=360.00 
App.ActiveDocument.C37.Placement=Base.Placement(Base.Vector(0.318551,204.828079,33.876578),Base.Rotation(-0.638795,0.006503,0.000000,0.769349))
App.ActiveDocument.addObject("Part::Cylinder","C38")
App.ActiveDocument.C38.Radius=0.639329
App.ActiveDocument.C38.Height=20.00
App.ActiveDocument.C38.Angle=360.00 
App.ActiveDocument.C38.Placement=Base.Placement(Base.Vector(0.308779,203.855890,38.421634),Base.Rotation(-0.616672,0.006977,0.000000,0.787189))
App.ActiveDocument.addObject("Part::Cylinder","C39")
App.ActiveDocument.C39.Radius=0.650193
App.ActiveDocument.C39.Height=20.00
App.ActiveDocument.C39.Angle=360.00 
App.ActiveDocument.C39.Placement=Base.Placement(Base.Vector(0.310046,202.646416,42.753214),Base.Rotation(-0.591769,0.006735,0.000000,0.806079))
App.ActiveDocument.addObject("Part::Cylinder","C40")
App.ActiveDocument.C40.Radius=0.660985
App.ActiveDocument.C40.Height=20.00
App.ActiveDocument.C40.Angle=360.00 
App.ActiveDocument.C40.Placement=Base.Placement(Base.Vector(0.307883,201.150939,46.977673),Base.Rotation(-0.562489,0.006697,0.000000,0.826778))
App.ActiveDocument.addObject("Part::Cylinder","C41")
App.ActiveDocument.C41.Radius=0.670814
App.ActiveDocument.C41.Height=20.00
App.ActiveDocument.C41.Angle=360.00 
App.ActiveDocument.C41.Placement=Base.Placement(Base.Vector(0.342916,199.501012,50.797919),Base.Rotation(-0.533175,0.004474,0.000000,0.845993))
App.ActiveDocument.addObject("Part::Cylinder","C42")
App.ActiveDocument.C42.Radius=0.680632
App.ActiveDocument.C42.Height=20.00
App.ActiveDocument.C42.Angle=360.00 
App.ActiveDocument.C42.Placement=Base.Placement(Base.Vector(0.345906,197.487967,54.766003),Base.Rotation(-0.509687,0.004226,0.000000,0.860350))
App.ActiveDocument.addObject("Part::Cylinder","C43")
App.ActiveDocument.C43.Radius=0.690267
App.ActiveDocument.C43.Height=20.00
App.ActiveDocument.C43.Angle=360.00 
App.ActiveDocument.C43.Placement=Base.Placement(Base.Vector(0.343087,195.195022,58.684035),Base.Rotation(-0.486735,0.004323,0.000000,0.873539))
App.ActiveDocument.addObject("Part::Cylinder","C44")
App.ActiveDocument.C44.Radius=0.699137
App.ActiveDocument.C44.Height=20.00
App.ActiveDocument.C44.Angle=360.00 
App.ActiveDocument.C44.Placement=Base.Placement(Base.Vector(0.408667,192.823277,62.279147),Base.Rotation(-0.464021,0.000562,0.000000,0.885824))
App.ActiveDocument.addObject("Part::Cylinder","C45")
App.ActiveDocument.C45.Radius=0.707769
App.ActiveDocument.C45.Height=20.00
App.ActiveDocument.C45.Angle=360.00 
App.ActiveDocument.C45.Placement=Base.Placement(Base.Vector(0.245404,190.288361,65.714673),Base.Rotation(-0.437047,0.009630,0.000000,0.899387))
App.ActiveDocument.addObject("Part::Cylinder","C46")
App.ActiveDocument.C46.Radius=0.716316
App.ActiveDocument.C46.Height=20.00
App.ActiveDocument.C46.Angle=360.00 
App.ActiveDocument.C46.Placement=Base.Placement(Base.Vector(0.294274,187.494768,68.980905),Base.Rotation(-0.400398,0.006785,0.000000,0.916316))
App.ActiveDocument.addObject("Part::Cylinder","C47")
App.ActiveDocument.C47.Radius=0.724223
App.ActiveDocument.C47.Height=20.00
App.ActiveDocument.C47.Angle=360.00 
App.ActiveDocument.C47.Placement=Base.Placement(Base.Vector(0.384360,184.534663,71.802750),Base.Rotation(-0.349182,0.001828,0.000000,0.937053))
App.ActiveDocument.addObject("Part::Cylinder","C48")
App.ActiveDocument.C48.Radius=0.730637
App.ActiveDocument.C48.Height=20.00
App.ActiveDocument.C48.Angle=360.00 
App.ActiveDocument.C48.Placement=Base.Placement(Base.Vector(0.407995,181.562909,74.070218),Base.Rotation(-0.299447,0.000557,0.000000,0.954113))
App.ActiveDocument.addObject("Part::Cylinder","C49")
App.ActiveDocument.C49.Radius=0.736293
App.ActiveDocument.C49.Height=20.00
App.ActiveDocument.C49.Angle=360.00 
App.ActiveDocument.C49.Placement=Base.Placement(Base.Vector(0.439284,178.423627,75.991607),Base.Rotation(-0.239428,-0.001064,0.000000,0.970914))
App.ActiveDocument.addObject("Part::Cylinder","C50")
App.ActiveDocument.C50.Radius=0.740517
App.ActiveDocument.C50.Height=20.00
App.ActiveDocument.C50.Angle=360.00 
App.ActiveDocument.C50.Placement=Base.Placement(Base.Vector(0.471229,175.325039,77.304026),Base.Rotation(-0.164477,-0.002667,0.000000,0.986377))
App.ActiveDocument.addObject("Part::Cylinder","C51")
App.ActiveDocument.C51.Radius=0.743580
App.ActiveDocument.C51.Height=20.00
App.ActiveDocument.C51.Angle=360.00 
App.ActiveDocument.C51.Placement=Base.Placement(Base.Vector(0.505439,171.352810,78.390427),Base.Rotation(-0.108717,-0.004367,0.000000,0.994063))
App.ActiveDocument.addObject("Part::Cylinder","C52")
App.ActiveDocument.C52.Radius=0.745672
App.ActiveDocument.C52.Height=20.00
App.ActiveDocument.C52.Angle=360.00 
App.ActiveDocument.C52.Placement=Base.Placement(Base.Vector(0.535933,166.991423,79.204999),Base.Rotation(-0.070820,-0.005881,0.000000,0.997472))
App.ActiveDocument.addObject("Part::Cylinder","C53")
App.ActiveDocument.C53.Radius=0.746935
App.ActiveDocument.C53.Height=20.00
App.ActiveDocument.C53.Angle=360.00 
App.ActiveDocument.C53.Placement=Base.Placement(Base.Vector(0.523528,162.456868,79.715194),Base.Rotation(-0.043134,-0.005250,0.000000,0.999056))
App.ActiveDocument.addObject("Part::Cylinder","C54")
App.ActiveDocument.C54.Radius=0.747786
App.ActiveDocument.C54.Height=20.00
App.ActiveDocument.C54.Angle=360.00 
App.ActiveDocument.C54.Placement=Base.Placement(Base.Vector(0.472815,157.353942,80.092539),Base.Rotation(-0.037820,-0.002712,0.000000,0.999281))
App.ActiveDocument.addObject("Part::Cylinder","C55")
App.ActiveDocument.C55.Radius=0.748725
App.ActiveDocument.C55.Height=20.00
App.ActiveDocument.C55.Angle=360.00 
App.ActiveDocument.C55.Placement=Base.Placement(Base.Vector(0.557834,152.046859,80.537283),Base.Rotation(-0.048129,-0.006969,0.000000,0.998817))
App.ActiveDocument.addObject("Part::Cylinder","C56")
App.ActiveDocument.C56.Radius=0.749635
App.ActiveDocument.C56.Height=20.00
App.ActiveDocument.C56.Angle=360.00 
App.ActiveDocument.C56.Placement=Base.Placement(Base.Vector(0.677345,147.411085,80.927692),Base.Rotation(-0.032539,-0.012944,0.000000,0.999387))
App.ActiveDocument.addObject("Part::Cylinder","C57")
App.ActiveDocument.C57.Radius=0.746970
App.ActiveDocument.C57.Height=20.00
App.ActiveDocument.C57.Angle=360.00 
App.ActiveDocument.C57.Placement=Base.Placement(Base.Vector(0.472058,151.718975,84.280220),Base.Rotation(0.478885,-0.003044,0.000000,0.877872))
App.ActiveDocument.addObject("Part::Cylinder","C58")
App.ActiveDocument.C58.Radius=0.560093
App.ActiveDocument.C58.Height=20.00
App.ActiveDocument.C58.Angle=360.00 
App.ActiveDocument.C58.Placement=Base.Placement(Base.Vector(0.352883,206.552646,-4.155963),Base.Rotation(-0.730722,0.004815,0.000000,0.682659))
App.ActiveDocument.addObject("Part::Cylinder","C59")
App.ActiveDocument.C59.Radius=0.571254
App.ActiveDocument.C59.Height=20.00
App.ActiveDocument.C59.Angle=360.00 
App.ActiveDocument.C59.Placement=Base.Placement(Base.Vector(0.353928,206.150574,-8.903248),Base.Rotation(-0.741606,0.004822,0.000000,0.670818))
App.ActiveDocument.addObject("Part::Cylinder","C60")
App.ActiveDocument.C60.Radius=0.582381
App.ActiveDocument.C60.Height=20.00
App.ActiveDocument.C60.Angle=360.00 
App.ActiveDocument.C60.Placement=Base.Placement(Base.Vector(0.368677,205.594273,-13.623950),Base.Rotation(-0.752713,0.003793,0.000000,0.658338))
App.ActiveDocument.addObject("Part::Cylinder","C61")
App.ActiveDocument.C61.Radius=0.594071
App.ActiveDocument.C61.Height=20.00
App.ActiveDocument.C61.Angle=360.00 
App.ActiveDocument.C61.Placement=Base.Placement(Base.Vector(0.359935,204.837479,-18.552005),Base.Rotation(-0.765236,0.004558,0.000000,0.643734))
App.ActiveDocument.addObject("Part::Cylinder","C62")
App.ActiveDocument.C62.Radius=0.604485
App.ActiveDocument.C62.Height=20.00
App.ActiveDocument.C62.Angle=360.00 
App.ActiveDocument.C62.Placement=Base.Placement(Base.Vector(0.370842,203.999638,-22.915825),Base.Rotation(-0.777080,0.003795,0.000000,0.629391))
App.ActiveDocument.addObject("Part::Cylinder","C63")
App.ActiveDocument.C63.Radius=0.615347
App.ActiveDocument.C63.Height=20.00
App.ActiveDocument.C63.Angle=360.00 
App.ActiveDocument.C63.Placement=Base.Placement(Base.Vector(0.371746,202.945086,-27.405707),Base.Rotation(-0.791182,0.003832,0.000000,0.611568))
App.ActiveDocument.addObject("Part::Cylinder","C64")
App.ActiveDocument.C64.Radius=0.625798
App.ActiveDocument.C64.Height=20.00
App.ActiveDocument.C64.Angle=360.00 
App.ActiveDocument.C64.Placement=Base.Placement(Base.Vector(0.378778,201.730721,-31.647281),Base.Rotation(-0.806951,0.003373,0.000000,0.590609))
App.ActiveDocument.addObject("Part::Cylinder","C65")
App.ActiveDocument.C65.Radius=0.636275
App.ActiveDocument.C65.Height=20.00
App.ActiveDocument.C65.Angle=360.00 
App.ActiveDocument.C65.Placement=Base.Placement(Base.Vector(0.357952,200.281226,-35.751997),Base.Rotation(-0.826921,0.005395,0.000000,0.562292))
App.ActiveDocument.addObject("Part::Cylinder","C66")
App.ActiveDocument.C66.Radius=0.646244
App.ActiveDocument.C66.Height=20.00
App.ActiveDocument.C66.Angle=360.00 
App.ActiveDocument.C66.Placement=Base.Placement(Base.Vector(0.372551,198.642929,-39.452888),Base.Rotation(-0.851525,0.004393,0.000000,0.524295))
App.ActiveDocument.addObject("Part::Cylinder","C67")
App.ActiveDocument.C67.Radius=0.655677
App.ActiveDocument.C67.Height=20.00
App.ActiveDocument.C67.Angle=360.00 
App.ActiveDocument.C67.Placement=Base.Placement(Base.Vector(0.363797,196.725332,-42.807049),Base.Rotation(-0.878370,0.005735,0.000000,0.477947))
App.ActiveDocument.addObject("Part::Cylinder","C68")
App.ActiveDocument.C68.Radius=0.664479
App.ActiveDocument.C68.Height=20.00
App.ActiveDocument.C68.Angle=360.00 
App.ActiveDocument.C68.Placement=Base.Placement(Base.Vector(0.350129,194.380289,-46.047630),Base.Rotation(-0.899619,0.007843,0.000000,0.436605))
App.ActiveDocument.addObject("Part::Cylinder","C69")
App.ActiveDocument.C69.Radius=0.672430
App.ActiveDocument.C69.Height=20.00
App.ActiveDocument.C69.Angle=360.00 
App.ActiveDocument.C69.Placement=Base.Placement(Base.Vector(0.358728,191.758044,-49.086398),Base.Rotation(-0.915377,0.007439,0.000000,0.402529))
App.ActiveDocument.addObject("Part::Cylinder","C70")
App.ActiveDocument.C70.Radius=0.680253
App.ActiveDocument.C70.Height=20.00
App.ActiveDocument.C70.Angle=360.00 
App.ActiveDocument.C70.Placement=Base.Placement(Base.Vector(0.361381,188.724152,-52.219115),Base.Rotation(-0.926768,0.007620,0.000000,0.375557))
App.ActiveDocument.addObject("Part::Cylinder","C71")
App.ActiveDocument.C71.Radius=0.687558
App.ActiveDocument.C71.Height=20.00
App.ActiveDocument.C71.Angle=360.00 
App.ActiveDocument.C71.Placement=Base.Placement(Base.Vector(0.389591,185.657899,-54.951988),Base.Rotation(-0.942413,0.004340,0.000000,0.334422))
App.ActiveDocument.addObject("Part::Cylinder","C72")
App.ActiveDocument.C72.Radius=0.694064
App.ActiveDocument.C72.Height=20.00
App.ActiveDocument.C72.Angle=360.00 
App.ActiveDocument.C72.Placement=Base.Placement(Base.Vector(0.388385,182.419587,-57.307684),Base.Rotation(-0.958153,0.005282,0.000000,0.286207))
App.ActiveDocument.addObject("Part::Cylinder","C73")
App.ActiveDocument.C73.Radius=0.699674
App.ActiveDocument.C73.Height=20.00
App.ActiveDocument.C73.Angle=360.00 
App.ActiveDocument.C73.Placement=Base.Placement(Base.Vector(0.394531,178.800376,-59.452754),Base.Rotation(-0.968601,0.004845,0.000000,0.248573))
App.ActiveDocument.addObject("Part::Cylinder","C74")
App.ActiveDocument.C74.Radius=0.704741
App.ActiveDocument.C74.Height=20.00
App.ActiveDocument.C74.Angle=360.00 
App.ActiveDocument.C74.Placement=Base.Placement(Base.Vector(0.379442,174.774760,-61.519395),Base.Rotation(-0.974598,0.008753,0.000000,0.223792))
App.ActiveDocument.addObject("Part::Cylinder","C75")
App.ActiveDocument.C75.Radius=0.709396
App.ActiveDocument.C75.Height=20.00
App.ActiveDocument.C75.Angle=360.00 
App.ActiveDocument.C75.Placement=Base.Placement(Base.Vector(0.369376,170.544453,-63.480468),Base.Rotation(-0.978469,0.011949,0.000000,0.206047))
App.ActiveDocument.addObject("Part::Cylinder","C76")
App.ActiveDocument.C76.Radius=0.713817
App.ActiveDocument.C76.Height=20.00
App.ActiveDocument.C76.Angle=360.00 
App.ActiveDocument.C76.Placement=Base.Placement(Base.Vector(0.342285,166.180081,-65.285994),Base.Rotation(-0.983458,0.021217,0.000000,0.179887))
App.ActiveDocument.addObject("Part::Cylinder","C77")
App.ActiveDocument.C77.Radius=0.717186
App.ActiveDocument.C77.Height=20.00
App.ActiveDocument.C77.Angle=360.00 
App.ActiveDocument.C77.Placement=Base.Placement(Base.Vector(0.357222,162.300080,-66.624799),Base.Rotation(-0.988321,0.020327,0.000000,0.151023))
App.ActiveDocument.addObject("Part::Cylinder","C78")
App.ActiveDocument.C78.Radius=0.720010
App.ActiveDocument.C78.Height=20.00
App.ActiveDocument.C78.Angle=360.00 
App.ActiveDocument.C78.Placement=Base.Placement(Base.Vector(0.359625,158.261671,-67.760689),Base.Rotation(-0.991944,0.023704,0.000000,0.124438))
App.ActiveDocument.addObject("Part::Cylinder","C79")
App.ActiveDocument.C79.Radius=0.722335
App.ActiveDocument.C79.Height=20.00
App.ActiveDocument.C79.Angle=360.00 
App.ActiveDocument.C79.Placement=Base.Placement(Base.Vector(0.362196,154.091159,-68.719686),Base.Rotation(-0.994285,0.027338,0.000000,0.103195))
App.ActiveDocument.addObject("Part::Cylinder","C80")
App.ActiveDocument.C80.Radius=0.724279
App.ActiveDocument.C80.Height=20.00
App.ActiveDocument.C80.Angle=360.00 
App.ActiveDocument.C80.Placement=Base.Placement(Base.Vector(0.372654,149.793349,-69.526073),Base.Rotation(-0.996198,0.027842,0.000000,0.082545))
App.ActiveDocument.addObject("Part::Cylinder","C81")
App.ActiveDocument.C81.Radius=0.725796
App.ActiveDocument.C81.Height=20.00
App.ActiveDocument.C81.Angle=360.00 
App.ActiveDocument.C81.Placement=Base.Placement(Base.Vector(0.366894,145.506043,-70.157892),Base.Rotation(-0.997166,0.040994,0.000000,0.063087))
App.ActiveDocument.addObject("Part::Cylinder","C82")
App.ActiveDocument.C82.Radius=0.726879
App.ActiveDocument.C82.Height=20.00
App.ActiveDocument.C82.Angle=360.00 
App.ActiveDocument.C82.Placement=Base.Placement(Base.Vector(0.376582,141.216597,-70.599171),Base.Rotation(-0.997742,0.055437,0.000000,0.037914))
App.ActiveDocument.addObject("Part::Cylinder","C83")
App.ActiveDocument.C83.Radius=0.727403
App.ActiveDocument.C83.Height=20.00
App.ActiveDocument.C83.Angle=360.00 
App.ActiveDocument.C83.Placement=Base.Placement(Base.Vector(0.368750,137.066144,-70.809980),Base.Rotation(-0.967973,0.250857,0.000000,0.009940))
App.ActiveDocument.addObject("Part::Cylinder","C84")
App.ActiveDocument.C84.Radius=0.727284
App.ActiveDocument.C84.Height=20.00
App.ActiveDocument.C84.Angle=360.00 
App.ActiveDocument.C84.Placement=Base.Placement(Base.Vector(0.381646,132.768271,-70.766955),Base.Rotation(0.996993,0.073276,0.000000,0.025228))
App.ActiveDocument.addObject("Part::Cylinder","C85")
App.ActiveDocument.C85.Radius=0.726401
App.ActiveDocument.C85.Height=20.00
App.ActiveDocument.C85.Angle=360.00 
App.ActiveDocument.C85.Placement=Base.Placement(Base.Vector(0.392463,128.444325,-70.421818),Base.Rotation(0.998033,0.022327,0.000000,0.058572))
App.ActiveDocument.addObject("Part::Cylinder","C86")
App.ActiveDocument.C86.Radius=0.724678
App.ActiveDocument.C86.Height=20.00
App.ActiveDocument.C86.Angle=360.00 
App.ActiveDocument.C86.Placement=Base.Placement(Base.Vector(0.406978,123.964950,-69.736876),Base.Rotation(0.995816,0.006384,0.000000,0.091162))
App.ActiveDocument.addObject("Part::Cylinder","C87")
App.ActiveDocument.C87.Radius=0.722318
App.ActiveDocument.C87.Height=20.00
App.ActiveDocument.C87.Angle=360.00 
App.ActiveDocument.C87.Placement=Base.Placement(Base.Vector(0.403721,119.604115,-68.782621),Base.Rotation(0.992864,0.006254,0.000000,0.119090))
App.ActiveDocument.addObject("Part::Cylinder","C88")
App.ActiveDocument.C88.Radius=0.719372
App.ActiveDocument.C88.Height=20.00
App.ActiveDocument.C88.Angle=360.00 
App.ActiveDocument.C88.Placement=Base.Placement(Base.Vector(0.311685,115.573217,-67.651992),Base.Rotation(0.987066,0.034134,0.000000,0.156636))
App.ActiveDocument.addObject("Part::Cylinder","C89")
App.ActiveDocument.C89.Radius=0.715505
App.ActiveDocument.C89.Height=20.00
App.ActiveDocument.C89.Angle=360.00 
App.ActiveDocument.C89.Placement=Base.Placement(Base.Vector(0.047329,112.365530,-66.537427),Base.Rotation(0.968152,0.078037,0.000000,0.237892))
App.ActiveDocument.addObject("Part::Cylinder","C90")
App.ActiveDocument.C90.Radius=0.708943
App.ActiveDocument.C90.Height=20.00
App.ActiveDocument.C90.Angle=360.00 
App.ActiveDocument.C90.Placement=Base.Placement(Base.Vector(0.120871,110.566139,-65.258135),Base.Rotation(0.925644,0.039560,0.000000,0.376321))
App.ActiveDocument.addObject("Part::Cylinder","C91")
App.ActiveDocument.C91.Radius=0.700497
App.ActiveDocument.C91.Height=20.00
App.ActiveDocument.C91.Angle=360.00 
App.ActiveDocument.C91.Placement=Base.Placement(Base.Vector(0.343863,108.925128,-63.741762),Base.Rotation(0.861617,0.007365,0.000000,0.507506))
App.ActiveDocument.addObject("Part::Cylinder","C92")
App.ActiveDocument.C92.Radius=0.553968
App.ActiveDocument.C92.Height=20.00
App.ActiveDocument.C92.Angle=360.00 
App.ActiveDocument.C92.Placement=Base.Placement(Base.Vector(4.396683,206.686642,5.145729),Base.Rotation(-0.704497,0.076587,0.000000,0.705563))
App.ActiveDocument.addObject("Part::Cylinder","C93")
App.ActiveDocument.C93.Radius=0.547872
App.ActiveDocument.C93.Height=20.00
App.ActiveDocument.C93.Angle=360.00 
App.ActiveDocument.C93.Placement=Base.Placement(Base.Vector(8.682647,206.021623,5.359275),Base.Rotation(-0.691365,0.136106,0.000000,0.709570))
App.ActiveDocument.addObject("Part::Cylinder","C94")
App.ActiveDocument.C94.Radius=0.541029
App.ActiveDocument.C94.Height=20.00
App.ActiveDocument.C94.Angle=360.00 
App.ActiveDocument.C94.Placement=Base.Placement(Base.Vector(12.768967,205.033175,5.098409),Base.Rotation(-0.674753,0.191136,0.000000,0.712864))
App.ActiveDocument.addObject("Part::Cylinder","C95")
App.ActiveDocument.C95.Radius=0.534549
App.ActiveDocument.C95.Height=20.00
App.ActiveDocument.C95.Angle=360.00 
App.ActiveDocument.C95.Placement=Base.Placement(Base.Vector(16.972532,203.703261,4.941350),Base.Rotation(-0.658978,0.230173,0.000000,0.716079))
App.ActiveDocument.addObject("Part::Cylinder","C96")
App.ActiveDocument.C96.Radius=0.528679
App.ActiveDocument.C96.Height=20.00
App.ActiveDocument.C96.Angle=360.00 
App.ActiveDocument.C96.Placement=Base.Placement(Base.Vector(20.946568,202.117359,5.081426),Base.Rotation(-0.636843,0.282085,0.000000,0.717537))
App.ActiveDocument.addObject("Part::Cylinder","C97")
App.ActiveDocument.C97.Radius=0.522228
App.ActiveDocument.C97.Height=20.00
App.ActiveDocument.C97.Angle=360.00 
App.ActiveDocument.C97.Placement=Base.Placement(Base.Vector(25.091121,200.146987,4.949071),Base.Rotation(-0.619996,0.317119,0.000000,0.717663))
App.ActiveDocument.addObject("Part::Cylinder","C98")
App.ActiveDocument.C98.Radius=0.516602
App.ActiveDocument.C98.Height=20.00
App.ActiveDocument.C98.Angle=360.00 
App.ActiveDocument.C98.Placement=Base.Placement(Base.Vector(29.093608,197.952539,5.046878),Base.Rotation(-0.601454,0.348459,0.000000,0.718909))
App.ActiveDocument.addObject("Part::Cylinder","C99")
App.ActiveDocument.C99.Radius=0.510796
App.ActiveDocument.C99.Height=20.00
App.ActiveDocument.C99.Angle=360.00 
App.ActiveDocument.C99.Placement=Base.Placement(Base.Vector(32.766069,195.699776,4.891961),Base.Rotation(-0.574045,0.387007,0.000000,0.721594))
App.ActiveDocument.addObject("Part::Cylinder","C100")
App.ActiveDocument.C100.Radius=0.505357
App.ActiveDocument.C100.Height=20.00
App.ActiveDocument.C100.Angle=360.00 
App.ActiveDocument.C100.Placement=Base.Placement(Base.Vector(35.955719,193.338733,4.834592),Base.Rotation(-0.528220,0.445992,0.000000,0.722547))
App.ActiveDocument.addObject("Part::Cylinder","C101")
App.ActiveDocument.C101.Radius=0.500488
App.ActiveDocument.C101.Height=20.00
App.ActiveDocument.C101.Angle=360.00 
App.ActiveDocument.C101.Placement=Base.Placement(Base.Vector(38.859703,190.609427,4.815739),Base.Rotation(-0.480073,0.497207,0.000000,0.722714))
App.ActiveDocument.addObject("Part::Cylinder","C102")
App.ActiveDocument.C102.Radius=0.496568
App.ActiveDocument.C102.Height=20.00
App.ActiveDocument.C102.Angle=360.00 
App.ActiveDocument.C102.Placement=Base.Placement(Base.Vector(41.494759,187.572893,4.982012),Base.Rotation(-0.427905,0.541262,0.000000,0.723832))
App.ActiveDocument.addObject("Part::Cylinder","C103")
App.ActiveDocument.C103.Radius=0.492316
App.ActiveDocument.C103.Height=20.00
App.ActiveDocument.C103.Angle=360.00 
App.ActiveDocument.C103.Placement=Base.Placement(Base.Vector(44.087962,183.982097,4.842863),Base.Rotation(-0.384533,0.571092,0.000000,0.725251))
App.ActiveDocument.addObject("Part::Cylinder","C104")
App.ActiveDocument.C104.Radius=0.488514
App.ActiveDocument.C104.Height=20.00
App.ActiveDocument.C104.Angle=360.00 
App.ActiveDocument.C104.Placement=Base.Placement(Base.Vector(46.456409,180.259479,4.697643),Base.Rotation(-0.343280,0.594159,0.000000,0.727416))
App.ActiveDocument.addObject("Part::Cylinder","C105")
App.ActiveDocument.C105.Radius=0.485742
App.ActiveDocument.C105.Height=20.00
App.ActiveDocument.C105.Angle=360.00 
App.ActiveDocument.C105.Placement=Base.Placement(Base.Vector(48.257327,176.755677,4.699803),Base.Rotation(-0.284408,0.621184,0.000000,0.730235))
App.ActiveDocument.addObject("Part::Cylinder","C106")
App.ActiveDocument.C106.Radius=0.483145
App.ActiveDocument.C106.Height=20.00
App.ActiveDocument.C106.Angle=360.00 
App.ActiveDocument.C106.Placement=Base.Placement(Base.Vector(49.401212,173.603859,4.434563),Base.Rotation(-0.196045,0.652032,0.000000,0.732408))
App.ActiveDocument.addObject("Part::Cylinder","C107")
App.ActiveDocument.C107.Radius=0.481454
App.ActiveDocument.C107.Height=20.00
App.ActiveDocument.C107.Angle=360.00 
App.ActiveDocument.C107.Placement=Base.Placement(Base.Vector(50.378188,169.544757,4.472478),Base.Rotation(-0.131499,0.670725,0.000000,0.729956))
App.ActiveDocument.addObject("Part::Cylinder","C108")
App.ActiveDocument.C108.Radius=0.480367
App.ActiveDocument.C108.Height=20.00
App.ActiveDocument.C108.Angle=360.00 
App.ActiveDocument.C108.Placement=Base.Placement(Base.Vector(51.160467,164.988506,4.665912),Base.Rotation(-0.098537,0.682228,0.000000,0.724469))
App.ActiveDocument.addObject("Part::Cylinder","C109")
App.ActiveDocument.C109.Radius=0.479533
App.ActiveDocument.C109.Height=20.00
App.ActiveDocument.C109.Angle=360.00 
App.ActiveDocument.C109.Placement=Base.Placement(Base.Vector(51.700361,160.549233,4.856771),Base.Rotation(-0.062438,0.693784,0.000000,0.717471))
App.ActiveDocument.addObject("Part::Cylinder","C110")
App.ActiveDocument.C110.Radius=0.479725
App.ActiveDocument.C110.Height=20.00
App.ActiveDocument.C110.Angle=360.00 
App.ActiveDocument.C110.Placement=Base.Placement(Base.Vector(51.940023,156.351553,5.230643),Base.Rotation(-0.011860,0.700690,0.000000,0.713367))
App.ActiveDocument.addObject("Part::Cylinder","C111")
App.ActiveDocument.C111.Radius=0.479812
App.ActiveDocument.C111.Height=20.00
App.ActiveDocument.C111.Angle=360.00 
App.ActiveDocument.C111.Placement=Base.Placement(Base.Vector(51.793564,152.485878,5.082235),Base.Rotation(0.070469,0.694755,0.000000,0.715786))
App.ActiveDocument.addObject("Part::Cylinder","C112")
App.ActiveDocument.C112.Radius=0.480843
App.ActiveDocument.C112.Height=20.00
App.ActiveDocument.C112.Angle=360.00 
App.ActiveDocument.C112.Placement=Base.Placement(Base.Vector(51.190081,147.995123,4.991801),Base.Rotation(0.105579,0.684763,0.000000,0.721078))
App.ActiveDocument.addObject("Part::Cylinder","C113")
App.ActiveDocument.C113.Radius=0.481203
App.ActiveDocument.C113.Height=20.00
App.ActiveDocument.C113.Angle=360.00 
App.ActiveDocument.C113.Placement=Base.Placement(Base.Vector(50.718836,140.777671,5.225192),Base.Rotation(-0.057914,0.701177,0.000000,0.710631))
App.ActiveDocument.addObject("Part::Cylinder","C114")
App.ActiveDocument.C114.Radius=0.479747
App.ActiveDocument.C114.Height=20.00
App.ActiveDocument.C114.Angle=360.00 
App.ActiveDocument.C114.Placement=Base.Placement(Base.Vector(51.905374,134.850982,5.287739),Base.Rotation(-0.129218,0.694839,0.000000,0.707462))
App.ActiveDocument.addObject("Part::Cylinder","C115")
App.ActiveDocument.C115.Radius=0.479656
App.ActiveDocument.C115.Height=20.00
App.ActiveDocument.C115.Angle=360.00 
App.ActiveDocument.C115.Placement=Base.Placement(Base.Vector(52.014811,132.415221,4.690128),Base.Rotation(0.046248,0.680154,0.000000,0.731609))
App.ActiveDocument.addObject("Part::Cylinder","C116")
App.ActiveDocument.C116.Radius=0.480707
App.ActiveDocument.C116.Height=20.00
App.ActiveDocument.C116.Angle=360.00 
App.ActiveDocument.C116.Placement=Base.Placement(Base.Vector(51.522718,128.500838,4.660365),Base.Rotation(0.115567,0.666987,0.000000,0.736052))
App.ActiveDocument.addObject("Part::Cylinder","C117")
App.ActiveDocument.C117.Radius=0.481882
App.ActiveDocument.C117.Height=20.00
App.ActiveDocument.C117.Angle=360.00 
App.ActiveDocument.C117.Placement=Base.Placement(Base.Vector(50.630429,124.508684,4.563763),Base.Rotation(0.165467,0.656445,0.000000,0.736003))
App.ActiveDocument.addObject("Part::Cylinder","C118")
App.ActiveDocument.C118.Radius=0.483519
App.ActiveDocument.C118.Height=20.00
App.ActiveDocument.C118.Angle=360.00 
App.ActiveDocument.C118.Placement=Base.Placement(Base.Vector(49.385190,120.168661,4.319125),Base.Rotation(0.193456,0.642690,0.000000,0.741299))
App.ActiveDocument.addObject("Part::Cylinder","C119")
App.ActiveDocument.C119.Radius=0.485211
App.ActiveDocument.C119.Height=20.00
App.ActiveDocument.C119.Angle=360.00 
App.ActiveDocument.C119.Placement=Base.Placement(Base.Vector(48.021039,114.939792,3.867326),Base.Rotation(0.162387,0.634330,0.000000,0.755815))
App.ActiveDocument.addObject("Part::Cylinder","C120")
App.ActiveDocument.C120.Radius=0.487347
App.ActiveDocument.C120.Height=20.00
App.ActiveDocument.C120.Angle=360.00 
App.ActiveDocument.C120.Placement=Base.Placement(Base.Vector(52.743897,116.914470,2.652417),Base.Rotation(0.595201,0.173137,0.000000,0.784703))
App.ActiveDocument.addObject("Part::Cylinder","C121")
App.ActiveDocument.C121.Radius=0.565179
App.ActiveDocument.C121.Height=20.00
App.ActiveDocument.C121.Angle=360.00 
App.ActiveDocument.C121.Placement=Base.Placement(Base.Vector(4.301399,206.656998,9.982949),Base.Rotation(-0.694511,0.082920,0.000000,0.714688))
App.ActiveDocument.addObject("Part::Cylinder","C122")
App.ActiveDocument.C122.Radius=0.558878
App.ActiveDocument.C122.Height=20.00
App.ActiveDocument.C122.Angle=360.00 
App.ActiveDocument.C122.Placement=Base.Placement(Base.Vector(8.424013,205.983576,10.003781),Base.Rotation(-0.683205,0.137133,0.000000,0.717235))
App.ActiveDocument.addObject("Part::Cylinder","C123")
App.ActiveDocument.C123.Radius=0.552134
App.ActiveDocument.C123.Height=20.00
App.ActiveDocument.C123.Angle=360.00 
App.ActiveDocument.C123.Placement=Base.Placement(Base.Vector(12.457008,204.988082,9.794278),Base.Rotation(-0.664826,0.196556,0.000000,0.720675))
App.ActiveDocument.addObject("Part::Cylinder","C124")
App.ActiveDocument.C124.Radius=0.546084
App.ActiveDocument.C124.Height=20.00
App.ActiveDocument.C124.Angle=360.00 
App.ActiveDocument.C124.Placement=Base.Placement(Base.Vector(16.779009,203.575445,9.862971),Base.Rotation(-0.650258,0.230565,0.000000,0.723882))
App.ActiveDocument.addObject("Part::Cylinder","C125")
App.ActiveDocument.C125.Radius=0.540358
App.ActiveDocument.C125.Height=20.00
App.ActiveDocument.C125.Angle=360.00 
App.ActiveDocument.C125.Placement=Base.Placement(Base.Vector(20.657840,202.026228,9.991868),Base.Rotation(-0.630740,0.277647,0.000000,0.724624))
App.ActiveDocument.addObject("Part::Cylinder","C126")
App.ActiveDocument.C126.Radius=0.533717
App.ActiveDocument.C126.Height=20.00
App.ActiveDocument.C126.Angle=360.00 
App.ActiveDocument.C126.Placement=Base.Placement(Base.Vector(24.642597,200.166937,9.704092),Base.Rotation(-0.614999,0.312802,0.000000,0.723831))
App.ActiveDocument.addObject("Part::Cylinder","C127")
App.ActiveDocument.C127.Radius=0.528462
App.ActiveDocument.C127.Height=20.00
App.ActiveDocument.C127.Angle=360.00 
App.ActiveDocument.C127.Placement=Base.Placement(Base.Vector(28.548575,198.032522,9.936156),Base.Rotation(-0.594956,0.346783,0.000000,0.725099))
App.ActiveDocument.addObject("Part::Cylinder","C128")
App.ActiveDocument.C128.Radius=0.522315
App.ActiveDocument.C128.Height=20.00
App.ActiveDocument.C128.Angle=360.00 
App.ActiveDocument.C128.Placement=Base.Placement(Base.Vector(32.325989,195.708584,9.674060),Base.Rotation(-0.571466,0.380814,0.000000,0.726916))
App.ActiveDocument.addObject("Part::Cylinder","C129")
App.ActiveDocument.C129.Radius=0.517115
App.ActiveDocument.C129.Height=20.00
App.ActiveDocument.C129.Angle=360.00 
App.ActiveDocument.C129.Placement=Base.Placement(Base.Vector(35.528463,193.361072,9.712388),Base.Rotation(-0.527444,0.437762,0.000000,0.728126))
App.ActiveDocument.addObject("Part::Cylinder","C130")
App.ActiveDocument.C130.Radius=0.511951
App.ActiveDocument.C130.Height=20.00
App.ActiveDocument.C130.Angle=360.00 
App.ActiveDocument.C130.Placement=Base.Placement(Base.Vector(38.428983,190.694217,9.552881),Base.Rotation(-0.482173,0.487349,0.000000,0.728011))
App.ActiveDocument.addObject("Part::Cylinder","C131")
App.ActiveDocument.C131.Radius=0.508088
App.ActiveDocument.C131.Height=20.00
App.ActiveDocument.C131.Angle=360.00 
App.ActiveDocument.C131.Placement=Base.Placement(Base.Vector(40.993713,187.791316,9.741588),Base.Rotation(-0.430415,0.533287,0.000000,0.728249))
App.ActiveDocument.addObject("Part::Cylinder","C132")
App.ActiveDocument.C132.Radius=0.503794
App.ActiveDocument.C132.Height=20.00
App.ActiveDocument.C132.Angle=360.00 
App.ActiveDocument.C132.Placement=Base.Placement(Base.Vector(43.445712,184.438726,9.524141),Base.Rotation(-0.383362,0.566123,0.000000,0.729752))
App.ActiveDocument.addObject("Part::Cylinder","C133")
App.ActiveDocument.C133.Radius=0.500111
App.ActiveDocument.C133.Height=20.00
App.ActiveDocument.C133.Angle=360.00 
App.ActiveDocument.C133.Placement=Base.Placement(Base.Vector(45.796713,180.765616,9.395011),Base.Rotation(-0.344839,0.587129,0.000000,0.732370))
App.ActiveDocument.addObject("Part::Cylinder","C134")
App.ActiveDocument.C134.Radius=0.497230
App.ActiveDocument.C134.Height=20.00
App.ActiveDocument.C134.Angle=360.00 
App.ActiveDocument.C134.Placement=Base.Placement(Base.Vector(47.654487,177.223132,9.342113),Base.Rotation(-0.291271,0.611279,0.000000,0.735867))
App.ActiveDocument.addObject("Part::Cylinder","C135")
App.ActiveDocument.C135.Radius=0.494555
App.ActiveDocument.C135.Height=20.00
App.ActiveDocument.C135.Angle=360.00 
App.ActiveDocument.C135.Placement=Base.Placement(Base.Vector(48.868486,174.003111,9.066319),Base.Rotation(-0.198157,0.643399,0.000000,0.739440))
App.ActiveDocument.addObject("Part::Cylinder","C136")
App.ActiveDocument.C136.Radius=0.492934
App.ActiveDocument.C136.Height=20.00
App.ActiveDocument.C136.Angle=360.00 
App.ActiveDocument.C136.Placement=Base.Placement(Base.Vector(49.923443,169.893647,9.138557),Base.Rotation(-0.145327,0.659081,0.000000,0.737897))
App.ActiveDocument.addObject("Part::Cylinder","C137")
App.ActiveDocument.C137.Radius=0.491323
App.ActiveDocument.C137.Height=20.00
App.ActiveDocument.C137.Angle=360.00 
App.ActiveDocument.C137.Placement=Base.Placement(Base.Vector(50.788184,165.451505,9.135779),Base.Rotation(-0.112942,0.670747,0.000000,0.733036))
App.ActiveDocument.addObject("Part::Cylinder","C138")
App.ActiveDocument.C138.Radius=0.490833
App.ActiveDocument.C138.Height=20.00
App.ActiveDocument.C138.Angle=360.00 
App.ActiveDocument.C138.Placement=Base.Placement(Base.Vector(51.449580,160.852309,9.527061),Base.Rotation(-0.082382,0.681406,0.000000,0.727255))
App.ActiveDocument.addObject("Part::Cylinder","C139")
App.ActiveDocument.C139.Radius=0.490520
App.ActiveDocument.C139.Height=20.00
App.ActiveDocument.C139.Angle=360.00 
App.ActiveDocument.C139.Placement=Base.Placement(Base.Vector(51.788674,156.897349,9.790591),Base.Rotation(-0.022738,0.691667,0.000000,0.721858))
App.ActiveDocument.addObject("Part::Cylinder","C140")
App.ActiveDocument.C140.Radius=0.490443
App.ActiveDocument.C140.Height=20.00
App.ActiveDocument.C140.Angle=360.00 
App.ActiveDocument.C140.Placement=Base.Placement(Base.Vector(51.709262,153.124454,9.682076),Base.Rotation(0.067041,0.688753,0.000000,0.721890))
App.ActiveDocument.addObject("Part::Cylinder","C141")
App.ActiveDocument.C141.Radius=0.491924
App.ActiveDocument.C141.Height=20.00
App.ActiveDocument.C141.Angle=360.00 
App.ActiveDocument.C141.Placement=Base.Placement(Base.Vector(51.074447,148.575500,9.924449),Base.Rotation(0.100816,0.684206,0.000000,0.722287))
App.ActiveDocument.addObject("Part::Cylinder","C142")
App.ActiveDocument.C142.Radius=0.492480
App.ActiveDocument.C142.Height=20.00
App.ActiveDocument.C142.Angle=360.00 
App.ActiveDocument.C142.Placement=Base.Placement(Base.Vector(50.562174,141.574502,9.960568),Base.Rotation(-0.044808,0.691576,0.000000,0.720913))
App.ActiveDocument.addObject("Part::Cylinder","C143")
App.ActiveDocument.C143.Radius=0.490952
App.ActiveDocument.C143.Height=20.00
App.ActiveDocument.C143.Angle=360.00 
App.ActiveDocument.C143.Placement=Base.Placement(Base.Vector(51.637232,135.769921,9.835307),Base.Rotation(-0.104758,0.684274,0.000000,0.721661))
App.ActiveDocument.addObject("Part::Cylinder","C144")
App.ActiveDocument.C144.Radius=0.492089
App.ActiveDocument.C144.Height=20.00
App.ActiveDocument.C144.Angle=360.00 
App.ActiveDocument.C144.Placement=Base.Placement(Base.Vector(51.616581,133.251214,10.062298),Base.Rotation(0.054024,0.678569,0.000000,0.732547))
App.ActiveDocument.addObject("Part::Cylinder","C145")
App.ActiveDocument.C145.Radius=0.492587
App.ActiveDocument.C145.Height=20.00
App.ActiveDocument.C145.Angle=360.00 
App.ActiveDocument.C145.Placement=Base.Placement(Base.Vector(51.161759,129.225232,9.678973),Base.Rotation(0.102924,0.662820,0.000000,0.741671))
App.ActiveDocument.addObject("Part::Cylinder","C146")
App.ActiveDocument.C146.Radius=0.493296
App.ActiveDocument.C146.Height=20.00
App.ActiveDocument.C146.Angle=360.00 
App.ActiveDocument.C146.Placement=Base.Placement(Base.Vector(50.366363,125.426360,9.251168),Base.Rotation(0.164008,0.644726,0.000000,0.746612))
App.ActiveDocument.addObject("Part::Cylinder","C147")
App.ActiveDocument.C147.Radius=0.494801
App.ActiveDocument.C147.Height=20.00
App.ActiveDocument.C147.Angle=360.00 
App.ActiveDocument.C147.Placement=Base.Placement(Base.Vector(49.129411,121.277996,8.882960),Base.Rotation(0.209269,0.624754,0.000000,0.752256))
App.ActiveDocument.addObject("Part::Cylinder","C148")
App.ActiveDocument.C148.Radius=0.496900
App.ActiveDocument.C148.Height=20.00
App.ActiveDocument.C148.Angle=360.00 
App.ActiveDocument.C148.Placement=Base.Placement(Base.Vector(47.594757,116.407072,8.644736),Base.Rotation(0.187368,0.619877,0.000000,0.762001))
App.ActiveDocument.addObject("Part::Cylinder","C149")
App.ActiveDocument.C149.Radius=0.499324
App.ActiveDocument.C149.Height=20.00
App.ActiveDocument.C149.Angle=360.00 
App.ActiveDocument.C149.Placement=Base.Placement(Base.Vector(46.989388,114.014301,7.097941),Base.Rotation(0.315139,0.498066,0.000000,0.807847))
App.ActiveDocument.addObject("Part::Cylinder","C150")
App.ActiveDocument.C150.Radius=0.576323
App.ActiveDocument.C150.Height=20.00
App.ActiveDocument.C150.Angle=360.00 
App.ActiveDocument.C150.Placement=Base.Placement(Base.Vector(4.181027,206.511196,14.760956),Base.Rotation(-0.685828,0.084717,0.000000,0.722816))
App.ActiveDocument.addObject("Part::Cylinder","C151")
App.ActiveDocument.C151.Radius=0.569999
App.ActiveDocument.C151.Height=20.00
App.ActiveDocument.C151.Angle=360.00 
App.ActiveDocument.C151.Placement=Base.Placement(Base.Vector(8.307248,205.809444,14.824277),Base.Rotation(-0.673875,0.142820,0.000000,0.724910))
App.ActiveDocument.addObject("Part::Cylinder","C152")
App.ActiveDocument.C152.Radius=0.563361
App.ActiveDocument.C152.Height=20.00
App.ActiveDocument.C152.Angle=360.00 
App.ActiveDocument.C152.Placement=Base.Placement(Base.Vector(12.239619,204.807607,14.627542),Base.Rotation(-0.655472,0.202335,0.000000,0.727610))
App.ActiveDocument.addObject("Part::Cylinder","C153")
App.ActiveDocument.C153.Radius=0.557308
App.ActiveDocument.C153.Height=20.00
App.ActiveDocument.C153.Angle=360.00 
App.ActiveDocument.C153.Placement=Base.Placement(Base.Vector(16.531311,203.371576,14.648069),Base.Rotation(-0.643452,0.230400,0.000000,0.729990))
App.ActiveDocument.addObject("Part::Cylinder","C154")
App.ActiveDocument.C154.Radius=0.551480
App.ActiveDocument.C154.Height=20.00
App.ActiveDocument.C154.Angle=360.00 
App.ActiveDocument.C154.Placement=Base.Placement(Base.Vector(20.569729,201.754624,14.814228),Base.Rotation(-0.625688,0.274286,0.000000,0.730262))
App.ActiveDocument.addObject("Part::Cylinder","C155")
App.ActiveDocument.C155.Radius=0.544173
App.ActiveDocument.C155.Height=20.00
App.ActiveDocument.C155.Angle=360.00 
App.ActiveDocument.C155.Placement=Base.Placement(Base.Vector(24.664038,199.869360,14.319580),Base.Rotation(-0.610169,0.310645,0.000000,0.728830))
App.ActiveDocument.addObject("Part::Cylinder","C156")
App.ActiveDocument.C156.Radius=0.539646
App.ActiveDocument.C156.Height=20.00
App.ActiveDocument.C156.Angle=360.00 
App.ActiveDocument.C156.Placement=Base.Placement(Base.Vector(28.607040,197.659940,14.956980),Base.Rotation(-0.586722,0.350336,0.000000,0.730084))
App.ActiveDocument.addObject("Part::Cylinder","C157")
App.ActiveDocument.C157.Radius=0.533611
App.ActiveDocument.C157.Height=20.00
App.ActiveDocument.C157.Angle=360.00 
App.ActiveDocument.C157.Placement=Base.Placement(Base.Vector(32.311498,195.331733,14.685125),Base.Rotation(-0.563046,0.383197,0.000000,0.732215))
App.ActiveDocument.addObject("Part::Cylinder","C158")
App.ActiveDocument.C158.Radius=0.528445
App.ActiveDocument.C158.Height=20.00
App.ActiveDocument.C158.Angle=360.00 
App.ActiveDocument.C158.Placement=Base.Placement(Base.Vector(35.521954,192.930307,14.706500),Base.Rotation(-0.522973,0.434742,0.000000,0.733143))
App.ActiveDocument.addObject("Part::Cylinder","C159")
App.ActiveDocument.C159.Radius=0.522674
App.ActiveDocument.C159.Height=20.00
App.ActiveDocument.C159.Angle=360.00 
App.ActiveDocument.C159.Placement=Base.Placement(Base.Vector(38.437663,190.234828,14.337515),Base.Rotation(-0.476174,0.487431,0.000000,0.731894))
App.ActiveDocument.addObject("Part::Cylinder","C160")
App.ActiveDocument.C160.Radius=0.518892
App.ActiveDocument.C160.Height=20.00
App.ActiveDocument.C160.Angle=360.00 
App.ActiveDocument.C160.Placement=Base.Placement(Base.Vector(40.927963,187.350173,14.539169),Base.Rotation(-0.418301,0.536866,0.000000,0.732666))
App.ActiveDocument.addObject("Part::Cylinder","C161")
App.ActiveDocument.C161.Radius=0.515033
App.ActiveDocument.C161.Height=20.00
App.ActiveDocument.C161.Angle=360.00 
App.ActiveDocument.C161.Placement=Base.Placement(Base.Vector(43.468106,183.756201,14.532481),Base.Rotation(-0.367684,0.568876,0.000000,0.735655))
App.ActiveDocument.addObject("Part::Cylinder","C162")
App.ActiveDocument.C162.Radius=0.511211
App.ActiveDocument.C162.Height=20.00
App.ActiveDocument.C162.Angle=360.00 
App.ActiveDocument.C162.Placement=Base.Placement(Base.Vector(45.752961,180.029782,14.263158),Base.Rotation(-0.331813,0.586681,0.000000,0.738719))
App.ActiveDocument.addObject("Part::Cylinder","C163")
App.ActiveDocument.C163.Radius=0.508159
App.ActiveDocument.C163.Height=20.00
App.ActiveDocument.C163.Angle=360.00 
App.ActiveDocument.C163.Placement=Base.Placement(Base.Vector(47.442165,176.547489,14.068745),Base.Rotation(-0.250259,0.619487,0.000000,0.744047))
App.ActiveDocument.addObject("Part::Cylinder","C164")
App.ActiveDocument.C164.Radius=0.505795
App.ActiveDocument.C164.Height=20.00
App.ActiveDocument.C164.Angle=360.00 
App.ActiveDocument.C164.Placement=Base.Placement(Base.Vector(48.678105,172.901049,13.925837),Base.Rotation(-0.182825,0.641849,0.000000,0.744718))
App.ActiveDocument.addObject("Part::Cylinder","C165")
App.ActiveDocument.C165.Radius=0.504308
App.ActiveDocument.C165.Height=20.00
App.ActiveDocument.C165.Angle=360.00 
App.ActiveDocument.C165.Placement=Base.Placement(Base.Vector(49.715046,168.641891,14.050437),Base.Rotation(-0.144506,0.654674,0.000000,0.741970))
App.ActiveDocument.addObject("Part::Cylinder","C166")
App.ActiveDocument.C166.Radius=0.503064
App.ActiveDocument.C166.Height=20.00
App.ActiveDocument.C166.Angle=360.00 
App.ActiveDocument.C166.Placement=Base.Placement(Base.Vector(50.578445,164.212789,14.189297),Base.Rotation(-0.117556,0.664836,0.000000,0.737681))
App.ActiveDocument.addObject("Part::Cylinder","C167")
App.ActiveDocument.C167.Radius=0.502134
App.ActiveDocument.C167.Height=20.00
App.ActiveDocument.C167.Angle=360.00 
App.ActiveDocument.C167.Placement=Base.Placement(Base.Vector(51.270262,159.612493,14.336082),Base.Rotation(-0.072572,0.674597,0.000000,0.734611))
App.ActiveDocument.addObject("Part::Cylinder","C168")
App.ActiveDocument.C168.Radius=0.501622
App.ActiveDocument.C168.Height=20.00
App.ActiveDocument.C168.Angle=360.00 
App.ActiveDocument.C168.Placement=Base.Placement(Base.Vector(51.550641,155.881746,14.266179),Base.Rotation(0.012570,0.676985,0.000000,0.735890))
App.ActiveDocument.addObject("Part::Cylinder","C169")
App.ActiveDocument.C169.Radius=0.502165
App.ActiveDocument.C169.Height=20.00
App.ActiveDocument.C169.Angle=360.00 
App.ActiveDocument.C169.Placement=Base.Placement(Base.Vector(51.309027,152.013736,14.298136),Base.Rotation(0.084796,0.670963,0.000000,0.736626))
App.ActiveDocument.addObject("Part::Cylinder","C170")
App.ActiveDocument.C170.Radius=0.503790
App.ActiveDocument.C170.Height=20.00
App.ActiveDocument.C170.Angle=360.00 
App.ActiveDocument.C170.Placement=Base.Placement(Base.Vector(50.563317,146.929883,14.417217),Base.Rotation(0.079314,0.665452,0.000000,0.742215))
App.ActiveDocument.addObject("Part::Cylinder","C171")
App.ActiveDocument.C171.Radius=0.503536
App.ActiveDocument.C171.Height=20.00
App.ActiveDocument.C171.Angle=360.00 
App.ActiveDocument.C171.Placement=Base.Placement(Base.Vector(50.613261,139.259420,14.284660),Base.Rotation(-0.104654,0.661378,0.000000,0.742716))
App.ActiveDocument.addObject("Part::Cylinder","C172")
App.ActiveDocument.C172.Radius=0.502609
App.ActiveDocument.C172.Height=20.00
App.ActiveDocument.C172.Angle=360.00 
App.ActiveDocument.C172.Placement=Base.Placement(Base.Vector(51.420920,135.778900,14.226145),Base.Rotation(-0.008494,0.662611,0.000000,0.748916))
App.ActiveDocument.addObject("Part::Cylinder","C173")
App.ActiveDocument.C173.Radius=0.504286
App.ActiveDocument.C173.Height=20.00
App.ActiveDocument.C173.Angle=360.00 
App.ActiveDocument.C173.Placement=Base.Placement(Base.Vector(51.027714,131.948030,15.138424),Base.Rotation(0.063800,0.674205,0.000000,0.735783))
App.ActiveDocument.addObject("Part::Cylinder","C174")
App.ActiveDocument.C174.Radius=0.504459
App.ActiveDocument.C174.Height=20.00
App.ActiveDocument.C174.Angle=360.00 
App.ActiveDocument.C174.Placement=Base.Placement(Base.Vector(50.550428,128.383228,14.150968),Base.Rotation(0.140942,0.638473,0.000000,0.756629))
App.ActiveDocument.addObject("Part::Cylinder","C175")
App.ActiveDocument.C175.Radius=0.505287
App.ActiveDocument.C175.Height=20.00
App.ActiveDocument.C175.Angle=360.00 
App.ActiveDocument.C175.Placement=Base.Placement(Base.Vector(49.583640,124.654911,13.829605),Base.Rotation(0.191431,0.625427,0.000000,0.756436))
App.ActiveDocument.addObject("Part::Cylinder","C176")
App.ActiveDocument.C176.Radius=0.506660
App.ActiveDocument.C176.Height=20.00
App.ActiveDocument.C176.Angle=360.00 
App.ActiveDocument.C176.Placement=Base.Placement(Base.Vector(48.094068,120.217021,13.630789),Base.Rotation(0.211561,0.623746,0.000000,0.752451))
App.ActiveDocument.addObject("Part::Cylinder","C177")
App.ActiveDocument.C177.Radius=0.509731
App.ActiveDocument.C177.Height=20.00
App.ActiveDocument.C177.Angle=360.00 
App.ActiveDocument.C177.Placement=Base.Placement(Base.Vector(46.565475,115.629349,13.797296),Base.Rotation(0.209343,0.613207,0.000000,0.761677))
App.ActiveDocument.addObject("Part::Cylinder","C178")
App.ActiveDocument.C178.Radius=0.511409
App.ActiveDocument.C178.Height=20.00
App.ActiveDocument.C178.Angle=360.00 
App.ActiveDocument.C178.Placement=Base.Placement(Base.Vector(51.872388,119.053376,10.045954),Base.Rotation(0.561878,0.000036,0.000000,0.827220))
App.ActiveDocument.addObject("Part::Cylinder","C179")
App.ActiveDocument.C179.Radius=0.587168
App.ActiveDocument.C179.Height=20.00
App.ActiveDocument.C179.Angle=360.00 
App.ActiveDocument.C179.Placement=Base.Placement(Base.Vector(4.014506,206.270570,19.378196),Base.Rotation(-0.677211,0.086344,0.000000,0.730705))
App.ActiveDocument.addObject("Part::Cylinder","C180")
App.ActiveDocument.C180.Radius=0.581530
App.ActiveDocument.C180.Height=20.00
App.ActiveDocument.C180.Angle=360.00 
App.ActiveDocument.C180.Placement=Base.Placement(Base.Vector(8.035346,205.560026,19.673925),Base.Rotation(-0.665279,0.142409,0.000000,0.732887))
App.ActiveDocument.addObject("Part::Cylinder","C181")
App.ActiveDocument.C181.Radius=0.574520
App.ActiveDocument.C181.Height=20.00
App.ActiveDocument.C181.Angle=360.00 
App.ActiveDocument.C181.Placement=Base.Placement(Base.Vector(12.120051,204.496886,19.458488),Base.Rotation(-0.646588,0.205277,0.000000,0.734701))
App.ActiveDocument.addObject("Part::Cylinder","C182")
App.ActiveDocument.C182.Radius=0.568190
App.ActiveDocument.C182.Height=20.00
App.ActiveDocument.C182.Angle=360.00 
App.ActiveDocument.C182.Placement=Base.Placement(Base.Vector(16.570822,202.976222,19.458299),Base.Rotation(-0.635965,0.231461,0.000000,0.736189))
App.ActiveDocument.addObject("Part::Cylinder","C183")
App.ActiveDocument.C183.Radius=0.562563
App.ActiveDocument.C183.Height=20.00
App.ActiveDocument.C183.Angle=360.00 
App.ActiveDocument.C183.Placement=Base.Placement(Base.Vector(20.842520,201.219765,19.851020),Base.Rotation(-0.619132,0.273473,0.000000,0.736131))
App.ActiveDocument.addObject("Part::Cylinder","C184")
App.ActiveDocument.C184.Radius=0.554899
App.ActiveDocument.C184.Height=20.00
App.ActiveDocument.C184.Angle=360.00 
App.ActiveDocument.C184.Placement=Base.Placement(Base.Vector(24.860539,199.389903,19.173068),Base.Rotation(-0.602998,0.311473,0.000000,0.734423))
App.ActiveDocument.addObject("Part::Cylinder","C185")
App.ActiveDocument.C185.Radius=0.550550
App.ActiveDocument.C185.Height=20.00
App.ActiveDocument.C185.Angle=360.00 
App.ActiveDocument.C185.Placement=Base.Placement(Base.Vector(28.624303,197.237460,19.815527),Base.Rotation(-0.577561,0.354133,0.000000,0.735536))
App.ActiveDocument.addObject("Part::Cylinder","C186")
App.ActiveDocument.C186.Radius=0.544714
App.ActiveDocument.C186.Height=20.00
App.ActiveDocument.C186.Angle=360.00 
App.ActiveDocument.C186.Placement=Base.Placement(Base.Vector(32.319683,194.856981,19.651293),Base.Rotation(-0.552973,0.388176,0.000000,0.737252))
App.ActiveDocument.addObject("Part::Cylinder","C187")
App.ActiveDocument.C187.Radius=0.539235
App.ActiveDocument.C187.Height=20.00
App.ActiveDocument.C187.Angle=360.00 
App.ActiveDocument.C187.Placement=Base.Placement(Base.Vector(35.591725,192.355920,19.547261),Base.Rotation(-0.514976,0.436279,0.000000,0.737876))
App.ActiveDocument.addObject("Part::Cylinder","C188")
App.ActiveDocument.C188.Radius=0.533779
App.ActiveDocument.C188.Height=20.00
App.ActiveDocument.C188.Angle=360.00 
App.ActiveDocument.C188.Placement=Base.Placement(Base.Vector(38.441490,189.677977,19.237183),Base.Rotation(-0.469164,0.485826,0.000000,0.737468))
App.ActiveDocument.addObject("Part::Cylinder","C189")
App.ActiveDocument.C189.Radius=0.530064
App.ActiveDocument.C189.Height=20.00
App.ActiveDocument.C189.Angle=360.00 
App.ActiveDocument.C189.Placement=Base.Placement(Base.Vector(40.808308,186.857472,19.422037),Base.Rotation(-0.406663,0.538105,0.000000,0.738288))
App.ActiveDocument.addObject("Part::Cylinder","C190")
App.ActiveDocument.C190.Radius=0.526140
App.ActiveDocument.C190.Height=20.00
App.ActiveDocument.C190.Angle=360.00 
App.ActiveDocument.C190.Placement=Base.Placement(Base.Vector(43.192507,183.403620,19.286508),Base.Rotation(-0.356173,0.569045,0.000000,0.741167))
App.ActiveDocument.addObject("Part::Cylinder","C191")
App.ActiveDocument.C191.Radius=0.522911
App.ActiveDocument.C191.Height=20.00
App.ActiveDocument.C191.Angle=360.00 
App.ActiveDocument.C191.Placement=Base.Placement(Base.Vector(45.299885,179.813068,19.154610),Base.Rotation(-0.316776,0.586701,0.000000,0.745275))
App.ActiveDocument.addObject("Part::Cylinder","C192")
App.ActiveDocument.C192.Radius=0.519536
App.ActiveDocument.C192.Height=20.00
App.ActiveDocument.C192.Angle=360.00 
App.ActiveDocument.C192.Placement=Base.Placement(Base.Vector(46.893309,176.451675,18.745332),Base.Rotation(-0.241452,0.616089,0.000000,0.749756))
App.ActiveDocument.addObject("Part::Cylinder","C193")
App.ActiveDocument.C193.Radius=0.517306
App.ActiveDocument.C193.Height=20.00
App.ActiveDocument.C193.Angle=360.00 
App.ActiveDocument.C193.Placement=Base.Placement(Base.Vector(48.158236,172.710118,18.649625),Base.Rotation(-0.184495,0.634736,0.000000,0.750381))
App.ActiveDocument.addObject("Part::Cylinder","C194")
App.ActiveDocument.C194.Radius=0.516152
App.ActiveDocument.C194.Height=20.00
App.ActiveDocument.C194.Angle=360.00 
App.ActiveDocument.C194.Placement=Base.Placement(Base.Vector(49.189875,168.566968,18.901622),Base.Rotation(-0.152744,0.645913,0.000000,0.747974))
App.ActiveDocument.addObject("Part::Cylinder","C195")
App.ActiveDocument.C195.Radius=0.514569
App.ActiveDocument.C195.Height=20.00
App.ActiveDocument.C195.Angle=360.00 
App.ActiveDocument.C195.Placement=Base.Placement(Base.Vector(50.145042,164.039281,18.985230),Base.Rotation(-0.127802,0.657616,0.000000,0.742434))
App.ActiveDocument.addObject("Part::Cylinder","C196")
App.ActiveDocument.C196.Radius=0.513875
App.ActiveDocument.C196.Height=20.00
App.ActiveDocument.C196.Angle=360.00 
App.ActiveDocument.C196.Placement=Base.Placement(Base.Vector(50.797363,159.933541,19.161291),Base.Rotation(-0.077870,0.666396,0.000000,0.741521))
App.ActiveDocument.addObject("Part::Cylinder","C197")
App.ActiveDocument.C197.Radius=0.512927
App.ActiveDocument.C197.Height=20.00
App.ActiveDocument.C197.Angle=360.00 
App.ActiveDocument.C197.Placement=Base.Placement(Base.Vector(51.092574,156.296898,18.558550),Base.Rotation(0.015764,0.657082,0.000000,0.753654))
App.ActiveDocument.addObject("Part::Cylinder","C198")
App.ActiveDocument.C198.Radius=0.513566
App.ActiveDocument.C198.Height=20.00
App.ActiveDocument.C198.Angle=360.00 
App.ActiveDocument.C198.Placement=Base.Placement(Base.Vector(50.843199,152.419726,18.205418),Base.Rotation(0.091325,0.635474,0.000000,0.766702))
App.ActiveDocument.addObject("Part::Cylinder","C199")
App.ActiveDocument.C199.Radius=0.515593
App.ActiveDocument.C199.Height=20.00
App.ActiveDocument.C199.Angle=360.00 
App.ActiveDocument.C199.Placement=Base.Placement(Base.Vector(50.064355,147.685922,18.312784),Base.Rotation(0.100801,0.622349,0.000000,0.776222))
App.ActiveDocument.addObject("Part::Cylinder","C200")
App.ActiveDocument.C200.Radius=0.515473
App.ActiveDocument.C200.Height=20.00
App.ActiveDocument.C200.Angle=360.00 
App.ActiveDocument.C200.Placement=Base.Placement(Base.Vector(49.830262,139.739452,17.886443),Base.Rotation(-0.093572,0.614930,0.000000,0.783011))
App.ActiveDocument.addObject("Part::Cylinder","C201")
App.ActiveDocument.C201.Radius=0.514226
App.ActiveDocument.C201.Height=20.00
App.ActiveDocument.C201.Angle=360.00 
App.ActiveDocument.C201.Placement=Base.Placement(Base.Vector(50.707153,135.385613,17.739998),Base.Rotation(-0.072937,0.612932,0.000000,0.786762))
App.ActiveDocument.addObject("Part::Cylinder","C202")
App.ActiveDocument.C202.Radius=0.516734
App.ActiveDocument.C202.Height=20.00
App.ActiveDocument.C202.Angle=360.00 
App.ActiveDocument.C202.Placement=Base.Placement(Base.Vector(50.489828,132.758459,17.639124),Base.Rotation(0.070307,0.573675,0.000000,0.816060))
App.ActiveDocument.addObject("Part::Cylinder","C203")
App.ActiveDocument.C203.Radius=0.516422
App.ActiveDocument.C203.Height=20.00
App.ActiveDocument.C203.Angle=360.00 
App.ActiveDocument.C203.Placement=Base.Placement(Base.Vector(49.938262,128.902588,17.325173),Base.Rotation(0.133843,0.572086,0.000000,0.809199))
App.ActiveDocument.addObject("Part::Cylinder","C204")
App.ActiveDocument.C204.Radius=0.517249
App.ActiveDocument.C204.Height=20.00
App.ActiveDocument.C204.Angle=360.00 
App.ActiveDocument.C204.Placement=Base.Placement(Base.Vector(48.944380,125.104382,17.068829),Base.Rotation(0.177594,0.563117,0.000000,0.807069))
App.ActiveDocument.addObject("Part::Cylinder","C205")
App.ActiveDocument.C205.Radius=0.518196
App.ActiveDocument.C205.Height=20.00
App.ActiveDocument.C205.Angle=360.00 
App.ActiveDocument.C205.Placement=Base.Placement(Base.Vector(47.498149,120.831896,16.826058),Base.Rotation(0.199359,0.565637,0.000000,0.800194))
App.ActiveDocument.addObject("Part::Cylinder","C206")
App.ActiveDocument.C206.Radius=0.521591
App.ActiveDocument.C206.Height=20.00
App.ActiveDocument.C206.Angle=360.00 
App.ActiveDocument.C206.Placement=Base.Placement(Base.Vector(46.425908,117.454630,16.576901),Base.Rotation(0.287294,0.497340,0.000000,0.818606))
App.ActiveDocument.addObject("Part::Cylinder","C207")
App.ActiveDocument.C207.Radius=0.598175
App.ActiveDocument.C207.Height=20.00
App.ActiveDocument.C207.Angle=360.00 
App.ActiveDocument.C207.Placement=Base.Placement(Base.Vector(4.154859,205.852284,24.182628),Base.Rotation(-0.665360,0.088704,0.000000,0.741234))
App.ActiveDocument.addObject("Part::Cylinder","C208")
App.ActiveDocument.C208.Radius=0.592301
App.ActiveDocument.C208.Height=20.00
App.ActiveDocument.C208.Angle=360.00 
App.ActiveDocument.C208.Placement=Base.Placement(Base.Vector(8.103430,205.127690,24.350873),Base.Rotation(-0.654825,0.142731,0.000000,0.742181))
App.ActiveDocument.addObject("Part::Cylinder","C209")
App.ActiveDocument.C209.Radius=0.585313
App.ActiveDocument.C209.Height=20.00
App.ActiveDocument.C209.Angle=360.00 
App.ActiveDocument.C209.Placement=Base.Placement(Base.Vector(11.955290,204.114847,24.030827),Base.Rotation(-0.637526,0.204284,0.000000,0.742852))
App.ActiveDocument.addObject("Part::Cylinder","C210")
App.ActiveDocument.C210.Radius=0.579581
App.ActiveDocument.C210.Height=20.00
App.ActiveDocument.C210.Angle=360.00 
App.ActiveDocument.C210.Placement=Base.Placement(Base.Vector(16.252497,202.606200,24.216379),Base.Rotation(-0.628132,0.228976,0.000000,0.743653))
App.ActiveDocument.addObject("Part::Cylinder","C211")
App.ActiveDocument.C211.Radius=0.574174
App.ActiveDocument.C211.Height=20.00
App.ActiveDocument.C211.Angle=360.00 
App.ActiveDocument.C211.Placement=Base.Placement(Base.Vector(20.470141,200.885496,24.604008),Base.Rotation(-0.612674,0.265187,0.000000,0.744518))
App.ActiveDocument.addObject("Part::Cylinder","C212")
App.ActiveDocument.C212.Radius=0.566334
App.ActiveDocument.C212.Height=20.00
App.ActiveDocument.C212.Angle=360.00 
App.ActiveDocument.C212.Placement=Base.Placement(Base.Vector(24.523283,199.084154,23.928851),Base.Rotation(-0.597674,0.305278,0.000000,0.741344))
App.ActiveDocument.addObject("Part::Cylinder","C213")
App.ActiveDocument.C213.Radius=0.561702
App.ActiveDocument.C213.Height=20.00
App.ActiveDocument.C213.Angle=360.00 
App.ActiveDocument.C213.Placement=Base.Placement(Base.Vector(28.254876,196.966026,24.460529),Base.Rotation(-0.570943,0.350975,0.000000,0.742186))
App.ActiveDocument.addObject("Part::Cylinder","C214")
App.ActiveDocument.C214.Radius=0.555887
App.ActiveDocument.C214.Height=20.00
App.ActiveDocument.C214.Angle=360.00 
App.ActiveDocument.C214.Placement=Base.Placement(Base.Vector(31.999981,194.527561,24.351851),Base.Rotation(-0.544911,0.386746,0.000000,0.743976))
App.ActiveDocument.addObject("Part::Cylinder","C215")
App.ActiveDocument.C215.Radius=0.550591
App.ActiveDocument.C215.Height=20.00
App.ActiveDocument.C215.Angle=360.00 
App.ActiveDocument.C215.Placement=Base.Placement(Base.Vector(35.271528,192.015516,24.311846),Base.Rotation(-0.509549,0.431650,0.000000,0.744337))
App.ActiveDocument.addObject("Part::Cylinder","C216")
App.ActiveDocument.C216.Radius=0.544839
App.ActiveDocument.C216.Height=20.00
App.ActiveDocument.C216.Angle=360.00 
App.ActiveDocument.C216.Placement=Base.Placement(Base.Vector(38.147907,189.337350,23.912114),Base.Rotation(-0.462437,0.482980,0.000000,0.743561))
App.ActiveDocument.addObject("Part::Cylinder","C217")
App.ActiveDocument.C217.Radius=0.541551
App.ActiveDocument.C217.Height=20.00
App.ActiveDocument.C217.Angle=360.00 
App.ActiveDocument.C217.Placement=Base.Placement(Base.Vector(40.491102,186.475937,24.237369),Base.Rotation(-0.398712,0.533857,0.000000,0.745671))
App.ActiveDocument.addObject("Part::Cylinder","C218")
App.ActiveDocument.C218.Radius=0.537282
App.ActiveDocument.C218.Height=20.00
App.ActiveDocument.C218.Angle=360.00 
App.ActiveDocument.C218.Placement=Base.Placement(Base.Vector(42.754973,183.150128,23.905351),Base.Rotation(-0.346662,0.566241,0.000000,0.747795))
App.ActiveDocument.addObject("Part::Cylinder","C219")
App.ActiveDocument.C219.Radius=0.534335
App.ActiveDocument.C219.Height=20.00
App.ActiveDocument.C219.Angle=360.00 
App.ActiveDocument.C219.Placement=Base.Placement(Base.Vector(44.832583,179.424870,23.886349),Base.Rotation(-0.291325,0.589000,0.000000,0.753796))
App.ActiveDocument.addObject("Part::Cylinder","C220")
App.ActiveDocument.C220.Radius=0.531076
App.ActiveDocument.C220.Height=20.00
App.ActiveDocument.C220.Angle=360.00 
App.ActiveDocument.C220.Placement=Base.Placement(Base.Vector(46.462376,175.755478,23.484961),Base.Rotation(-0.223477,0.611925,0.000000,0.758687))
App.ActiveDocument.addObject("Part::Cylinder","C221")
App.ActiveDocument.C221.Radius=0.529034
App.ActiveDocument.C221.Height=20.00
App.ActiveDocument.C221.Angle=360.00 
App.ActiveDocument.C221.Placement=Base.Placement(Base.Vector(47.695943,171.916681,23.419637),Base.Rotation(-0.180990,0.625524,0.000000,0.758922))
App.ActiveDocument.addObject("Part::Cylinder","C222")
App.ActiveDocument.C222.Radius=0.527503
App.ActiveDocument.C222.Height=20.00
App.ActiveDocument.C222.Angle=360.00 
App.ActiveDocument.C222.Placement=Base.Placement(Base.Vector(48.844052,167.434786,23.598609),Base.Rotation(-0.153816,0.636887,0.000000,0.755457))
App.ActiveDocument.addObject("Part::Cylinder","C223")
App.ActiveDocument.C223.Radius=0.525750
App.ActiveDocument.C223.Height=20.00
App.ActiveDocument.C223.Angle=360.00 
App.ActiveDocument.C223.Placement=Base.Placement(Base.Vector(49.833526,163.030843,23.397758),Base.Rotation(-0.114028,0.642485,0.000000,0.757767))
App.ActiveDocument.addObject("Part::Cylinder","C224")
App.ActiveDocument.C224.Radius=0.525461
App.ActiveDocument.C224.Height=20.00
App.ActiveDocument.C224.Angle=360.00 
App.ActiveDocument.C224.Placement=Base.Placement(Base.Vector(50.345456,159.381929,23.106670),Base.Rotation(-0.025602,0.632482,0.000000,0.774152))
App.ActiveDocument.addObject("Part::Cylinder","C225")
App.ActiveDocument.C225.Radius=0.524743
App.ActiveDocument.C225.Height=20.00
App.ActiveDocument.C225.Angle=360.00 
App.ActiveDocument.C225.Placement=Base.Placement(Base.Vector(50.395159,155.933020,22.361681),Base.Rotation(0.064971,0.614738,0.000000,0.786051))
App.ActiveDocument.addObject("Part::Cylinder","C226")
App.ActiveDocument.C226.Radius=0.526389
App.ActiveDocument.C226.Height=20.00
App.ActiveDocument.C226.Angle=360.00 
App.ActiveDocument.C226.Placement=Base.Placement(Base.Vector(49.736855,151.789350,22.111644),Base.Rotation(0.120803,0.587679,0.000000,0.800025))
App.ActiveDocument.addObject("Part::Cylinder","C227")
App.ActiveDocument.C227.Radius=0.528384
App.ActiveDocument.C227.Height=20.00
App.ActiveDocument.C227.Angle=360.00 
App.ActiveDocument.C227.Placement=Base.Placement(Base.Vector(48.723460,146.717898,22.062351),Base.Rotation(0.109187,0.576824,0.000000,0.809538))
App.ActiveDocument.addObject("Part::Cylinder","C228")
App.ActiveDocument.C228.Radius=0.527956
App.ActiveDocument.C228.Height=20.00
App.ActiveDocument.C228.Angle=360.00 
App.ActiveDocument.C228.Placement=Base.Placement(Base.Vector(48.659318,138.854074,21.453320),Base.Rotation(-0.075401,0.566858,0.000000,0.820358))
App.ActiveDocument.addObject("Part::Cylinder","C229")
App.ActiveDocument.C229.Radius=0.527542
App.ActiveDocument.C229.Height=20.00
App.ActiveDocument.C229.Angle=360.00 
App.ActiveDocument.C229.Placement=Base.Placement(Base.Vector(49.161990,135.675787,21.650069),Base.Rotation(0.015270,0.572886,0.000000,0.819493))
App.ActiveDocument.addObject("Part::Cylinder","C230")
App.ActiveDocument.C230.Radius=0.529559
App.ActiveDocument.C230.Height=20.00
App.ActiveDocument.C230.Angle=360.00 
App.ActiveDocument.C230.Placement=Base.Placement(Base.Vector(48.588955,132.018854,22.142647),Base.Rotation(0.094829,0.565115,0.000000,0.819544))
App.ActiveDocument.addObject("Part::Cylinder","C231")
App.ActiveDocument.C231.Radius=0.529386
App.ActiveDocument.C231.Height=20.00
App.ActiveDocument.C231.Angle=360.00 
App.ActiveDocument.C231.Placement=Base.Placement(Base.Vector(48.039299,128.259814,21.313264),Base.Rotation(0.150867,0.541935,0.000000,0.826768))
App.ActiveDocument.addObject("Part::Cylinder","C232")
App.ActiveDocument.C232.Radius=0.530725
App.ActiveDocument.C232.Height=20.00
App.ActiveDocument.C232.Angle=360.00 
App.ActiveDocument.C232.Placement=Base.Placement(Base.Vector(46.866466,124.256744,20.881635),Base.Rotation(0.190059,0.521721,0.000000,0.831676))
App.ActiveDocument.addObject("Part::Cylinder","C233")
App.ActiveDocument.C233.Radius=0.530998
App.ActiveDocument.C233.Height=20.00
App.ActiveDocument.C233.Angle=360.00 
App.ActiveDocument.C233.Placement=Base.Placement(Base.Vector(45.844416,120.124573,19.802256),Base.Rotation(0.216813,0.493032,0.000000,0.842562))
App.ActiveDocument.addObject("Part::Cylinder","C234")
App.ActiveDocument.C234.Radius=0.533289
App.ActiveDocument.C234.Height=20.00
App.ActiveDocument.C234.Angle=360.00 
App.ActiveDocument.C234.Placement=Base.Placement(Base.Vector(50.451146,122.377665,18.707490),Base.Rotation(0.540297,0.005695,0.000000,0.841455))
App.ActiveDocument.addObject("Part::Cylinder","C235")
App.ActiveDocument.C235.Radius=0.608906
App.ActiveDocument.C235.Height=20.00
App.ActiveDocument.C235.Angle=360.00 
App.ActiveDocument.C235.Placement=Base.Placement(Base.Vector(4.030045,205.344610,28.659396),Base.Rotation(-0.652995,0.088175,0.000000,0.752212))
App.ActiveDocument.addObject("Part::Cylinder","C236")
App.ActiveDocument.C236.Radius=0.603381
App.ActiveDocument.C236.Height=20.00
App.ActiveDocument.C236.Angle=360.00 
App.ActiveDocument.C236.Placement=Base.Placement(Base.Vector(8.067264,204.558756,29.048587),Base.Rotation(-0.640953,0.144615,0.000000,0.753834))
App.ActiveDocument.addObject("Part::Cylinder","C237")
App.ActiveDocument.C237.Radius=0.595870
App.ActiveDocument.C237.Height=20.00
App.ActiveDocument.C237.Angle=360.00 
App.ActiveDocument.C237.Placement=Base.Placement(Base.Vector(12.134300,203.480000,28.662919),Base.Rotation(-0.624762,0.205860,0.000000,0.753189))
App.ActiveDocument.addObject("Part::Cylinder","C238")
App.ActiveDocument.C238.Radius=0.590024
App.ActiveDocument.C238.Height=20.00
App.ActiveDocument.C238.Angle=360.00 
App.ActiveDocument.C238.Placement=Base.Placement(Base.Vector(16.604997,201.866525,28.882548),Base.Rotation(-0.614569,0.229990,0.000000,0.754592))
App.ActiveDocument.addObject("Part::Cylinder","C239")
App.ActiveDocument.C239.Radius=0.584798
App.ActiveDocument.C239.Height=20.00
App.ActiveDocument.C239.Angle=360.00 
App.ActiveDocument.C239.Placement=Base.Placement(Base.Vector(20.843395,200.079548,29.345349),Base.Rotation(-0.599576,0.263890,0.000000,0.755560))
App.ActiveDocument.addObject("Part::Cylinder","C240")
App.ActiveDocument.C240.Radius=0.576870
App.ActiveDocument.C240.Height=20.00
App.ActiveDocument.C240.Angle=360.00 
App.ActiveDocument.C240.Placement=Base.Placement(Base.Vector(24.758906,198.364053,28.527507),Base.Rotation(-0.585884,0.301088,0.000000,0.752387))
App.ActiveDocument.addObject("Part::Cylinder","C241")
App.ActiveDocument.C241.Radius=0.571957
App.ActiveDocument.C241.Height=20.00
App.ActiveDocument.C241.Angle=360.00 
App.ActiveDocument.C241.Placement=Base.Placement(Base.Vector(28.431390,196.221116,28.958887),Base.Rotation(-0.555746,0.352362,0.000000,0.752985))
App.ActiveDocument.addObject("Part::Cylinder","C242")
App.ActiveDocument.C242.Radius=0.565908
App.ActiveDocument.C242.Height=20.00
App.ActiveDocument.C242.Angle=360.00 
App.ActiveDocument.C242.Placement=Base.Placement(Base.Vector(32.091630,193.795928,28.715329),Base.Rotation(-0.533643,0.385083,0.000000,0.752951))
App.ActiveDocument.addObject("Part::Cylinder","C243")
App.ActiveDocument.C243.Radius=0.560773
App.ActiveDocument.C243.Height=20.00
App.ActiveDocument.C243.Angle=360.00 
App.ActiveDocument.C243.Placement=Base.Placement(Base.Vector(35.341272,191.199973,28.790956),Base.Rotation(-0.489095,0.438103,0.000000,0.754223))
App.ActiveDocument.addObject("Part::Cylinder","C244")
App.ActiveDocument.C244.Radius=0.555591
App.ActiveDocument.C244.Height=20.00
App.ActiveDocument.C244.Angle=360.00 
App.ActiveDocument.C244.Placement=Base.Placement(Base.Vector(38.149869,188.496166,28.517235),Base.Rotation(-0.442649,0.483399,0.000000,0.755240))
App.ActiveDocument.addObject("Part::Cylinder","C245")
App.ActiveDocument.C245.Radius=0.552550
App.ActiveDocument.C245.Height=20.00
App.ActiveDocument.C245.Angle=360.00 
App.ActiveDocument.C245.Placement=Base.Placement(Base.Vector(40.360413,185.625453,28.833857),Base.Rotation(-0.376827,0.531823,0.000000,0.758397))
App.ActiveDocument.addObject("Part::Cylinder","C246")
App.ActiveDocument.C246.Radius=0.548449
App.ActiveDocument.C246.Height=20.00
App.ActiveDocument.C246.Angle=360.00 
App.ActiveDocument.C246.Placement=Base.Placement(Base.Vector(42.541229,182.255753,28.495181),Base.Rotation(-0.320040,0.563343,0.000000,0.761721))
App.ActiveDocument.addObject("Part::Cylinder","C247")
App.ActiveDocument.C247.Radius=0.545613
App.ActiveDocument.C247.Height=20.00
App.ActiveDocument.C247.Angle=360.00 
App.ActiveDocument.C247.Placement=Base.Placement(Base.Vector(44.410646,178.635572,28.448510),Base.Rotation(-0.268748,0.584927,0.000000,0.765268))
App.ActiveDocument.addObject("Part::Cylinder","C248")
App.ActiveDocument.C248.Radius=0.542547
App.ActiveDocument.C248.Height=20.00
App.ActiveDocument.C248.Angle=360.00 
App.ActiveDocument.C248.Placement=Base.Placement(Base.Vector(45.888135,175.043709,28.080155),Base.Rotation(-0.208321,0.605858,0.000000,0.767814))
App.ActiveDocument.addObject("Part::Cylinder","C249")
App.ActiveDocument.C249.Radius=0.540894
App.ActiveDocument.C249.Height=20.00
App.ActiveDocument.C249.Angle=360.00 
App.ActiveDocument.C249.Placement=Base.Placement(Base.Vector(47.161086,170.828199,28.192410),Base.Rotation(-0.174308,0.616407,0.000000,0.767893))
App.ActiveDocument.addObject("Part::Cylinder","C250")
App.ActiveDocument.C250.Radius=0.539650
App.ActiveDocument.C250.Height=20.00
App.ActiveDocument.C250.Angle=360.00 
App.ActiveDocument.C250.Placement=Base.Placement(Base.Vector(48.247526,166.504737,28.242941),Base.Rotation(-0.138623,0.621054,0.000000,0.771411))
App.ActiveDocument.addObject("Part::Cylinder","C251")
App.ActiveDocument.C251.Radius=0.536996
App.ActiveDocument.C251.Height=20.00
App.ActiveDocument.C251.Angle=360.00 
App.ActiveDocument.C251.Placement=Base.Placement(Base.Vector(49.119933,162.546342,27.379480),Base.Rotation(-0.076831,0.621690,0.000000,0.779486))
App.ActiveDocument.addObject("Part::Cylinder","C252")
App.ActiveDocument.C252.Radius=0.537610
App.ActiveDocument.C252.Height=20.00
App.ActiveDocument.C252.Angle=360.00 
App.ActiveDocument.C252.Placement=Base.Placement(Base.Vector(49.256908,159.128696,27.596555),Base.Rotation(0.018355,0.619590,0.000000,0.784711))
App.ActiveDocument.addObject("Part::Cylinder","C253")
App.ActiveDocument.C253.Radius=0.537248
App.ActiveDocument.C253.Height=20.00
App.ActiveDocument.C253.Angle=360.00 
App.ActiveDocument.C253.Placement=Base.Placement(Base.Vector(49.011487,155.309023,27.134791),Base.Rotation(0.095090,0.609588,0.000000,0.786995))
App.ActiveDocument.addObject("Part::Cylinder","C254")
App.ActiveDocument.C254.Radius=0.539366
App.ActiveDocument.C254.Height=20.00
App.ActiveDocument.C254.Angle=360.00 
App.ActiveDocument.C254.Placement=Base.Placement(Base.Vector(48.079736,150.911594,27.603295),Base.Rotation(0.129107,0.607859,0.000000,0.783478))
App.ActiveDocument.addObject("Part::Cylinder","C255")
App.ActiveDocument.C255.Radius=0.541037
App.ActiveDocument.C255.Height=20.00
App.ActiveDocument.C255.Angle=360.00 
App.ActiveDocument.C255.Placement=Base.Placement(Base.Vector(46.937319,145.255847,26.999522),Base.Rotation(0.084951,0.589037,0.000000,0.803629))
App.ActiveDocument.addObject("Part::Cylinder","C256")
App.ActiveDocument.C256.Radius=0.541185
App.ActiveDocument.C256.Height=20.00
App.ActiveDocument.C256.Angle=360.00 
App.ActiveDocument.C256.Placement=Base.Placement(Base.Vector(47.150845,137.435620,26.657229),Base.Rotation(-0.093066,0.568965,0.000000,0.817078))
App.ActiveDocument.addObject("Part::Cylinder","C257")
App.ActiveDocument.C257.Radius=0.540953
App.ActiveDocument.C257.Height=20.00
App.ActiveDocument.C257.Angle=360.00 
App.ActiveDocument.C257.Placement=Base.Placement(Base.Vector(47.457749,134.932111,26.285963),Base.Rotation(0.047606,0.556402,0.000000,0.829549))
App.ActiveDocument.addObject("Part::Cylinder","C258")
App.ActiveDocument.C258.Radius=0.542712
App.ActiveDocument.C258.Height=20.00
App.ActiveDocument.C258.Angle=360.00 
App.ActiveDocument.C258.Placement=Base.Placement(Base.Vector(46.830368,131.370062,26.316302),Base.Rotation(0.120575,0.535087,0.000000,0.836148))
App.ActiveDocument.addObject("Part::Cylinder","C259")
App.ActiveDocument.C259.Radius=0.542456
App.ActiveDocument.C259.Height=20.00
App.ActiveDocument.C259.Angle=360.00 
App.ActiveDocument.C259.Placement=Base.Placement(Base.Vector(46.131069,127.547835,25.403863),Base.Rotation(0.173578,0.511921,0.000000,0.841313))
App.ActiveDocument.addObject("Part::Cylinder","C260")
App.ActiveDocument.C260.Radius=0.543632
App.ActiveDocument.C260.Height=20.00
App.ActiveDocument.C260.Angle=360.00 
App.ActiveDocument.C260.Placement=Base.Placement(Base.Vector(44.740362,123.252447,24.879108),Base.Rotation(0.196065,0.498551,0.000000,0.844397))
App.ActiveDocument.addObject("Part::Cylinder","C261")
App.ActiveDocument.C261.Radius=0.544636
App.ActiveDocument.C261.Height=20.00
App.ActiveDocument.C261.Angle=360.00 
App.ActiveDocument.C261.Placement=Base.Placement(Base.Vector(48.064887,123.872849,23.225941),Base.Rotation(0.463979,0.172131,0.000000,0.868962))
App.ActiveDocument.addObject("Part::Cylinder","C262")
App.ActiveDocument.C262.Radius=0.619633
App.ActiveDocument.C262.Height=20.00
App.ActiveDocument.C262.Angle=360.00 
App.ActiveDocument.C262.Placement=Base.Placement(Base.Vector(3.957999,204.670431,33.038088),Base.Rotation(-0.636559,0.085007,0.000000,0.766529))
App.ActiveDocument.addObject("Part::Cylinder","C263")
App.ActiveDocument.C263.Radius=0.614262
App.ActiveDocument.C263.Height=20.00
App.ActiveDocument.C263.Angle=360.00 
App.ActiveDocument.C263.Placement=Base.Placement(Base.Vector(7.956013,203.860090,33.463534),Base.Rotation(-0.624316,0.140370,0.000000,0.768457))
App.ActiveDocument.addObject("Part::Cylinder","C264")
App.ActiveDocument.C264.Radius=0.607463
App.ActiveDocument.C264.Height=20.00
App.ActiveDocument.C264.Angle=360.00 
App.ActiveDocument.C264.Placement=Base.Placement(Base.Vector(11.789413,202.834158,33.289025),Base.Rotation(-0.609375,0.200984,0.000000,0.766986))
App.ActiveDocument.addObject("Part::Cylinder","C265")
App.ActiveDocument.C265.Radius=0.601497
App.ActiveDocument.C265.Height=20.00
App.ActiveDocument.C265.Angle=360.00 
App.ActiveDocument.C265.Placement=Base.Placement(Base.Vector(16.119039,201.290167,33.369998),Base.Rotation(-0.600616,0.223065,0.000000,0.767791))
App.ActiveDocument.addObject("Part::Cylinder","C266")
App.ActiveDocument.C266.Radius=0.596042
App.ActiveDocument.C266.Height=20.00
App.ActiveDocument.C266.Angle=360.00 
App.ActiveDocument.C266.Placement=Base.Placement(Base.Vector(20.291064,199.557295,33.698426),Base.Rotation(-0.587909,0.254634,0.000000,0.767805))
App.ActiveDocument.addObject("Part::Cylinder","C267")
App.ActiveDocument.C267.Radius=0.588935
App.ActiveDocument.C267.Height=20.00
App.ActiveDocument.C267.Angle=360.00 
App.ActiveDocument.C267.Placement=Base.Placement(Base.Vector(24.141981,197.869576,33.132377),Base.Rotation(-0.571872,0.290079,0.000000,0.767344))
App.ActiveDocument.addObject("Part::Cylinder","C268")
App.ActiveDocument.C268.Radius=0.583884
App.ActiveDocument.C268.Height=20.00
App.ActiveDocument.C268.Angle=360.00 
App.ActiveDocument.C268.Placement=Base.Placement(Base.Vector(27.775935,195.784121,33.357315),Base.Rotation(-0.542462,0.334770,0.000000,0.770496))
App.ActiveDocument.addObject("Part::Cylinder","C269")
App.ActiveDocument.C269.Radius=0.577283
App.ActiveDocument.C269.Height=20.00
App.ActiveDocument.C269.Angle=360.00 
App.ActiveDocument.C269.Placement=Base.Placement(Base.Vector(31.381709,193.444910,32.947580),Base.Rotation(-0.515756,0.376647,0.000000,0.769501))
App.ActiveDocument.addObject("Part::Cylinder","C270")
App.ActiveDocument.C270.Radius=0.572579
App.ActiveDocument.C270.Height=20.00
App.ActiveDocument.C270.Angle=360.00 
App.ActiveDocument.C270.Placement=Base.Placement(Base.Vector(34.731432,190.746399,33.126691),Base.Rotation(-0.477768,0.417795,0.000000,0.772777))
App.ActiveDocument.addObject("Part::Cylinder","C271")
App.ActiveDocument.C271.Radius=0.567114
App.ActiveDocument.C271.Height=20.00
App.ActiveDocument.C271.Angle=360.00 
App.ActiveDocument.C271.Placement=Base.Placement(Base.Vector(37.515068,188.092418,32.885693),Base.Rotation(-0.418728,0.477443,0.000000,0.772473))
App.ActiveDocument.addObject("Part::Cylinder","C272")
App.ActiveDocument.C272.Radius=0.563793
App.ActiveDocument.C272.Height=20.00
App.ActiveDocument.C272.Angle=360.00 
App.ActiveDocument.C272.Placement=Base.Placement(Base.Vector(39.928668,184.875122,33.211041),Base.Rotation(-0.356529,0.522898,0.000000,0.774251))
App.ActiveDocument.addObject("Part::Cylinder","C273")
App.ActiveDocument.C273.Radius=0.560179
App.ActiveDocument.C273.Height=20.00
App.ActiveDocument.C273.Angle=360.00 
App.ActiveDocument.C273.Placement=Base.Placement(Base.Vector(42.037345,181.418803,33.121772),Base.Rotation(-0.306567,0.553452,0.000000,0.774408))
App.ActiveDocument.addObject("Part::Cylinder","C274")
App.ActiveDocument.C274.Radius=0.557061
App.ActiveDocument.C274.Height=20.00
App.ActiveDocument.C274.Angle=360.00 
App.ActiveDocument.C274.Placement=Base.Placement(Base.Vector(43.809854,177.811500,33.081396),Base.Rotation(-0.247429,0.583686,0.000000,0.773362))
App.ActiveDocument.addObject("Part::Cylinder","C275")
App.ActiveDocument.C275.Radius=0.554304
App.ActiveDocument.C275.Height=20.00
App.ActiveDocument.C275.Angle=360.00 
App.ActiveDocument.C275.Placement=Base.Placement(Base.Vector(45.273911,173.977262,32.948207),Base.Rotation(-0.202993,0.603450,0.000000,0.771131))
App.ActiveDocument.addObject("Part::Cylinder","C276")
App.ActiveDocument.C276.Radius=0.552846
App.ActiveDocument.C276.Height=20.00
App.ActiveDocument.C276.Angle=360.00 
App.ActiveDocument.C276.Placement=Base.Placement(Base.Vector(46.489719,169.740389,33.163898),Base.Rotation(-0.164071,0.616463,0.000000,0.770100))
App.ActiveDocument.addObject("Part::Cylinder","C277")
App.ActiveDocument.C277.Radius=0.551401
App.ActiveDocument.C277.Height=20.00
App.ActiveDocument.C277.Angle=360.00 
App.ActiveDocument.C277.Placement=Base.Placement(Base.Vector(47.479638,165.260254,33.259207),Base.Rotation(-0.119370,0.628791,0.000000,0.768357))
App.ActiveDocument.addObject("Part::Cylinder","C278")
App.ActiveDocument.C278.Radius=0.549346
App.ActiveDocument.C278.Height=20.00
App.ActiveDocument.C278.Angle=360.00 
App.ActiveDocument.C278.Placement=Base.Placement(Base.Vector(48.098932,161.529317,32.925468),Base.Rotation(-0.053009,0.642846,0.000000,0.764159))
App.ActiveDocument.addObject("Part::Cylinder","C279")
App.ActiveDocument.C279.Radius=0.549874
App.ActiveDocument.C279.Height=20.00
App.ActiveDocument.C279.Angle=360.00 
App.ActiveDocument.C279.Placement=Base.Placement(Base.Vector(48.127835,158.229445,32.976761),Base.Rotation(0.066216,0.634770,0.000000,0.769859))
App.ActiveDocument.addObject("Part::Cylinder","C280")
App.ActiveDocument.C280.Radius=0.550040
App.ActiveDocument.C280.Height=20.00
App.ActiveDocument.C280.Angle=360.00 
App.ActiveDocument.C280.Placement=Base.Placement(Base.Vector(47.652192,154.437048,32.475448),Base.Rotation(0.116274,0.619628,0.000000,0.776235))
App.ActiveDocument.addObject("Part::Cylinder","C281")
App.ActiveDocument.C281.Radius=0.552229
App.ActiveDocument.C281.Height=20.00
App.ActiveDocument.C281.Angle=360.00 
App.ActiveDocument.C281.Placement=Base.Placement(Base.Vector(46.757609,150.463518,32.593323),Base.Rotation(0.166942,0.599771,0.000000,0.782563))
App.ActiveDocument.addObject("Part::Cylinder","C282")
App.ActiveDocument.C282.Radius=0.553947
App.ActiveDocument.C282.Height=20.00
App.ActiveDocument.C282.Angle=360.00 
App.ActiveDocument.C282.Placement=Base.Placement(Base.Vector(45.053943,143.558938,31.372392),Base.Rotation(0.044586,0.579299,0.000000,0.813895))
App.ActiveDocument.addObject("Part::Cylinder","C283")
App.ActiveDocument.C283.Radius=0.553695
App.ActiveDocument.C283.Height=20.00
App.ActiveDocument.C283.Angle=360.00 
App.ActiveDocument.C283.Placement=Base.Placement(Base.Vector(45.432708,136.438552,32.443213),Base.Rotation(-0.094352,0.609543,0.000000,0.787118))
App.ActiveDocument.addObject("Part::Cylinder","C284")
App.ActiveDocument.C284.Radius=0.554026
App.ActiveDocument.C284.Height=20.00
App.ActiveDocument.C284.Angle=360.00 
App.ActiveDocument.C284.Placement=Base.Placement(Base.Vector(45.251949,134.699810,32.783119),Base.Rotation(0.099805,0.619547,0.000000,0.778588))
App.ActiveDocument.addObject("Part::Cylinder","C285")
App.ActiveDocument.C285.Radius=0.555846
App.ActiveDocument.C285.Height=20.00
App.ActiveDocument.C285.Angle=360.00 
App.ActiveDocument.C285.Placement=Base.Placement(Base.Vector(44.458692,131.306699,32.480966),Base.Rotation(0.186759,0.582557,0.000000,0.791042))
App.ActiveDocument.addObject("Part::Cylinder","C286")
App.ActiveDocument.C286.Radius=0.555285
App.ActiveDocument.C286.Height=20.00
App.ActiveDocument.C286.Angle=360.00 
App.ActiveDocument.C286.Placement=Base.Placement(Base.Vector(43.554145,127.348437,30.595848),Base.Rotation(0.213585,0.536702,0.000000,0.816291))
App.ActiveDocument.addObject("Part::Cylinder","C287")
App.ActiveDocument.C287.Radius=0.556801
App.ActiveDocument.C287.Height=20.00
App.ActiveDocument.C287.Angle=360.00 
App.ActiveDocument.C287.Placement=Base.Placement(Base.Vector(45.301187,126.444265,28.749016),Base.Rotation(0.423261,0.294828,0.000000,0.856695))
App.ActiveDocument.addObject("Part::Cylinder","C288")
App.ActiveDocument.C288.Radius=0.555663
App.ActiveDocument.C288.Height=20.00
App.ActiveDocument.C288.Angle=360.00 
App.ActiveDocument.C288.Placement=Base.Placement(Base.Vector(46.686261,125.700956,25.830716),Base.Rotation(0.506472,-0.000102,0.000000,0.862256))
App.ActiveDocument.addObject("Part::Cylinder","C289")
App.ActiveDocument.C289.Radius=0.630473
App.ActiveDocument.C289.Height=20.00
App.ActiveDocument.C289.Angle=360.00 
App.ActiveDocument.C289.Placement=Base.Placement(Base.Vector(3.792888,203.802306,37.341511),Base.Rotation(-0.616346,0.082663,0.000000,0.783124))
App.ActiveDocument.addObject("Part::Cylinder","C290")
App.ActiveDocument.C290.Radius=0.625353
App.ActiveDocument.C290.Height=20.00
App.ActiveDocument.C290.Angle=360.00 
App.ActiveDocument.C290.Placement=Base.Placement(Base.Vector(7.796694,202.952077,37.857493),Base.Rotation(-0.603742,0.135714,0.000000,0.785543))
App.ActiveDocument.addObject("Part::Cylinder","C291")
App.ActiveDocument.C291.Radius=0.618286
App.ActiveDocument.C291.Height=20.00
App.ActiveDocument.C291.Angle=360.00 
App.ActiveDocument.C291.Placement=Base.Placement(Base.Vector(11.613205,201.971192,37.598261),Base.Rotation(-0.591935,0.194233,0.000000,0.782232))
App.ActiveDocument.addObject("Part::Cylinder","C292")
App.ActiveDocument.C292.Radius=0.612765
App.ActiveDocument.C292.Height=20.00
App.ActiveDocument.C292.Angle=360.00 
App.ActiveDocument.C292.Placement=Base.Placement(Base.Vector(15.902436,200.386768,37.881789),Base.Rotation(-0.583312,0.217336,0.000000,0.782631))
App.ActiveDocument.addObject("Part::Cylinder","C293")
App.ActiveDocument.C293.Radius=0.607457
App.ActiveDocument.C293.Height=20.00
App.ActiveDocument.C293.Angle=360.00 
App.ActiveDocument.C293.Placement=Base.Placement(Base.Vector(19.977993,198.680825,38.174023),Base.Rotation(-0.569034,0.247828,0.000000,0.784080))
App.ActiveDocument.addObject("Part::Cylinder","C294")
App.ActiveDocument.C294.Radius=0.599986
App.ActiveDocument.C294.Height=20.00
App.ActiveDocument.C294.Angle=360.00 
App.ActiveDocument.C294.Placement=Base.Placement(Base.Vector(23.772917,197.061447,37.456062),Base.Rotation(-0.552917,0.285312,0.000000,0.782866))
App.ActiveDocument.addObject("Part::Cylinder","C295")
App.ActiveDocument.C295.Radius=0.595541
App.ActiveDocument.C295.Height=20.00
App.ActiveDocument.C295.Angle=360.00 
App.ActiveDocument.C295.Placement=Base.Placement(Base.Vector(27.285541,194.928571,37.843890),Base.Rotation(-0.521985,0.328509,0.000000,0.787155))
App.ActiveDocument.addObject("Part::Cylinder","C296")
App.ActiveDocument.C296.Radius=0.588917
App.ActiveDocument.C296.Height=20.00
App.ActiveDocument.C296.Angle=360.00 
App.ActiveDocument.C296.Placement=Base.Placement(Base.Vector(30.840021,192.644007,37.323452),Base.Rotation(-0.494785,0.366813,0.000000,0.787805))
App.ActiveDocument.addObject("Part::Cylinder","C297")
App.ActiveDocument.C297.Radius=0.583979
App.ActiveDocument.C297.Height=20.00
App.ActiveDocument.C297.Angle=360.00 
App.ActiveDocument.C297.Placement=Base.Placement(Base.Vector(34.001372,190.112102,37.321391),Base.Rotation(-0.456705,0.408743,0.000000,0.790158))
App.ActiveDocument.addObject("Part::Cylinder","C298")
App.ActiveDocument.C298.Radius=0.578966
App.ActiveDocument.C298.Height=20.00
App.ActiveDocument.C298.Angle=360.00 
App.ActiveDocument.C298.Placement=Base.Placement(Base.Vector(36.796483,187.429656,37.200949),Base.Rotation(-0.404617,0.459568,0.000000,0.790621))
App.ActiveDocument.addObject("Part::Cylinder","C299")
App.ActiveDocument.C299.Radius=0.576302
App.ActiveDocument.C299.Height=20.00
App.ActiveDocument.C299.Angle=360.00 
App.ActiveDocument.C299.Placement=Base.Placement(Base.Vector(39.054961,184.317783,37.797511),Base.Rotation(-0.349236,0.504186,0.000000,0.789829))
App.ActiveDocument.addObject("Part::Cylinder","C300")
App.ActiveDocument.C300.Radius=0.572476
App.ActiveDocument.C300.Height=20.00
App.ActiveDocument.C300.Angle=360.00 
App.ActiveDocument.C300.Placement=Base.Placement(Base.Vector(41.165549,180.872409,37.796012),Base.Rotation(-0.306812,0.538923,0.000000,0.784492))
App.ActiveDocument.addObject("Part::Cylinder","C301")
App.ActiveDocument.C301.Radius=0.568841
App.ActiveDocument.C301.Height=20.00
App.ActiveDocument.C301.Angle=360.00 
App.ActiveDocument.C301.Placement=Base.Placement(Base.Vector(42.979225,177.301036,37.688926),Base.Rotation(-0.254243,0.572910,0.000000,0.779188))
App.ActiveDocument.addObject("Part::Cylinder","C302")
App.ActiveDocument.C302.Radius=0.566312
App.ActiveDocument.C302.Height=20.00
App.ActiveDocument.C302.Angle=360.00 
App.ActiveDocument.C302.Placement=Base.Placement(Base.Vector(44.475061,173.385303,37.762616),Base.Rotation(-0.205688,0.597173,0.000000,0.775291))
App.ActiveDocument.addObject("Part::Cylinder","C303")
App.ActiveDocument.C303.Radius=0.565030
App.ActiveDocument.C303.Height=20.00
App.ActiveDocument.C303.Angle=360.00 
App.ActiveDocument.C303.Placement=Base.Placement(Base.Vector(45.633201,169.322569,38.143837),Base.Rotation(-0.170397,0.614002,0.000000,0.770692))
App.ActiveDocument.addObject("Part::Cylinder","C304")
App.ActiveDocument.C304.Radius=0.563557
App.ActiveDocument.C304.Height=20.00
App.ActiveDocument.C304.Angle=360.00 
App.ActiveDocument.C304.Placement=Base.Placement(Base.Vector(46.663371,164.935427,38.330382),Base.Rotation(-0.129022,0.629049,0.000000,0.766584))
App.ActiveDocument.addObject("Part::Cylinder","C305")
App.ActiveDocument.C305.Radius=0.560848
App.ActiveDocument.C305.Height=20.00
App.ActiveDocument.C305.Angle=360.00 
App.ActiveDocument.C305.Placement=Base.Placement(Base.Vector(47.333652,161.498787,37.518378),Base.Rotation(-0.038831,0.637586,0.000000,0.769400))
App.ActiveDocument.addObject("Part::Cylinder","C306")
App.ActiveDocument.C306.Radius=0.562518
App.ActiveDocument.C306.Height=20.00
App.ActiveDocument.C306.Angle=360.00 
App.ActiveDocument.C306.Placement=Base.Placement(Base.Vector(47.120449,158.051988,38.247146),Base.Rotation(0.066420,0.639537,0.000000,0.765886))
App.ActiveDocument.addObject("Part::Cylinder","C307")
App.ActiveDocument.C307.Radius=0.562411
App.ActiveDocument.C307.Height=20.00
App.ActiveDocument.C307.Angle=360.00 
App.ActiveDocument.C307.Placement=Base.Placement(Base.Vector(46.513984,153.979329,38.109373),Base.Rotation(0.124286,0.643478,0.000000,0.755307))
App.ActiveDocument.addObject("Part::Cylinder","C308")
App.ActiveDocument.C308.Radius=0.564570
App.ActiveDocument.C308.Height=20.00
App.ActiveDocument.C308.Angle=360.00 
App.ActiveDocument.C308.Placement=Base.Placement(Base.Vector(45.675496,150.567321,38.344720),Base.Rotation(0.223109,0.616523,0.000000,0.755064))
App.ActiveDocument.addObject("Part::Cylinder","C309")
App.ActiveDocument.C309.Radius=0.566538
App.ActiveDocument.C309.Height=20.00
App.ActiveDocument.C309.Angle=360.00 
App.ActiveDocument.C309.Placement=Base.Placement(Base.Vector(43.359057,142.656020,37.308975),Base.Rotation(0.022434,0.624093,0.000000,0.781028))
App.ActiveDocument.addObject("Part::Cylinder","C310")
App.ActiveDocument.C310.Radius=0.566456
App.ActiveDocument.C310.Height=20.00
App.ActiveDocument.C310.Angle=360.00 
App.ActiveDocument.C310.Placement=Base.Placement(Base.Vector(44.479483,136.638487,35.230917),Base.Rotation(-0.042007,0.526173,0.000000,0.849339))
App.ActiveDocument.addObject("Part::Cylinder","C311")
App.ActiveDocument.C311.Radius=0.566844
App.ActiveDocument.C311.Height=20.00
App.ActiveDocument.C311.Angle=360.00 
App.ActiveDocument.C311.Placement=Base.Placement(Base.Vector(44.481177,133.960737,34.525753),Base.Rotation(0.092552,0.489406,0.000000,0.867131))
App.ActiveDocument.addObject("Part::Cylinder","C312")
App.ActiveDocument.C312.Radius=0.568380
App.ActiveDocument.C312.Height=20.00
App.ActiveDocument.C312.Angle=360.00 
App.ActiveDocument.C312.Placement=Base.Placement(Base.Vector(43.246279,130.358918,35.085433),Base.Rotation(0.177868,0.497828,0.000000,0.848841))
App.ActiveDocument.addObject("Part::Cylinder","C313")
App.ActiveDocument.C313.Radius=0.567917
App.ActiveDocument.C313.Height=20.00
App.ActiveDocument.C313.Angle=360.00 
App.ActiveDocument.C313.Placement=Base.Placement(Base.Vector(42.441991,127.368016,34.365793),Base.Rotation(0.274697,0.469184,0.000000,0.839290))
App.ActiveDocument.addObject("Part::Cylinder","C314")
App.ActiveDocument.C314.Radius=0.569419
App.ActiveDocument.C314.Height=20.00
App.ActiveDocument.C314.Angle=360.00 
App.ActiveDocument.C314.Placement=Base.Placement(Base.Vector(46.451252,128.952556,32.322369),Base.Rotation(0.525089,0.000151,0.000000,0.851047))
App.ActiveDocument.addObject("Part::Cylinder","C315")
App.ActiveDocument.C315.Radius=0.567237
App.ActiveDocument.C315.Height=20.00
App.ActiveDocument.C315.Angle=360.00 
App.ActiveDocument.C315.Placement=Base.Placement(Base.Vector(42.830295,127.516945,29.307757),Base.Rotation(0.532657,-0.000054,0.000000,0.846331))
App.ActiveDocument.addObject("Part::Cylinder","C316")
App.ActiveDocument.C316.Radius=0.641121
App.ActiveDocument.C316.Height=20.00
App.ActiveDocument.C316.Angle=360.00 
App.ActiveDocument.C316.Placement=Base.Placement(Base.Vector(3.822147,202.656537,41.631099),Base.Rotation(-0.592090,0.083050,0.000000,0.801581))
App.ActiveDocument.addObject("Part::Cylinder","C317")
App.ActiveDocument.C317.Radius=0.635444
App.ActiveDocument.C317.Height=20.00
App.ActiveDocument.C317.Angle=360.00 
App.ActiveDocument.C317.Placement=Base.Placement(Base.Vector(7.967572,201.773942,41.987066),Base.Rotation(-0.580336,0.133680,0.000000,0.803330))
App.ActiveDocument.addObject("Part::Cylinder","C318")
App.ActiveDocument.C318.Radius=0.628698
App.ActiveDocument.C318.Height=20.00
App.ActiveDocument.C318.Angle=360.00 
App.ActiveDocument.C318.Placement=Base.Placement(Base.Vector(11.914953,200.705109,41.889418),Base.Rotation(-0.568580,0.187279,0.000000,0.801027))
App.ActiveDocument.addObject("Part::Cylinder","C319")
App.ActiveDocument.C319.Radius=0.623459
App.ActiveDocument.C319.Height=20.00
App.ActiveDocument.C319.Angle=360.00 
App.ActiveDocument.C319.Placement=Base.Placement(Base.Vector(16.134465,199.063969,42.296653),Base.Rotation(-0.558582,0.213764,0.000000,0.801431))
App.ActiveDocument.addObject("Part::Cylinder","C320")
App.ActiveDocument.C320.Radius=0.617644
App.ActiveDocument.C320.Height=20.00
App.ActiveDocument.C320.Angle=360.00 
App.ActiveDocument.C320.Placement=Base.Placement(Base.Vector(20.333026,197.264877,42.491115),Base.Rotation(-0.545305,0.245507,0.000000,0.801479))
App.ActiveDocument.addObject("Part::Cylinder","C321")
App.ActiveDocument.C321.Radius=0.610275
App.ActiveDocument.C321.Height=20.00
App.ActiveDocument.C321.Angle=360.00 
App.ActiveDocument.C321.Placement=Base.Placement(Base.Vector(23.925821,195.687657,41.781057),Base.Rotation(-0.522560,0.292476,0.000000,0.800867))
App.ActiveDocument.addObject("Part::Cylinder","C322")
App.ActiveDocument.C322.Radius=0.605720
App.ActiveDocument.C322.Height=20.00
App.ActiveDocument.C322.Angle=360.00 
App.ActiveDocument.C322.Placement=Base.Placement(Base.Vector(27.451831,193.410837,42.055562),Base.Rotation(-0.492303,0.329283,0.000000,0.805736))
App.ActiveDocument.addObject("Part::Cylinder","C323")
App.ActiveDocument.C323.Radius=0.599062
App.ActiveDocument.C323.Height=20.00
App.ActiveDocument.C323.Angle=360.00 
App.ActiveDocument.C323.Placement=Base.Placement(Base.Vector(30.932405,191.107768,41.497765),Base.Rotation(-0.467169,0.365444,0.000000,0.805111))
App.ActiveDocument.addObject("Part::Cylinder","C324")
App.ActiveDocument.C324.Radius=0.594554
App.ActiveDocument.C324.Height=20.00
App.ActiveDocument.C324.Angle=360.00 
App.ActiveDocument.C324.Placement=Base.Placement(Base.Vector(33.977276,188.437926,41.697490),Base.Rotation(-0.425596,0.410977,0.000000,0.806204))
App.ActiveDocument.addObject("Part::Cylinder","C325")
App.ActiveDocument.C325.Radius=0.590148
App.ActiveDocument.C325.Height=20.00
App.ActiveDocument.C325.Angle=360.00 
App.ActiveDocument.C325.Placement=Base.Placement(Base.Vector(36.585924,185.717957,41.727066),Base.Rotation(-0.382445,0.454074,0.000000,0.804707))
App.ActiveDocument.addObject("Part::Cylinder","C326")
App.ActiveDocument.C326.Radius=0.587277
App.ActiveDocument.C326.Height=20.00
App.ActiveDocument.C326.Angle=360.00 
App.ActiveDocument.C326.Placement=Base.Placement(Base.Vector(38.777423,182.537284,42.303522),Base.Rotation(-0.334635,0.498430,0.000000,0.799742))
App.ActiveDocument.addObject("Part::Cylinder","C327")
App.ActiveDocument.C327.Radius=0.583113
App.ActiveDocument.C327.Height=20.00
App.ActiveDocument.C327.Angle=360.00 
App.ActiveDocument.C327.Placement=Base.Placement(Base.Vector(40.924582,179.062590,42.214156),Base.Rotation(-0.297895,0.532101,0.000000,0.792545))
App.ActiveDocument.addObject("Part::Cylinder","C328")
App.ActiveDocument.C328.Radius=0.580167
App.ActiveDocument.C328.Height=20.00
App.ActiveDocument.C328.Angle=360.00 
App.ActiveDocument.C328.Placement=Base.Placement(Base.Vector(42.496855,175.736669,42.292018),Base.Rotation(-0.238234,0.568290,0.000000,0.787586))
App.ActiveDocument.addObject("Part::Cylinder","C329")
App.ActiveDocument.C329.Radius=0.578068
App.ActiveDocument.C329.Height=20.00
App.ActiveDocument.C329.Angle=360.00 
App.ActiveDocument.C329.Placement=Base.Placement(Base.Vector(43.915076,171.871368,42.449996),Base.Rotation(-0.202013,0.586670,0.000000,0.784225))
App.ActiveDocument.addObject("Part::Cylinder","C330")
App.ActiveDocument.C330.Radius=0.576964
App.ActiveDocument.C330.Height=20.00
App.ActiveDocument.C330.Angle=360.00 
App.ActiveDocument.C330.Placement=Base.Placement(Base.Vector(45.085807,167.711165,42.896207),Base.Rotation(-0.162088,0.603458,0.000000,0.780747))
App.ActiveDocument.addObject("Part::Cylinder","C331")
App.ActiveDocument.C331.Radius=0.575112
App.ActiveDocument.C331.Height=20.00
App.ActiveDocument.C331.Angle=360.00 
App.ActiveDocument.C331.Placement=Base.Placement(Base.Vector(46.001300,163.724236,42.693789),Base.Rotation(-0.095481,0.615907,0.000000,0.782012))
App.ActiveDocument.addObject("Part::Cylinder","C332")
App.ActiveDocument.C332.Radius=0.572927
App.ActiveDocument.C332.Height=20.00
App.ActiveDocument.C332.Angle=360.00 
App.ActiveDocument.C332.Placement=Base.Placement(Base.Vector(46.425934,160.332892,42.309266),Base.Rotation(-0.024248,0.632908,0.000000,0.773847))
App.ActiveDocument.addObject("Part::Cylinder","C333")
App.ActiveDocument.C333.Radius=0.574552
App.ActiveDocument.C333.Height=20.00
App.ActiveDocument.C333.Angle=360.00 
App.ActiveDocument.C333.Placement=Base.Placement(Base.Vector(46.168991,156.637418,43.465439),Base.Rotation(0.053883,0.651855,0.000000,0.756427))
App.ActiveDocument.addObject("Part::Cylinder","C334")
App.ActiveDocument.C334.Radius=0.574705
App.ActiveDocument.C334.Height=20.00
App.ActiveDocument.C334.Angle=360.00 
App.ActiveDocument.C334.Placement=Base.Placement(Base.Vector(45.683452,153.028640,43.332047),Base.Rotation(0.141996,0.645994,0.000000,0.750020))
App.ActiveDocument.addObject("Part::Cylinder","C335")
App.ActiveDocument.C335.Radius=0.576834
App.ActiveDocument.C335.Height=20.00
App.ActiveDocument.C335.Angle=360.00 
App.ActiveDocument.C335.Placement=Base.Placement(Base.Vector(44.730799,149.905547,43.515266),Base.Rotation(0.259101,0.613251,0.000000,0.746184))
App.ActiveDocument.addObject("Part::Cylinder","C336")
App.ActiveDocument.C336.Radius=0.579165
App.ActiveDocument.C336.Height=20.00
App.ActiveDocument.C336.Angle=360.00 
App.ActiveDocument.C336.Placement=Base.Placement(Base.Vector(42.808572,145.576643,42.140555),Base.Rotation(0.252467,0.568525,0.000000,0.782968))
App.ActiveDocument.addObject("Part::Cylinder","C337")
App.ActiveDocument.C337.Radius=0.579298
App.ActiveDocument.C337.Height=20.00
App.ActiveDocument.C337.Angle=360.00 
App.ActiveDocument.C337.Placement=Base.Placement(Base.Vector(42.436074,138.716070,37.672294),Base.Rotation(0.101425,0.439630,0.000000,0.892434))
App.ActiveDocument.addObject("Part::Cylinder","C338")
App.ActiveDocument.C338.Radius=0.579788
App.ActiveDocument.C338.Height=20.00
App.ActiveDocument.C338.Angle=360.00 
App.ActiveDocument.C338.Placement=Base.Placement(Base.Vector(42.269987,133.155255,36.759387),Base.Rotation(0.063384,0.403050,0.000000,0.912980))
App.ActiveDocument.addObject("Part::Cylinder","C339")
App.ActiveDocument.C339.Radius=0.581509
App.ActiveDocument.C339.Height=20.00
App.ActiveDocument.C339.Angle=360.00 
App.ActiveDocument.C339.Placement=Base.Placement(Base.Vector(41.117009,129.267562,37.160166),Base.Rotation(0.123937,0.407770,0.000000,0.904634))
App.ActiveDocument.addObject("Part::Cylinder","C340")
App.ActiveDocument.C340.Radius=0.581067
App.ActiveDocument.C340.Height=20.00
App.ActiveDocument.C340.Angle=360.00 
App.ActiveDocument.C340.Placement=Base.Placement(Base.Vector(43.844552,130.751557,37.040764),Base.Rotation(0.457086,0.168261,0.000000,0.873362))
App.ActiveDocument.addObject("Part::Cylinder","C341")
App.ActiveDocument.C341.Radius=0.651534
App.ActiveDocument.C341.Height=20.00
App.ActiveDocument.C341.Angle=360.00 
App.ActiveDocument.C341.Placement=Base.Placement(Base.Vector(3.969069,201.209644,45.849464),Base.Rotation(-0.565389,0.083067,0.000000,0.820631))
App.ActiveDocument.addObject("Part::Cylinder","C342")
App.ActiveDocument.C342.Radius=0.645434
App.ActiveDocument.C342.Height=20.00
App.ActiveDocument.C342.Angle=360.00 
App.ActiveDocument.C342.Placement=Base.Placement(Base.Vector(8.195446,200.298798,46.138539),Base.Rotation(-0.556654,0.133004,0.000000,0.820028))
App.ActiveDocument.addObject("Part::Cylinder","C343")
App.ActiveDocument.C343.Radius=0.639151
App.ActiveDocument.C343.Height=20.00
App.ActiveDocument.C343.Angle=360.00 
App.ActiveDocument.C343.Placement=Base.Placement(Base.Vector(12.113781,199.176760,46.169049),Base.Rotation(-0.545767,0.180453,0.000000,0.818276))
App.ActiveDocument.addObject("Part::Cylinder","C344")
App.ActiveDocument.C344.Radius=0.634199
App.ActiveDocument.C344.Height=20.00
App.ActiveDocument.C344.Angle=360.00 
App.ActiveDocument.C344.Placement=Base.Placement(Base.Vector(16.093139,197.567025,46.566457),Base.Rotation(-0.534156,0.208600,0.000000,0.819246))
App.ActiveDocument.addObject("Part::Cylinder","C345")
App.ActiveDocument.C345.Radius=0.628239
App.ActiveDocument.C345.Height=20.00
App.ActiveDocument.C345.Angle=360.00 
App.ActiveDocument.C345.Placement=Base.Placement(Base.Vector(20.088056,195.904848,46.502766),Base.Rotation(-0.519159,0.237680,0.000000,0.820964))
App.ActiveDocument.addObject("Part::Cylinder","C346")
App.ActiveDocument.C346.Radius=0.621054
App.ActiveDocument.C346.Height=20.00
App.ActiveDocument.C346.Angle=360.00 
App.ActiveDocument.C346.Placement=Base.Placement(Base.Vector(23.586533,194.307727,45.961651),Base.Rotation(-0.497942,0.289425,0.000000,0.817488))
App.ActiveDocument.addObject("Part::Cylinder","C347")
App.ActiveDocument.C347.Radius=0.616451
App.ActiveDocument.C347.Height=20.00
App.ActiveDocument.C347.Angle=360.00 
App.ActiveDocument.C347.Placement=Base.Placement(Base.Vector(27.113821,191.902900,46.303413),Base.Rotation(-0.469283,0.327778,0.000000,0.819960))
App.ActiveDocument.addObject("Part::Cylinder","C348")
App.ActiveDocument.C348.Radius=0.609589
App.ActiveDocument.C348.Height=20.00
App.ActiveDocument.C348.Angle=360.00 
App.ActiveDocument.C348.Placement=Base.Placement(Base.Vector(30.745600,189.421763,45.740330),Base.Rotation(-0.444074,0.362733,0.000000,0.819282))
App.ActiveDocument.addObject("Part::Cylinder","C349")
App.ActiveDocument.C349.Radius=0.605274
App.ActiveDocument.C349.Height=20.00
App.ActiveDocument.C349.Angle=360.00 
App.ActiveDocument.C349.Placement=Base.Placement(Base.Vector(33.712867,186.646247,45.995763),Base.Rotation(-0.405882,0.405412,0.000000,0.819085))
App.ActiveDocument.addObject("Part::Cylinder","C350")
App.ActiveDocument.C350.Radius=0.601571
App.ActiveDocument.C350.Height=20.00
App.ActiveDocument.C350.Angle=360.00 
App.ActiveDocument.C350.Placement=Base.Placement(Base.Vector(36.163527,183.844199,46.245644),Base.Rotation(-0.362653,0.447281,0.000000,0.817571))
App.ActiveDocument.addObject("Part::Cylinder","C351")
App.ActiveDocument.C351.Radius=0.598393
App.ActiveDocument.C351.Height=20.00
App.ActiveDocument.C351.Angle=360.00 
App.ActiveDocument.C351.Placement=Base.Placement(Base.Vector(38.455198,180.547411,46.599616),Base.Rotation(-0.327120,0.479922,0.000000,0.814044))
App.ActiveDocument.addObject("Part::Cylinder","C352")
App.ActiveDocument.C352.Radius=0.594535
App.ActiveDocument.C352.Height=20.00
App.ActiveDocument.C352.Angle=360.00 
App.ActiveDocument.C352.Placement=Base.Placement(Base.Vector(40.457338,177.231462,46.650865),Base.Rotation(-0.274273,0.522629,0.000000,0.807238))
App.ActiveDocument.addObject("Part::Cylinder","C353")
App.ActiveDocument.C353.Radius=0.591334
App.ActiveDocument.C353.Height=20.00
App.ActiveDocument.C353.Angle=360.00 
App.ActiveDocument.C353.Placement=Base.Placement(Base.Vector(41.998428,173.893211,46.593286),Base.Rotation(-0.225721,0.554424,0.000000,0.801040))
App.ActiveDocument.addObject("Part::Cylinder","C354")
App.ActiveDocument.C354.Radius=0.589740
App.ActiveDocument.C354.Height=20.00
App.ActiveDocument.C354.Angle=360.00 
App.ActiveDocument.C354.Placement=Base.Placement(Base.Vector(43.354177,169.939489,46.937919),Base.Rotation(-0.190516,0.572044,0.000000,0.797790))
App.ActiveDocument.addObject("Part::Cylinder","C355")
App.ActiveDocument.C355.Radius=0.588600
App.ActiveDocument.C355.Height=20.00
App.ActiveDocument.C355.Angle=360.00 
App.ActiveDocument.C355.Placement=Base.Placement(Base.Vector(44.370691,166.100270,47.256224),Base.Rotation(-0.143144,0.588999,0.000000,0.795355))
App.ActiveDocument.addObject("Part::Cylinder","C356")
App.ActiveDocument.C356.Radius=0.587105
App.ActiveDocument.C356.Height=20.00
App.ActiveDocument.C356.Angle=360.00 
App.ActiveDocument.C356.Placement=Base.Placement(Base.Vector(45.085520,162.068548,47.372906),Base.Rotation(-0.089195,0.608918,0.000000,0.788203))
App.ActiveDocument.addObject("Part::Cylinder","C357")
App.ActiveDocument.C357.Radius=0.585026
App.ActiveDocument.C357.Height=20.00
App.ActiveDocument.C357.Angle=360.00 
App.ActiveDocument.C357.Placement=Base.Placement(Base.Vector(45.550687,158.566749,47.186773),Base.Rotation(-0.033774,0.629473,0.000000,0.776288))
App.ActiveDocument.addObject("Part::Cylinder","C358")
App.ActiveDocument.C358.Radius=0.586532
App.ActiveDocument.C358.Height=20.00
App.ActiveDocument.C358.Angle=360.00 
App.ActiveDocument.C358.Placement=Base.Placement(Base.Vector(45.325967,155.254482,48.046055),Base.Rotation(0.064857,0.638801,0.000000,0.766634))
App.ActiveDocument.addObject("Part::Cylinder","C359")
App.ActiveDocument.C359.Radius=0.586862
App.ActiveDocument.C359.Height=20.00
App.ActiveDocument.C359.Angle=360.00 
App.ActiveDocument.C359.Placement=Base.Placement(Base.Vector(44.772519,151.824816,48.111792),Base.Rotation(0.171439,0.634284,0.000000,0.753852))
App.ActiveDocument.addObject("Part::Cylinder","C360")
App.ActiveDocument.C360.Radius=0.589484
App.ActiveDocument.C360.Height=20.00
App.ActiveDocument.C360.Angle=360.00 
App.ActiveDocument.C360.Placement=Base.Placement(Base.Vector(43.615905,148.791288,48.564298),Base.Rotation(0.267383,0.609999,0.000000,0.745927))
App.ActiveDocument.addObject("Part::Cylinder","C361")
App.ActiveDocument.C361.Radius=0.591578
App.ActiveDocument.C361.Height=20.00
App.ActiveDocument.C361.Angle=360.00 
App.ActiveDocument.C361.Placement=Base.Placement(Base.Vector(42.073595,146.346831,48.202827),Base.Rotation(0.393827,0.547629,0.000000,0.738243))
App.ActiveDocument.addObject("Part::Cylinder","C362")
App.ActiveDocument.C362.Radius=0.592133
App.ActiveDocument.C362.Height=20.00
App.ActiveDocument.C362.Angle=360.00 
App.ActiveDocument.C362.Placement=Base.Placement(Base.Vector(39.233148,140.545858,44.012402),Base.Rotation(0.246939,0.500754,0.000000,0.829619))
App.ActiveDocument.addObject("Part::Cylinder","C363")
App.ActiveDocument.C363.Radius=0.592592
App.ActiveDocument.C363.Height=20.00
App.ActiveDocument.C363.Angle=360.00 
App.ActiveDocument.C363.Placement=Base.Placement(Base.Vector(38.303052,133.669956,41.524190),Base.Rotation(0.111271,0.450078,0.000000,0.886029))
App.ActiveDocument.addObject("Part::Cylinder","C364")
App.ActiveDocument.C364.Radius=0.594473
App.ActiveDocument.C364.Height=20.00
App.ActiveDocument.C364.Angle=360.00 
App.ActiveDocument.C364.Placement=Base.Placement(Base.Vector(38.435958,130.796418,41.048272),Base.Rotation(0.222981,0.367523,0.000000,0.902888))
App.ActiveDocument.addObject("Part::Cylinder","C365")
App.ActiveDocument.C365.Radius=0.591870
App.ActiveDocument.C365.Height=20.00
App.ActiveDocument.C365.Angle=360.00 
App.ActiveDocument.C365.Placement=Base.Placement(Base.Vector(42.503460,132.723796,40.609397),Base.Rotation(0.547130,-0.000000,0.000000,0.837048))
App.ActiveDocument.addObject("Part::Cylinder","C366")
App.ActiveDocument.C366.Radius=0.661584
App.ActiveDocument.C366.Height=20.00
App.ActiveDocument.C366.Angle=360.00 
App.ActiveDocument.C366.Placement=Base.Placement(Base.Vector(3.901331,199.614740,49.746175),Base.Rotation(-0.539417,0.077815,0.000000,0.838436))
App.ActiveDocument.addObject("Part::Cylinder","C367")
App.ActiveDocument.C367.Radius=0.655716
App.ActiveDocument.C367.Height=20.00
App.ActiveDocument.C367.Angle=360.00 
App.ActiveDocument.C367.Placement=Base.Placement(Base.Vector(8.185168,198.622489,50.148683),Base.Rotation(-0.527575,0.129532,0.000000,0.839575))
App.ActiveDocument.addObject("Part::Cylinder","C368")
App.ActiveDocument.C368.Radius=0.649339
App.ActiveDocument.C368.Height=20.00
App.ActiveDocument.C368.Angle=360.00 
App.ActiveDocument.C368.Placement=Base.Placement(Base.Vector(12.202549,197.459435,50.202352),Base.Rotation(-0.519510,0.173037,0.000000,0.836760))
App.ActiveDocument.addObject("Part::Cylinder","C369")
App.ActiveDocument.C369.Radius=0.644526
App.ActiveDocument.C369.Height=20.00
App.ActiveDocument.C369.Angle=360.00 
App.ActiveDocument.C369.Placement=Base.Placement(Base.Vector(16.254412,195.736282,50.636662),Base.Rotation(-0.502699,0.202221,0.000000,0.840476))
App.ActiveDocument.addObject("Part::Cylinder","C370")
App.ActiveDocument.C370.Radius=0.637867
App.ActiveDocument.C370.Height=20.00
App.ActiveDocument.C370.Angle=360.00 
App.ActiveDocument.C370.Placement=Base.Placement(Base.Vector(20.346252,194.010998,50.472729),Base.Rotation(-0.488747,0.237817,0.000000,0.839386))
App.ActiveDocument.addObject("Part::Cylinder","C371")
App.ActiveDocument.C371.Radius=0.631199
App.ActiveDocument.C371.Height=20.00
App.ActiveDocument.C371.Angle=360.00 
App.ActiveDocument.C371.Placement=Base.Placement(Base.Vector(23.817036,192.258697,50.185228),Base.Rotation(-0.469353,0.288085,0.000000,0.834695))
App.ActiveDocument.addObject("Part::Cylinder","C372")
App.ActiveDocument.C372.Radius=0.626697
App.ActiveDocument.C372.Height=20.00
App.ActiveDocument.C372.Angle=360.00 
App.ActiveDocument.C372.Placement=Base.Placement(Base.Vector(27.137960,189.834809,50.548408),Base.Rotation(-0.445956,0.325631,0.000000,0.833719))
App.ActiveDocument.addObject("Part::Cylinder","C373")
App.ActiveDocument.C373.Radius=0.620152
App.ActiveDocument.C373.Height=20.00
App.ActiveDocument.C373.Angle=360.00 
App.ActiveDocument.C373.Placement=Base.Placement(Base.Vector(30.448334,187.516437,49.957295),Base.Rotation(-0.422840,0.359133,0.000000,0.832004))
App.ActiveDocument.addObject("Part::Cylinder","C374")
App.ActiveDocument.C374.Radius=0.616312
App.ActiveDocument.C374.Height=20.00
App.ActiveDocument.C374.Angle=360.00 
App.ActiveDocument.C374.Placement=Base.Placement(Base.Vector(33.241802,184.735467,50.297057),Base.Rotation(-0.387740,0.397747,0.000000,0.831538))
App.ActiveDocument.addObject("Part::Cylinder","C375")
App.ActiveDocument.C375.Radius=0.612400
App.ActiveDocument.C375.Height=20.00
App.ActiveDocument.C375.Angle=360.00 
App.ActiveDocument.C375.Placement=Base.Placement(Base.Vector(35.750633,181.725760,50.557537),Base.Rotation(-0.345569,0.441066,0.000000,0.828277))
App.ActiveDocument.addObject("Part::Cylinder","C376")
App.ActiveDocument.C376.Radius=0.609579
App.ActiveDocument.C376.Height=20.00
App.ActiveDocument.C376.Angle=360.00 
App.ActiveDocument.C376.Placement=Base.Placement(Base.Vector(37.947290,178.405107,50.913907),Base.Rotation(-0.307665,0.469941,0.000000,0.827344))
App.ActiveDocument.addObject("Part::Cylinder","C377")
App.ActiveDocument.C377.Radius=0.605567
App.ActiveDocument.C377.Height=20.00
App.ActiveDocument.C377.Angle=360.00 
App.ActiveDocument.C377.Placement=Base.Placement(Base.Vector(39.911351,175.142832,50.820558),Base.Rotation(-0.256623,0.509070,0.000000,0.821579))
App.ActiveDocument.addObject("Part::Cylinder","C378")
App.ActiveDocument.C378.Radius=0.602634
App.ActiveDocument.C378.Height=20.00
App.ActiveDocument.C378.Angle=360.00 
App.ActiveDocument.C378.Placement=Base.Placement(Base.Vector(41.463656,171.489658,50.882700),Base.Rotation(-0.208868,0.539589,0.000000,0.815609))
App.ActiveDocument.addObject("Part::Cylinder","C379")
App.ActiveDocument.C379.Radius=0.601417
App.ActiveDocument.C379.Height=20.00
App.ActiveDocument.C379.Angle=360.00 
App.ActiveDocument.C379.Placement=Base.Placement(Base.Vector(42.638267,167.788522,51.302371),Base.Rotation(-0.174159,0.557052,0.000000,0.812011))
App.ActiveDocument.addObject("Part::Cylinder","C380")
App.ActiveDocument.C380.Radius=0.600242
App.ActiveDocument.C380.Height=20.00
App.ActiveDocument.C380.Angle=360.00 
App.ActiveDocument.C380.Placement=Base.Placement(Base.Vector(43.517098,164.080938,51.537065),Base.Rotation(-0.125688,0.573992,0.000000,0.809158))
App.ActiveDocument.addObject("Part::Cylinder","C381")
App.ActiveDocument.C381.Radius=0.598883
App.ActiveDocument.C381.Height=20.00
App.ActiveDocument.C381.Angle=360.00 
App.ActiveDocument.C381.Placement=Base.Placement(Base.Vector(44.215234,159.985754,51.704073),Base.Rotation(-0.086053,0.591707,0.000000,0.801547))
App.ActiveDocument.addObject("Part::Cylinder","C382")
App.ActiveDocument.C382.Radius=0.597828
App.ActiveDocument.C382.Height=20.00
App.ActiveDocument.C382.Angle=360.00 
App.ActiveDocument.C382.Placement=Base.Placement(Base.Vector(44.536211,156.840270,51.743657),Base.Rotation(-0.018922,0.607123,0.000000,0.794383))
App.ActiveDocument.addObject("Part::Cylinder","C383")
App.ActiveDocument.C383.Radius=0.598667
App.ActiveDocument.C383.Height=20.00
App.ActiveDocument.C383.Angle=360.00 
App.ActiveDocument.C383.Placement=Base.Placement(Base.Vector(44.266253,153.662336,52.446615),Base.Rotation(0.090381,0.620038,0.000000,0.779349))
App.ActiveDocument.addObject("Part::Cylinder","C384")
App.ActiveDocument.C384.Radius=0.599741
App.ActiveDocument.C384.Height=20.00
App.ActiveDocument.C384.Angle=360.00 
App.ActiveDocument.C384.Placement=Base.Placement(Base.Vector(43.603245,150.371579,52.619115),Base.Rotation(0.174672,0.610935,0.000000,0.772171))
App.ActiveDocument.addObject("Part::Cylinder","C385")
App.ActiveDocument.C385.Radius=0.602075
App.ActiveDocument.C385.Height=20.00
App.ActiveDocument.C385.Angle=360.00 
App.ActiveDocument.C385.Placement=Base.Placement(Base.Vector(42.328018,147.328977,53.287501),Base.Rotation(0.277263,0.599037,0.000000,0.751186))
App.ActiveDocument.addObject("Part::Cylinder","C386")
App.ActiveDocument.C386.Radius=0.603540
App.ActiveDocument.C386.Height=20.00
App.ActiveDocument.C386.Angle=360.00 
App.ActiveDocument.C386.Placement=Base.Placement(Base.Vector(40.626455,144.558056,53.737882),Base.Rotation(0.391735,0.586047,0.000000,0.709291))
App.ActiveDocument.addObject("Part::Cylinder","C387")
App.ActiveDocument.C387.Radius=0.604795
App.ActiveDocument.C387.Height=20.00
App.ActiveDocument.C387.Angle=360.00 
App.ActiveDocument.C387.Placement=Base.Placement(Base.Vector(37.510026,141.004023,51.732397),Base.Rotation(0.392904,0.558757,0.000000,0.730354))
App.ActiveDocument.addObject("Part::Cylinder","C388")
App.ActiveDocument.C388.Radius=0.605815
App.ActiveDocument.C388.Height=20.00
App.ActiveDocument.C388.Angle=360.00 
App.ActiveDocument.C388.Placement=Base.Placement(Base.Vector(34.719328,134.381036,48.340598),Base.Rotation(0.210955,0.541917,0.000000,0.813526))
App.ActiveDocument.addObject("Part::Cylinder","C389")
App.ActiveDocument.C389.Radius=0.606933
App.ActiveDocument.C389.Height=20.00
App.ActiveDocument.C389.Angle=360.00 
App.ActiveDocument.C389.Placement=Base.Placement(Base.Vector(35.546911,132.585281,45.719594),Base.Rotation(0.348834,0.345535,0.000000,0.871160))
App.ActiveDocument.addObject("Part::Cylinder","C390")
App.ActiveDocument.C390.Radius=0.671048
App.ActiveDocument.C390.Height=20.00
App.ActiveDocument.C390.Angle=360.00 
App.ActiveDocument.C390.Placement=Base.Placement(Base.Vector(4.196106,197.678752,53.644179),Base.Rotation(-0.508672,0.081517,0.000000,0.857093))
App.ActiveDocument.addObject("Part::Cylinder","C391")
App.ActiveDocument.C391.Radius=0.665824
App.ActiveDocument.C391.Height=20.00
App.ActiveDocument.C391.Angle=360.00 
App.ActiveDocument.C391.Placement=Base.Placement(Base.Vector(8.381775,196.538172,54.257305),Base.Rotation(-0.503624,0.121024,0.000000,0.855404))
App.ActiveDocument.addObject("Part::Cylinder","C392")
App.ActiveDocument.C392.Radius=0.659701
App.ActiveDocument.C392.Height=20.00
App.ActiveDocument.C392.Angle=360.00 
App.ActiveDocument.C392.Placement=Base.Placement(Base.Vector(12.209724,195.400136,54.335199),Base.Rotation(-0.493022,0.168653,0.000000,0.853514))
App.ActiveDocument.addObject("Part::Cylinder","C393")
App.ActiveDocument.C393.Radius=0.655162
App.ActiveDocument.C393.Height=20.00
App.ActiveDocument.C393.Angle=360.00 
App.ActiveDocument.C393.Placement=Base.Placement(Base.Vector(16.036769,193.668313,54.831477),Base.Rotation(-0.481282,0.195845,0.000000,0.854408))
App.ActiveDocument.addObject("Part::Cylinder","C394")
App.ActiveDocument.C394.Radius=0.648027
App.ActiveDocument.C394.Height=20.00
App.ActiveDocument.C394.Angle=360.00 
App.ActiveDocument.C394.Placement=Base.Placement(Base.Vector(20.025344,192.049297,54.499428),Base.Rotation(-0.471412,0.233129,0.000000,0.850542))
App.ActiveDocument.addObject("Part::Cylinder","C395")
App.ActiveDocument.C395.Radius=0.641928
App.ActiveDocument.C395.Height=20.00
App.ActiveDocument.C395.Angle=360.00 
App.ActiveDocument.C395.Placement=Base.Placement(Base.Vector(23.596632,190.151758,54.387219),Base.Rotation(-0.453057,0.274913,0.000000,0.848034))
App.ActiveDocument.addObject("Part::Cylinder","C396")
App.ActiveDocument.C396.Radius=0.637138
App.ActiveDocument.C396.Height=20.00
App.ActiveDocument.C396.Angle=360.00 
App.ActiveDocument.C396.Placement=Base.Placement(Base.Vector(26.838072,187.732325,54.728286),Base.Rotation(-0.426827,0.321662,0.000000,0.845193))
App.ActiveDocument.addObject("Part::Cylinder","C397")
App.ActiveDocument.C397.Radius=0.630965
App.ActiveDocument.C397.Height=20.00
App.ActiveDocument.C397.Angle=360.00 
App.ActiveDocument.C397.Placement=Base.Placement(Base.Vector(30.119454,185.251555,54.342781),Base.Rotation(-0.402466,0.357645,0.000000,0.842681))
App.ActiveDocument.addObject("Part::Cylinder","C398")
App.ActiveDocument.C398.Radius=0.627048
App.ActiveDocument.C398.Height=20.00
App.ActiveDocument.C398.Angle=360.00 
App.ActiveDocument.C398.Placement=Base.Placement(Base.Vector(32.847072,182.430386,54.639208),Base.Rotation(-0.369389,0.395346,0.000000,0.840983))
App.ActiveDocument.addObject("Part::Cylinder","C399")
App.ActiveDocument.C399.Radius=0.623508
App.ActiveDocument.C399.Height=20.00
App.ActiveDocument.C399.Angle=360.00 
App.ActiveDocument.C399.Placement=Base.Placement(Base.Vector(35.234282,179.319995,54.973741),Base.Rotation(-0.323365,0.438379,0.000000,0.838606))
App.ActiveDocument.addObject("Part::Cylinder","C400")
App.ActiveDocument.C400.Radius=0.620422
App.ActiveDocument.C400.Height=20.00
App.ActiveDocument.C400.Angle=360.00 
App.ActiveDocument.C400.Placement=Base.Placement(Base.Vector(37.357248,176.013508,55.147611),Base.Rotation(-0.282438,0.466534,0.000000,0.838197))
App.ActiveDocument.addObject("Part::Cylinder","C401")
App.ActiveDocument.C401.Radius=0.616661
App.ActiveDocument.C401.Height=20.00
App.ActiveDocument.C401.Angle=360.00 
App.ActiveDocument.C401.Placement=Base.Placement(Base.Vector(39.214159,172.763998,54.986054),Base.Rotation(-0.235460,0.498411,0.000000,0.834353))
App.ActiveDocument.addObject("Part::Cylinder","C402")
App.ActiveDocument.C402.Radius=0.614791
App.ActiveDocument.C402.Height=20.00
App.ActiveDocument.C402.Angle=360.00 
App.ActiveDocument.C402.Placement=Base.Placement(Base.Vector(40.515250,169.361216,55.230623),Base.Rotation(-0.194387,0.520831,0.000000,0.831233))
App.ActiveDocument.addObject("Part::Cylinder","C403")
App.ActiveDocument.C403.Radius=0.613239
App.ActiveDocument.C403.Height=20.00
App.ActiveDocument.C403.Angle=360.00 
App.ActiveDocument.C403.Placement=Base.Placement(Base.Vector(41.724856,165.433746,55.426121),Base.Rotation(-0.147825,0.536660,0.000000,0.830749))
App.ActiveDocument.addObject("Part::Cylinder","C404")
App.ActiveDocument.C404.Radius=0.612263
App.ActiveDocument.C404.Height=20.00
App.ActiveDocument.C404.Angle=360.00 
App.ActiveDocument.C404.Placement=Base.Placement(Base.Vector(42.533689,161.558482,55.666296),Base.Rotation(-0.113091,0.549104,0.000000,0.828067))
App.ActiveDocument.addObject("Part::Cylinder","C405")
App.ActiveDocument.C405.Radius=0.611600
App.ActiveDocument.C405.Height=20.00
App.ActiveDocument.C405.Angle=360.00 
App.ActiveDocument.C405.Placement=Base.Placement(Base.Vector(43.026931,157.727633,56.043769),Base.Rotation(-0.067944,0.567557,0.000000,0.820526))
App.ActiveDocument.addObject("Part::Cylinder","C406")
App.ActiveDocument.C406.Radius=0.610131
App.ActiveDocument.C406.Height=20.00
App.ActiveDocument.C406.Angle=360.00 
App.ActiveDocument.C406.Placement=Base.Placement(Base.Vector(43.318329,154.846374,55.891224),Base.Rotation(-0.000281,0.582284,0.000000,0.812985))
App.ActiveDocument.addObject("Part::Cylinder","C407")
App.ActiveDocument.C407.Radius=0.612144
App.ActiveDocument.C407.Height=20.00
App.ActiveDocument.C407.Angle=360.00 
App.ActiveDocument.C407.Placement=Base.Placement(Base.Vector(42.849344,152.050220,56.724099),Base.Rotation(0.100324,0.583853,0.000000,0.805637))
App.ActiveDocument.addObject("Part::Cylinder","C408")
App.ActiveDocument.C408.Radius=0.612496
App.ActiveDocument.C408.Height=20.00
App.ActiveDocument.C408.Angle=360.00 
App.ActiveDocument.C408.Placement=Base.Placement(Base.Vector(42.069386,148.668612,56.748177),Base.Rotation(0.170837,0.585148,0.000000,0.792727))
App.ActiveDocument.addObject("Part::Cylinder","C409")
App.ActiveDocument.C409.Radius=0.614789
App.ActiveDocument.C409.Height=20.00
App.ActiveDocument.C409.Angle=360.00 
App.ActiveDocument.C409.Placement=Base.Placement(Base.Vector(40.704894,145.339854,57.514680),Base.Rotation(0.264329,0.582117,0.000000,0.768941))
App.ActiveDocument.addObject("Part::Cylinder","C410")
App.ActiveDocument.C410.Radius=0.615581
App.ActiveDocument.C410.Height=20.00
App.ActiveDocument.C410.Angle=360.00 
App.ActiveDocument.C410.Placement=Base.Placement(Base.Vector(38.898974,141.939751,57.655598),Base.Rotation(0.344807,0.586530,0.000000,0.732865))
App.ActiveDocument.addObject("Part::Cylinder","C411")
App.ActiveDocument.C411.Radius=0.616530
App.ActiveDocument.C411.Height=20.00
App.ActiveDocument.C411.Angle=360.00 
App.ActiveDocument.C411.Placement=Base.Placement(Base.Vector(36.733596,139.082031,58.626232),Base.Rotation(0.461419,0.603938,0.000000,0.649885))
App.ActiveDocument.addObject("Part::Cylinder","C412")
App.ActiveDocument.C412.Radius=0.618698
App.ActiveDocument.C412.Height=20.00
App.ActiveDocument.C412.Angle=360.00 
App.ActiveDocument.C412.Placement=Base.Placement(Base.Vector(39.171417,138.336478,52.821598),Base.Rotation(0.549894,0.152666,0.000000,0.821163))
App.ActiveDocument.addObject("Part::Cylinder","C413")
App.ActiveDocument.C413.Radius=0.618448
App.ActiveDocument.C413.Height=20.00
App.ActiveDocument.C413.Angle=360.00 
App.ActiveDocument.C413.Placement=Base.Placement(Base.Vector(37.654097,136.731250,49.756271),Base.Rotation(0.547130,-0.000000,0.000000,0.837048))
App.ActiveDocument.addObject("Part::Cylinder","C414")
App.ActiveDocument.C414.Radius=0.680783
App.ActiveDocument.C414.Height=20.00
App.ActiveDocument.C414.Angle=360.00 
App.ActiveDocument.C414.Placement=Base.Placement(Base.Vector(3.924849,195.568415,57.485353),Base.Rotation(-0.492950,0.073347,0.000000,0.866961))
App.ActiveDocument.addObject("Part::Cylinder","C415")
App.ActiveDocument.C415.Radius=0.676215
App.ActiveDocument.C415.Height=20.00
App.ActiveDocument.C415.Angle=360.00 
App.ActiveDocument.C415.Placement=Base.Placement(Base.Vector(8.047716,194.310534,58.312042),Base.Rotation(-0.484933,0.113757,0.000000,0.867121))
App.ActiveDocument.addObject("Part::Cylinder","C416")
App.ActiveDocument.C416.Radius=0.669779
App.ActiveDocument.C416.Height=20.00
App.ActiveDocument.C416.Angle=360.00 
App.ActiveDocument.C416.Placement=Base.Placement(Base.Vector(11.952742,193.178218,58.358020),Base.Rotation(-0.473059,0.166527,0.000000,0.865150))
App.ActiveDocument.addObject("Part::Cylinder","C417")
App.ActiveDocument.C417.Radius=0.664918
App.ActiveDocument.C417.Height=20.00
App.ActiveDocument.C417.Angle=360.00 
App.ActiveDocument.C417.Placement=Base.Placement(Base.Vector(15.923996,191.380156,58.786980),Base.Rotation(-0.464366,0.189674,0.000000,0.865094))
App.ActiveDocument.addObject("Part::Cylinder","C418")
App.ActiveDocument.C418.Radius=0.658101
App.ActiveDocument.C418.Height=20.00
App.ActiveDocument.C418.Angle=360.00 
App.ActiveDocument.C418.Placement=Base.Placement(Base.Vector(19.787013,189.790155,58.473686),Base.Rotation(-0.450114,0.228015,0.000000,0.863369))
App.ActiveDocument.addObject("Part::Cylinder","C419")
App.ActiveDocument.C419.Radius=0.652211
App.ActiveDocument.C419.Height=20.00
App.ActiveDocument.C419.Angle=360.00 
App.ActiveDocument.C419.Placement=Base.Placement(Base.Vector(23.555753,187.629641,58.553304),Base.Rotation(-0.431060,0.268615,0.000000,0.861414))
App.ActiveDocument.addObject("Part::Cylinder","C420")
App.ActiveDocument.C420.Radius=0.646811
App.ActiveDocument.C420.Height=20.00
App.ActiveDocument.C420.Angle=360.00 
App.ActiveDocument.C420.Placement=Base.Placement(Base.Vector(26.811459,185.225736,58.715544),Base.Rotation(-0.406294,0.317698,0.000000,0.856734))
App.ActiveDocument.addObject("Part::Cylinder","C421")
App.ActiveDocument.C421.Radius=0.641751
App.ActiveDocument.C421.Height=20.00
App.ActiveDocument.C421.Angle=360.00 
App.ActiveDocument.C421.Placement=Base.Placement(Base.Vector(29.727736,182.809987,58.632982),Base.Rotation(-0.384458,0.352174,0.000000,0.853326))
App.ActiveDocument.addObject("Part::Cylinder","C422")
App.ActiveDocument.C422.Radius=0.637865
App.ActiveDocument.C422.Height=20.00
App.ActiveDocument.C422.Angle=360.00 
App.ActiveDocument.C422.Placement=Base.Placement(Base.Vector(32.330328,179.960878,58.929508),Base.Rotation(-0.345924,0.394435,0.000000,0.851327))
App.ActiveDocument.addObject("Part::Cylinder","C423")
App.ActiveDocument.C423.Radius=0.634934
App.ActiveDocument.C423.Height=20.00
App.ActiveDocument.C423.Angle=360.00 
App.ActiveDocument.C423.Placement=Base.Placement(Base.Vector(34.459649,176.937533,59.297879),Base.Rotation(-0.302340,0.431329,0.000000,0.850027))
App.ActiveDocument.addObject("Part::Cylinder","C424")
App.ActiveDocument.C424.Radius=0.631347
App.ActiveDocument.C424.Height=20.00
App.ActiveDocument.C424.Angle=360.00 
App.ActiveDocument.C424.Placement=Base.Placement(Base.Vector(36.536226,173.607945,59.286105),Base.Rotation(-0.255395,0.463219,0.000000,0.848647))
App.ActiveDocument.addObject("Part::Cylinder","C425")
App.ActiveDocument.C425.Radius=0.627963
App.ActiveDocument.C425.Height=20.00
App.ActiveDocument.C425.Angle=360.00 
App.ActiveDocument.C425.Placement=Base.Placement(Base.Vector(38.301013,170.271070,59.052464),Base.Rotation(-0.208154,0.486426,0.000000,0.848564))
App.ActiveDocument.addObject("Part::Cylinder","C426")
App.ActiveDocument.C426.Radius=0.626725
App.ActiveDocument.C426.Height=20.00
App.ActiveDocument.C426.Angle=360.00 
App.ActiveDocument.C426.Placement=Base.Placement(Base.Vector(39.481305,166.779063,59.240972),Base.Rotation(-0.158374,0.499275,0.000000,0.851846))
App.ActiveDocument.addObject("Part::Cylinder","C427")
App.ActiveDocument.C427.Radius=0.625738
App.ActiveDocument.C427.Height=20.00
App.ActiveDocument.C427.Angle=360.00 
App.ActiveDocument.C427.Placement=Base.Placement(Base.Vector(40.484521,162.831503,59.476613),Base.Rotation(-0.134489,0.506534,0.000000,0.851667))
App.ActiveDocument.addObject("Part::Cylinder","C428")
App.ActiveDocument.C428.Radius=0.624967
App.ActiveDocument.C428.Height=20.00
App.ActiveDocument.C428.Angle=360.00 
App.ActiveDocument.C428.Placement=Base.Placement(Base.Vector(41.239386,158.816555,59.869564),Base.Rotation(-0.108453,0.521010,0.000000,0.846632))
App.ActiveDocument.addObject("Part::Cylinder","C429")
App.ActiveDocument.C429.Radius=0.623649
App.ActiveDocument.C429.Height=20.00
App.ActiveDocument.C429.Angle=360.00 
App.ActiveDocument.C429.Placement=Base.Placement(Base.Vector(41.654790,155.382005,60.049299),Base.Rotation(-0.040276,0.546255,0.000000,0.836650))
App.ActiveDocument.addObject("Part::Cylinder","C430")
App.ActiveDocument.C430.Radius=0.623943
App.ActiveDocument.C430.Height=20.00
App.ActiveDocument.C430.Angle=360.00 
App.ActiveDocument.C430.Placement=Base.Placement(Base.Vector(41.579553,152.723203,60.344997),Base.Rotation(0.040601,0.553740,0.000000,0.831699))
App.ActiveDocument.addObject("Part::Cylinder","C431")
App.ActiveDocument.C431.Radius=0.625430
App.ActiveDocument.C431.Height=20.00
App.ActiveDocument.C431.Angle=360.00 
App.ActiveDocument.C431.Placement=Base.Placement(Base.Vector(40.854928,149.283862,60.898459),Base.Rotation(0.124206,0.557177,0.000000,0.821052))
App.ActiveDocument.addObject("Part::Cylinder","C432")
App.ActiveDocument.C432.Radius=0.626555
App.ActiveDocument.C432.Height=20.00
App.ActiveDocument.C432.Angle=360.00 
App.ActiveDocument.C432.Placement=Base.Placement(Base.Vector(39.947199,146.203473,60.963400),Base.Rotation(0.192735,0.548251,0.000000,0.813802))
App.ActiveDocument.addObject("Part::Cylinder","C433")
App.ActiveDocument.C433.Radius=0.627413
App.ActiveDocument.C433.Height=20.00
App.ActiveDocument.C433.Angle=360.00 
App.ActiveDocument.C433.Placement=Base.Placement(Base.Vector(38.399416,142.388477,61.103581),Base.Rotation(0.236305,0.562461,0.000000,0.792337))
App.ActiveDocument.addObject("Part::Cylinder","C434")
App.ActiveDocument.C434.Radius=0.627390
App.ActiveDocument.C434.Height=20.00
App.ActiveDocument.C434.Angle=360.00 
App.ActiveDocument.C434.Placement=Base.Placement(Base.Vector(36.931458,139.167624,60.880118),Base.Rotation(0.310505,0.563827,0.000000,0.765301))
App.ActiveDocument.addObject("Part::Cylinder","C435")
App.ActiveDocument.C435.Radius=0.629620
App.ActiveDocument.C435.Height=20.00
App.ActiveDocument.C435.Angle=360.00 
App.ActiveDocument.C435.Placement=Base.Placement(Base.Vector(41.700518,140.331685,57.947611),Base.Rotation(0.555605,0.045234,0.000000,0.830215))
App.ActiveDocument.addObject("Part::Cylinder","C436")
App.ActiveDocument.C436.Radius=0.630852
App.ActiveDocument.C436.Height=20.00
App.ActiveDocument.C436.Angle=360.00 
App.ActiveDocument.C436.Placement=Base.Placement(Base.Vector(38.039951,139.300836,55.621261),Base.Rotation(0.547130,-0.000000,0.000000,0.837048))
App.ActiveDocument.addObject("Part::Cylinder","C437")
App.ActiveDocument.C437.Radius=0.630320
App.ActiveDocument.C437.Height=20.00
App.ActiveDocument.C437.Angle=360.00 
App.ActiveDocument.C437.Placement=Base.Placement(Base.Vector(33.800792,138.075820,52.825204),Base.Rotation(0.547130,-0.000000,0.000000,0.837048))
App.ActiveDocument.addObject("Part::Cylinder","C438")
App.ActiveDocument.C438.Radius=0.689913
App.ActiveDocument.C438.Height=20.00
App.ActiveDocument.C438.Angle=360.00 
App.ActiveDocument.C438.Placement=Base.Placement(Base.Vector(4.198856,193.164583,61.228890),Base.Rotation(-0.468866,0.064637,0.000000,0.880901))
App.ActiveDocument.addObject("Part::Cylinder","C439")
App.ActiveDocument.C439.Radius=0.685897
App.ActiveDocument.C439.Height=20.00
App.ActiveDocument.C439.Angle=360.00 
App.ActiveDocument.C439.Placement=Base.Placement(Base.Vector(8.164763,191.727754,62.315940),Base.Rotation(-0.462865,0.109651,0.000000,0.879621))
App.ActiveDocument.addObject("Part::Cylinder","C440")
App.ActiveDocument.C440.Radius=0.679594
App.ActiveDocument.C440.Height=20.00
App.ActiveDocument.C440.Angle=360.00 
App.ActiveDocument.C440.Placement=Base.Placement(Base.Vector(11.915202,190.644483,62.316387),Base.Rotation(-0.452838,0.159169,0.000000,0.877270))
App.ActiveDocument.addObject("Part::Cylinder","C441")
App.ActiveDocument.C441.Radius=0.674389
App.ActiveDocument.C441.Height=20.00
App.ActiveDocument.C441.Angle=360.00 
App.ActiveDocument.C441.Placement=Base.Placement(Base.Vector(15.796332,188.897586,62.617666),Base.Rotation(-0.442335,0.188569,0.000000,0.876802))
App.ActiveDocument.addObject("Part::Cylinder","C442")
App.ActiveDocument.C442.Radius=0.667860
App.ActiveDocument.C442.Height=20.00
App.ActiveDocument.C442.Angle=360.00 
App.ActiveDocument.C442.Placement=Base.Placement(Base.Vector(19.708909,187.218867,62.359385),Base.Rotation(-0.426758,0.221577,0.000000,0.876802))
App.ActiveDocument.addObject("Part::Cylinder","C443")
App.ActiveDocument.C443.Radius=0.662572
App.ActiveDocument.C443.Height=20.00
App.ActiveDocument.C443.Angle=360.00 
App.ActiveDocument.C443.Placement=Base.Placement(Base.Vector(23.240512,185.050021,62.557302),Base.Rotation(-0.408270,0.260481,0.000000,0.874909))
App.ActiveDocument.addObject("Part::Cylinder","C444")
App.ActiveDocument.C444.Radius=0.657544
App.ActiveDocument.C444.Height=20.00
App.ActiveDocument.C444.Angle=360.00 
App.ActiveDocument.C444.Placement=Base.Placement(Base.Vector(26.396571,182.679574,62.729193),Base.Rotation(-0.385680,0.302856,0.000000,0.871510))
App.ActiveDocument.addObject("Part::Cylinder","C445")
App.ActiveDocument.C445.Radius=0.652336
App.ActiveDocument.C445.Height=20.00
App.ActiveDocument.C445.Angle=360.00 
App.ActiveDocument.C445.Placement=Base.Placement(Base.Vector(29.352441,180.116331,62.743606),Base.Rotation(-0.360204,0.345428,0.000000,0.866564))
App.ActiveDocument.addObject("Part::Cylinder","C446")
App.ActiveDocument.C446.Radius=0.648584
App.ActiveDocument.C446.Height=20.00
App.ActiveDocument.C446.Angle=360.00 
App.ActiveDocument.C446.Placement=Base.Placement(Base.Vector(31.786250,177.258492,63.007600),Base.Rotation(-0.316080,0.389374,0.000000,0.865148))
App.ActiveDocument.addObject("Part::Cylinder","C447")
App.ActiveDocument.C447.Radius=0.645833
App.ActiveDocument.C447.Height=20.00
App.ActiveDocument.C447.Angle=360.00 
App.ActiveDocument.C447.Placement=Base.Placement(Base.Vector(33.753342,174.199722,63.312254),Base.Rotation(-0.268094,0.424219,0.000000,0.864965))
App.ActiveDocument.addObject("Part::Cylinder","C448")
App.ActiveDocument.C448.Radius=0.642052
App.ActiveDocument.C448.Height=20.00
App.ActiveDocument.C448.Angle=360.00 
App.ActiveDocument.C448.Placement=Base.Placement(Base.Vector(35.611432,171.115655,63.062834),Base.Rotation(-0.219276,0.453897,0.000000,0.863652))
App.ActiveDocument.addObject("Part::Cylinder","C449")
App.ActiveDocument.C449.Radius=0.639745
App.ActiveDocument.C449.Height=20.00
App.ActiveDocument.C449.Angle=360.00 
App.ActiveDocument.C449.Placement=Base.Placement(Base.Vector(36.996046,167.972312,62.872967),Base.Rotation(-0.160560,0.469251,0.000000,0.868346))
App.ActiveDocument.addObject("Part::Cylinder","C450")
App.ActiveDocument.C450.Radius=0.638610
App.ActiveDocument.C450.Height=20.00
App.ActiveDocument.C450.Angle=360.00 
App.ActiveDocument.C450.Placement=Base.Placement(Base.Vector(38.200883,163.825125,62.994464),Base.Rotation(-0.134190,0.470815,0.000000,0.871967))
App.ActiveDocument.addObject("Part::Cylinder","C451")
App.ActiveDocument.C451.Radius=0.638546
App.ActiveDocument.C451.Height=20.00
App.ActiveDocument.C451.Angle=360.00 
App.ActiveDocument.C451.Placement=Base.Placement(Base.Vector(39.122108,159.619775,63.363234),Base.Rotation(-0.126303,0.466130,0.000000,0.875654))
App.ActiveDocument.addObject("Part::Cylinder","C452")
App.ActiveDocument.C452.Radius=0.637100
App.ActiveDocument.C452.Height=20.00
App.ActiveDocument.C452.Angle=360.00 
App.ActiveDocument.C452.Placement=Base.Placement(Base.Vector(39.816339,155.862646,63.732143),Base.Rotation(-0.091139,0.493864,0.000000,0.864750))
App.ActiveDocument.addObject("Part::Cylinder","C453")
App.ActiveDocument.C453.Radius=0.637025
App.ActiveDocument.C453.Height=20.00
App.ActiveDocument.C453.Angle=360.00 
App.ActiveDocument.C453.Placement=Base.Placement(Base.Vector(39.777115,152.930537,64.323358),Base.Rotation(-0.006962,0.522857,0.000000,0.852392))
App.ActiveDocument.addObject("Part::Cylinder","C454")
App.ActiveDocument.C454.Radius=0.637061
App.ActiveDocument.C454.Height=20.00
App.ActiveDocument.C454.Angle=360.00 
App.ActiveDocument.C454.Placement=Base.Placement(Base.Vector(39.430524,149.979286,64.648193),Base.Rotation(0.077413,0.538220,0.000000,0.839241))
App.ActiveDocument.addObject("Part::Cylinder","C455")
App.ActiveDocument.C455.Radius=0.639250
App.ActiveDocument.C455.Height=20.00
App.ActiveDocument.C455.Angle=360.00 
App.ActiveDocument.C455.Placement=Base.Placement(Base.Vector(38.207024,146.498434,65.633726),Base.Rotation(0.138275,0.557046,0.000000,0.818889))
App.ActiveDocument.addObject("Part::Cylinder","C456")
App.ActiveDocument.C456.Radius=0.640060
App.ActiveDocument.C456.Height=20.00
App.ActiveDocument.C456.Angle=360.00 
App.ActiveDocument.C456.Placement=Base.Placement(Base.Vector(36.840221,142.413187,66.727794),Base.Rotation(0.146355,0.611444,0.000000,0.777635))
App.ActiveDocument.addObject("Part::Cylinder","C457")
App.ActiveDocument.C457.Radius=0.639523
App.ActiveDocument.C457.Height=20.00
App.ActiveDocument.C457.Angle=360.00 
App.ActiveDocument.C457.Placement=Base.Placement(Base.Vector(38.721633,142.744532,65.352842),Base.Rotation(0.447699,0.413151,0.000000,0.793015))
App.ActiveDocument.addObject("Part::Cylinder","C458")
App.ActiveDocument.C458.Radius=0.640736
App.ActiveDocument.C458.Height=20.00
App.ActiveDocument.C458.Angle=360.00 
App.ActiveDocument.C458.Placement=Base.Placement(Base.Vector(41.804933,142.348563,62.587338),Base.Rotation(0.548843,0.016522,0.000000,0.835762))
App.ActiveDocument.addObject("Part::Cylinder","C459")
App.ActiveDocument.C459.Radius=0.642071
App.ActiveDocument.C459.Height=20.00
App.ActiveDocument.C459.Angle=360.00 
App.ActiveDocument.C459.Placement=Base.Placement(Base.Vector(37.875550,141.489313,60.616382),Base.Rotation(0.547130,-0.000000,0.000000,0.837048))
App.ActiveDocument.addObject("Part::Cylinder","C460")
App.ActiveDocument.C460.Radius=0.642838
App.ActiveDocument.C460.Height=20.00
App.ActiveDocument.C460.Angle=360.00 
App.ActiveDocument.C460.Placement=Base.Placement(Base.Vector(33.750941,140.552992,58.479263),Base.Rotation(0.547130,-0.000000,0.000000,0.837048))
App.ActiveDocument.addObject("Part::Cylinder","C461")
App.ActiveDocument.C461.Radius=0.641561
App.ActiveDocument.C461.Height=20.00
App.ActiveDocument.C461.Angle=360.00 
App.ActiveDocument.C461.Placement=Base.Placement(Base.Vector(29.834758,139.265151,55.539810),Base.Rotation(0.547130,-0.000000,0.000000,0.837048))
App.ActiveDocument.addObject("Part::Cylinder","C462")
App.ActiveDocument.C462.Radius=0.699782
App.ActiveDocument.C462.Height=20.00
App.ActiveDocument.C462.Angle=360.00 
App.ActiveDocument.C462.Placement=Base.Placement(Base.Vector(4.205290,190.434621,65.074948),Base.Rotation(-0.441075,0.053621,0.000000,0.895867))
App.ActiveDocument.addObject("Part::Cylinder","C463")
App.ActiveDocument.C463.Radius=0.695434
App.ActiveDocument.C463.Height=20.00
App.ActiveDocument.C463.Angle=360.00 
App.ActiveDocument.C463.Placement=Base.Placement(Base.Vector(8.181713,189.080860,66.013649),Base.Rotation(-0.436841,0.096609,0.000000,0.894336))
App.ActiveDocument.addObject("Part::Cylinder","C464")
App.ActiveDocument.C464.Radius=0.689085
App.ActiveDocument.C464.Height=20.00
App.ActiveDocument.C464.Angle=360.00 
App.ActiveDocument.C464.Placement=Base.Placement(Base.Vector(11.882397,187.922734,66.102306),Base.Rotation(-0.430382,0.151382,0.000000,0.889862))
App.ActiveDocument.addObject("Part::Cylinder","C465")
App.ActiveDocument.C465.Radius=0.683485
App.ActiveDocument.C465.Height=20.00
App.ActiveDocument.C465.Angle=360.00 
App.ActiveDocument.C465.Placement=Base.Placement(Base.Vector(15.824966,186.120496,66.343398),Base.Rotation(-0.413697,0.190630,0.000000,0.890233))
App.ActiveDocument.addObject("Part::Cylinder","C466")
App.ActiveDocument.C466.Radius=0.677276
App.ActiveDocument.C466.Height=20.00
App.ActiveDocument.C466.Angle=360.00 
App.ActiveDocument.C466.Placement=Base.Placement(Base.Vector(19.681477,184.373966,66.123292),Base.Rotation(-0.399346,0.217526,0.000000,0.890621))
App.ActiveDocument.addObject("Part::Cylinder","C467")
App.ActiveDocument.C467.Radius=0.672299
App.ActiveDocument.C467.Height=20.00
App.ActiveDocument.C467.Angle=360.00 
App.ActiveDocument.C467.Placement=Base.Placement(Base.Vector(23.045807,182.225192,66.274700),Base.Rotation(-0.380309,0.251481,0.000000,0.890013))
App.ActiveDocument.addObject("Part::Cylinder","C468")
App.ActiveDocument.C468.Radius=0.667199
App.ActiveDocument.C468.Height=20.00
App.ActiveDocument.C468.Angle=360.00 
App.ActiveDocument.C468.Placement=Base.Placement(Base.Vector(26.267288,179.718028,66.424600),Base.Rotation(-0.356861,0.292212,0.000000,0.887278))
App.ActiveDocument.addObject("Part::Cylinder","C469")
App.ActiveDocument.C469.Radius=0.662272
App.ActiveDocument.C469.Height=20.00
App.ActiveDocument.C469.Angle=360.00 
App.ActiveDocument.C469.Placement=Base.Placement(Base.Vector(29.001962,177.217531,66.428553),Base.Rotation(-0.322419,0.338338,0.000000,0.884066))
App.ActiveDocument.addObject("Part::Cylinder","C470")
App.ActiveDocument.C470.Radius=0.659444
App.ActiveDocument.C470.Height=20.00
App.ActiveDocument.C470.Angle=360.00 
App.ActiveDocument.C470.Placement=Base.Placement(Base.Vector(30.987584,174.468686,66.842807),Base.Rotation(-0.276557,0.380639,0.000000,0.882400))
App.ActiveDocument.addObject("Part::Cylinder","C471")
App.ActiveDocument.C471.Radius=0.656077
App.ActiveDocument.C471.Height=20.00
App.ActiveDocument.C471.Angle=360.00 
App.ActiveDocument.C471.Placement=Base.Placement(Base.Vector(32.879598,171.607272,66.737710),Base.Rotation(-0.217174,0.413080,0.000000,0.884421))
App.ActiveDocument.addObject("Part::Cylinder","C472")
App.ActiveDocument.C472.Radius=0.653372
App.ActiveDocument.C472.Height=20.00
App.ActiveDocument.C472.Angle=360.00 
App.ActiveDocument.C472.Placement=Base.Placement(Base.Vector(34.347949,168.623832,66.463588),Base.Rotation(-0.148572,0.432911,0.000000,0.889109))
App.ActiveDocument.addObject("Part::Cylinder","C473")
App.ActiveDocument.C473.Radius=0.651712
App.ActiveDocument.C473.Height=20.00
App.ActiveDocument.C473.Angle=360.00 
App.ActiveDocument.C473.Placement=Base.Placement(Base.Vector(35.574112,164.951101,66.228220),Base.Rotation(-0.115481,0.430130,0.000000,0.895350))
App.ActiveDocument.addObject("Part::Cylinder","C474")
App.ActiveDocument.C474.Radius=0.652016
App.ActiveDocument.C474.Height=20.00
App.ActiveDocument.C474.Angle=360.00 
App.ActiveDocument.C474.Placement=Base.Placement(Base.Vector(36.485748,160.884463,66.388776),Base.Rotation(-0.111304,0.409939,0.000000,0.905296))
App.ActiveDocument.addObject("Part::Cylinder","C475")
App.ActiveDocument.C475.Radius=0.650617
App.ActiveDocument.C475.Height=20.00
App.ActiveDocument.C475.Angle=360.00 
App.ActiveDocument.C475.Placement=Base.Placement(Base.Vector(37.773659,156.168735,66.568427),Base.Rotation(-0.128045,0.408727,0.000000,0.903630))
App.ActiveDocument.addObject("Part::Cylinder","C476")
App.ActiveDocument.C476.Radius=0.649636
App.ActiveDocument.C476.Height=20.00
App.ActiveDocument.C476.Angle=360.00 
App.ActiveDocument.C476.Placement=Base.Placement(Base.Vector(38.078637,153.003548,67.185294),Base.Rotation(-0.069826,0.450878,0.000000,0.889850))
App.ActiveDocument.addObject("Part::Cylinder","C477")
App.ActiveDocument.C477.Radius=0.650267
App.ActiveDocument.C477.Height=20.00
App.ActiveDocument.C477.Angle=360.00 
App.ActiveDocument.C477.Placement=Base.Placement(Base.Vector(37.603751,150.003791,68.311457),Base.Rotation(0.011355,0.496426,0.000000,0.868005))
App.ActiveDocument.addObject("Part::Cylinder","C478")
App.ActiveDocument.C478.Radius=0.651451
App.ActiveDocument.C478.Height=20.00
App.ActiveDocument.C478.Angle=360.00 
App.ActiveDocument.C478.Placement=Base.Placement(Base.Vector(36.676210,146.332175,69.547126),Base.Rotation(0.030722,0.542053,0.000000,0.839783))
App.ActiveDocument.addObject("Part::Cylinder","C479")
App.ActiveDocument.C479.Radius=0.652413
App.ActiveDocument.C479.Height=20.00
App.ActiveDocument.C479.Angle=360.00 
App.ActiveDocument.C479.Placement=Base.Placement(Base.Vector(35.967119,140.434487,71.836178),Base.Rotation(-0.059497,0.621988,0.000000,0.780763))
App.ActiveDocument.addObject("Part::Cylinder","C480")
App.ActiveDocument.C480.Radius=0.651320
App.ActiveDocument.C480.Height=20.00
App.ActiveDocument.C480.Angle=360.00 
App.ActiveDocument.C480.Placement=Base.Placement(Base.Vector(40.138735,144.324574,69.584211),Base.Rotation(0.474262,0.304854,0.000000,0.825917))
App.ActiveDocument.addObject("Part::Cylinder","C481")
App.ActiveDocument.C481.Radius=0.708478
App.ActiveDocument.C481.Height=20.00
App.ActiveDocument.C481.Angle=360.00 
App.ActiveDocument.C481.Placement=Base.Placement(Base.Vector(4.401265,187.629459,68.487370),Base.Rotation(-0.409781,0.043437,0.000000,0.911149))
App.ActiveDocument.addObject("Part::Cylinder","C482")
App.ActiveDocument.C482.Radius=0.703943
App.ActiveDocument.C482.Height=20.00
App.ActiveDocument.C482.Angle=360.00 
App.ActiveDocument.C482.Placement=Base.Placement(Base.Vector(8.386182,186.353620,69.276689),Base.Rotation(-0.405456,0.081900,0.000000,0.910438))
App.ActiveDocument.addObject("Part::Cylinder","C483")
App.ActiveDocument.C483.Radius=0.697972
App.ActiveDocument.C483.Height=20.00
App.ActiveDocument.C483.Angle=360.00 
App.ActiveDocument.C483.Placement=Base.Placement(Base.Vector(11.974029,185.051819,69.505896),Base.Rotation(-0.391030,0.146971,0.000000,0.908568))
App.ActiveDocument.addObject("Part::Cylinder","C484")
App.ActiveDocument.C484.Radius=0.692716
App.ActiveDocument.C484.Height=20.00
App.ActiveDocument.C484.Angle=360.00 
App.ActiveDocument.C484.Placement=Base.Placement(Base.Vector(15.840317,183.189286,69.726009),Base.Rotation(-0.371946,0.179243,0.000000,0.910784))
App.ActiveDocument.addObject("Part::Cylinder","C485")
App.ActiveDocument.C485.Radius=0.686447
App.ActiveDocument.C485.Height=20.00
App.ActiveDocument.C485.Angle=360.00 
App.ActiveDocument.C485.Placement=Base.Placement(Base.Vector(19.551742,181.363634,69.572655),Base.Rotation(-0.361214,0.212280,0.000000,0.907999))
App.ActiveDocument.addObject("Part::Cylinder","C486")
App.ActiveDocument.C486.Radius=0.681141
App.ActiveDocument.C486.Height=20.00
App.ActiveDocument.C486.Angle=360.00 
App.ActiveDocument.C486.Placement=Base.Placement(Base.Vector(23.002938,179.118866,69.605060),Base.Rotation(-0.347325,0.240474,0.000000,0.906387))
App.ActiveDocument.addObject("Part::Cylinder","C487")
App.ActiveDocument.C487.Radius=0.676602
App.ActiveDocument.C487.Height=20.00
App.ActiveDocument.C487.Angle=360.00 
App.ActiveDocument.C487.Placement=Base.Placement(Base.Vector(25.978024,176.567807,69.814274),Base.Rotation(-0.318411,0.281045,0.000000,0.905333))
App.ActiveDocument.addObject("Part::Cylinder","C488")
App.ActiveDocument.C488.Radius=0.672508
App.ActiveDocument.C488.Height=20.00
App.ActiveDocument.C488.Angle=360.00 
App.ActiveDocument.C488.Placement=Base.Placement(Base.Vector(28.395501,174.032607,69.941672),Base.Rotation(-0.273216,0.327304,0.000000,0.904558))
App.ActiveDocument.addObject("Part::Cylinder","C489")
App.ActiveDocument.C489.Radius=0.669681
App.ActiveDocument.C489.Height=20.00
App.ActiveDocument.C489.Angle=360.00 
App.ActiveDocument.C489.Placement=Base.Placement(Base.Vector(30.136265,171.607943,69.963166),Base.Rotation(-0.202236,0.364154,0.000000,0.909116))
App.ActiveDocument.addObject("Part::Cylinder","C490")
App.ActiveDocument.C490.Radius=0.666911
App.ActiveDocument.C490.Height=20.00
App.ActiveDocument.C490.Angle=360.00 
App.ActiveDocument.C490.Placement=Base.Placement(Base.Vector(31.547595,168.793557,69.723796),Base.Rotation(-0.138579,0.386868,0.000000,0.911663))
App.ActiveDocument.addObject("Part::Cylinder","C491")
App.ActiveDocument.C491.Radius=0.665473
App.ActiveDocument.C491.Height=20.00
App.ActiveDocument.C491.Angle=360.00 
App.ActiveDocument.C491.Placement=Base.Placement(Base.Vector(32.620020,165.626322,69.439755),Base.Rotation(-0.082693,0.384379,0.000000,0.919464))
App.ActiveDocument.addObject("Part::Cylinder","C492")
App.ActiveDocument.C492.Radius=0.664700
App.ActiveDocument.C492.Height=20.00
App.ActiveDocument.C492.Angle=360.00 
App.ActiveDocument.C492.Placement=Base.Placement(Base.Vector(33.482299,162.136833,69.231486),Base.Rotation(-0.069036,0.370388,0.000000,0.926308))
App.ActiveDocument.addObject("Part::Cylinder","C493")
App.ActiveDocument.C493.Radius=0.664101
App.ActiveDocument.C493.Height=20.00
App.ActiveDocument.C493.Angle=360.00 
App.ActiveDocument.C493.Placement=Base.Placement(Base.Vector(34.596127,157.368285,69.243199),Base.Rotation(-0.108757,0.348965,0.000000,0.930804))
App.ActiveDocument.addObject("Part::Cylinder","C494")
App.ActiveDocument.C494.Radius=0.663077
App.ActiveDocument.C494.Height=20.00
App.ActiveDocument.C494.Angle=360.00 
App.ActiveDocument.C494.Placement=Base.Placement(Base.Vector(35.890544,152.935140,69.448718),Base.Rotation(-0.114639,0.343315,0.000000,0.932198))
App.ActiveDocument.addObject("Part::Cylinder","C495")
App.ActiveDocument.C495.Radius=0.662684
App.ActiveDocument.C495.Height=20.00
App.ActiveDocument.C495.Angle=360.00 
App.ActiveDocument.C495.Placement=Base.Placement(Base.Vector(36.001411,149.179668,70.451874),Base.Rotation(-0.075127,0.395007,0.000000,0.915601))
App.ActiveDocument.addObject("Part::Cylinder","C496")
App.ActiveDocument.C496.Radius=0.664597
App.ActiveDocument.C496.Height=20.00
App.ActiveDocument.C496.Angle=360.00 
App.ActiveDocument.C496.Placement=Base.Placement(Base.Vector(35.356939,145.646631,71.785841),Base.Rotation(-0.064428,0.429921,0.000000,0.900565))
App.ActiveDocument.addObject("Part::Cylinder","C497")
App.ActiveDocument.C497.Radius=0.664490
App.ActiveDocument.C497.Height=20.00
App.ActiveDocument.C497.Angle=360.00 
App.ActiveDocument.C497.Placement=Base.Placement(Base.Vector(35.554273,140.350226,73.129229),Base.Rotation(-0.124115,0.471629,0.000000,0.873019))
App.ActiveDocument.addObject("Part::Cylinder","C498")
App.ActiveDocument.C498.Radius=0.663975
App.ActiveDocument.C498.Height=20.00
App.ActiveDocument.C498.Angle=360.00 
App.ActiveDocument.C498.Placement=Base.Placement(Base.Vector(38.845832,145.057885,71.788449),Base.Rotation(0.380978,0.239525,0.000000,0.893019))
App.ActiveDocument.addObject("Part::Cylinder","C499")
App.ActiveDocument.C499.Radius=0.716200
App.ActiveDocument.C499.Height=20.00
App.ActiveDocument.C499.Angle=360.00 
App.ActiveDocument.C499.Placement=Base.Placement(Base.Vector(4.591822,184.856024,71.302724),Base.Rotation(-0.367918,0.030493,0.000000,0.929358))
App.ActiveDocument.addObject("Part::Cylinder","C500")
App.ActiveDocument.C500.Radius=0.712078
App.ActiveDocument.C500.Height=20.00
App.ActiveDocument.C500.Angle=360.00 
App.ActiveDocument.C500.Placement=Base.Placement(Base.Vector(8.489488,183.437706,72.184698),Base.Rotation(-0.357832,0.071991,0.000000,0.931007))
App.ActiveDocument.addObject("Part::Cylinder","C501")
App.ActiveDocument.C501.Radius=0.706241
App.ActiveDocument.C501.Height=20.00
App.ActiveDocument.C501.Angle=360.00 
App.ActiveDocument.C501.Placement=Base.Placement(Base.Vector(12.051061,181.954134,72.523715),Base.Rotation(-0.339525,0.142951,0.000000,0.929671))
App.ActiveDocument.addObject("Part::Cylinder","C502")
App.ActiveDocument.C502.Radius=0.701279
App.ActiveDocument.C502.Height=20.00
App.ActiveDocument.C502.Angle=360.00 
App.ActiveDocument.C502.Placement=Base.Placement(Base.Vector(15.887938,179.980843,72.707485),Base.Rotation(-0.322749,0.162714,0.000000,0.932393))
App.ActiveDocument.addObject("Part::Cylinder","C503")
App.ActiveDocument.C503.Radius=0.694664
App.ActiveDocument.C503.Height=20.00
App.ActiveDocument.C503.Angle=360.00 
App.ActiveDocument.C503.Placement=Base.Placement(Base.Vector(19.740727,177.936982,72.591330),Base.Rotation(-0.319931,0.196138,0.000000,0.926917))
App.ActiveDocument.addObject("Part::Cylinder","C504")
App.ActiveDocument.C504.Radius=0.689810
App.ActiveDocument.C504.Height=20.00
App.ActiveDocument.C504.Angle=360.00 
App.ActiveDocument.C504.Placement=Base.Placement(Base.Vector(23.002457,175.521423,72.762964),Base.Rotation(-0.302723,0.228136,0.000000,0.925372))
App.ActiveDocument.addObject("Part::Cylinder","C505")
App.ActiveDocument.C505.Radius=0.685759
App.ActiveDocument.C505.Height=20.00
App.ActiveDocument.C505.Angle=360.00 
App.ActiveDocument.C505.Placement=Base.Placement(Base.Vector(25.346799,173.423593,72.821975),Base.Rotation(-0.260938,0.273239,0.000000,0.925879))
App.ActiveDocument.addObject("Part::Cylinder","C506")
App.ActiveDocument.C506.Radius=0.682702
App.ActiveDocument.C506.Height=20.00
App.ActiveDocument.C506.Angle=360.00 
App.ActiveDocument.C506.Placement=Base.Placement(Base.Vector(27.168500,171.148942,72.833452),Base.Rotation(-0.186615,0.314658,0.000000,0.930680))
App.ActiveDocument.addObject("Part::Cylinder","C507")
App.ActiveDocument.C507.Radius=0.679938
App.ActiveDocument.C507.Height=20.00
App.ActiveDocument.C507.Angle=360.00 
App.ActiveDocument.C507.Placement=Base.Placement(Base.Vector(28.606108,168.636361,72.501401),Base.Rotation(-0.111657,0.334629,0.000000,0.935711))
App.ActiveDocument.addObject("Part::Cylinder","C508")
App.ActiveDocument.C508.Radius=0.678225
App.ActiveDocument.C508.Height=20.00
App.ActiveDocument.C508.Angle=360.00 
App.ActiveDocument.C508.Placement=Base.Placement(Base.Vector(29.598689,165.640564,72.274917),Base.Rotation(-0.061303,0.339291,0.000000,0.938682))
App.ActiveDocument.addObject("Part::Cylinder","C509")
App.ActiveDocument.C509.Radius=0.677066
App.ActiveDocument.C509.Height=20.00
App.ActiveDocument.C509.Angle=360.00 
App.ActiveDocument.C509.Placement=Base.Placement(Base.Vector(30.274271,162.435112,72.054571),Base.Rotation(-0.039605,0.336651,0.000000,0.940796))
App.ActiveDocument.addObject("Part::Cylinder","C510")
App.ActiveDocument.C510.Radius=0.676869
App.ActiveDocument.C510.Height=20.00
App.ActiveDocument.C510.Angle=360.00 
App.ActiveDocument.C510.Placement=Base.Placement(Base.Vector(31.123659,157.879223,71.880282),Base.Rotation(-0.065148,0.308573,0.000000,0.948967))
App.ActiveDocument.addObject("Part::Cylinder","C511")
App.ActiveDocument.C511.Radius=0.675426
App.ActiveDocument.C511.Height=20.00
App.ActiveDocument.C511.Angle=360.00 
App.ActiveDocument.C511.Placement=Base.Placement(Base.Vector(32.755633,152.701651,71.841602),Base.Rotation(-0.117089,0.284309,0.000000,0.951556))
App.ActiveDocument.addObject("Part::Cylinder","C512")
App.ActiveDocument.C512.Radius=0.675332
App.ActiveDocument.C512.Height=20.00
App.ActiveDocument.C512.Angle=360.00 
App.ActiveDocument.C512.Placement=Base.Placement(Base.Vector(33.615035,148.310066,72.684763),Base.Rotation(-0.129084,0.298603,0.000000,0.945607))
App.ActiveDocument.addObject("Part::Cylinder","C513")
App.ActiveDocument.C513.Radius=0.677120
App.ActiveDocument.C513.Height=20.00
App.ActiveDocument.C513.Angle=360.00 
App.ActiveDocument.C513.Placement=Base.Placement(Base.Vector(33.552165,144.382965,73.714180),Base.Rotation(-0.084053,0.317652,0.000000,0.944475))
App.ActiveDocument.addObject("Part::Cylinder","C514")
App.ActiveDocument.C514.Radius=0.677088
App.ActiveDocument.C514.Height=20.00
App.ActiveDocument.C514.Angle=360.00 
App.ActiveDocument.C514.Placement=Base.Placement(Base.Vector(37.382902,147.216572,74.613343),Base.Rotation(0.356961,0.132750,0.000000,0.924638))
App.ActiveDocument.addObject("Part::Cylinder","C515")
App.ActiveDocument.C515.Radius=0.723641
App.ActiveDocument.C515.Height=20.00
App.ActiveDocument.C515.Angle=360.00 
App.ActiveDocument.C515.Placement=Base.Placement(Base.Vector(4.860321,181.746949,73.849833),Base.Rotation(-0.310955,0.011963,0.000000,0.950349))
App.ActiveDocument.addObject("Part::Cylinder","C516")
App.ActiveDocument.C516.Radius=0.719675
App.ActiveDocument.C516.Height=20.00
App.ActiveDocument.C516.Angle=360.00 
App.ActiveDocument.C516.Placement=Base.Placement(Base.Vector(8.589464,180.090516,74.882134),Base.Rotation(-0.305415,0.062543,0.000000,0.950163))
App.ActiveDocument.addObject("Part::Cylinder","C517")
App.ActiveDocument.C517.Radius=0.714029
App.ActiveDocument.C517.Height=20.00
App.ActiveDocument.C517.Angle=360.00 
App.ActiveDocument.C517.Placement=Base.Placement(Base.Vector(11.905979,178.555625,75.252680),Base.Rotation(-0.298630,0.129567,0.000000,0.945533))
App.ActiveDocument.addObject("Part::Cylinder","C518")
App.ActiveDocument.C518.Radius=0.708860
App.ActiveDocument.C518.Height=20.00
App.ActiveDocument.C518.Angle=360.00 
App.ActiveDocument.C518.Placement=Base.Placement(Base.Vector(15.776732,176.773362,75.208567),Base.Rotation(-0.265879,0.148915,0.000000,0.952435))
App.ActiveDocument.addObject("Part::Cylinder","C519")
App.ActiveDocument.C519.Radius=0.703762
App.ActiveDocument.C519.Height=20.00
App.ActiveDocument.C519.Angle=360.00 
App.ActiveDocument.C519.Placement=Base.Placement(Base.Vector(19.584254,174.557461,75.237351),Base.Rotation(-0.257944,0.156358,0.000000,0.953424))
App.ActiveDocument.addObject("Part::Cylinder","C520")
App.ActiveDocument.C520.Radius=0.698621
App.ActiveDocument.C520.Height=20.00
App.ActiveDocument.C520.Angle=360.00 
App.ActiveDocument.C520.Placement=Base.Placement(Base.Vector(22.444324,172.621598,75.092852),Base.Rotation(-0.213986,0.203278,0.000000,0.955452))
App.ActiveDocument.addObject("Part::Cylinder","C521")
App.ActiveDocument.C521.Radius=0.694944
App.ActiveDocument.C521.Height=20.00
App.ActiveDocument.C521.Angle=360.00 
App.ActiveDocument.C521.Placement=Base.Placement(Base.Vector(24.260993,170.687530,74.919240),Base.Rotation(-0.150962,0.245028,0.000000,0.957691))
App.ActiveDocument.addObject("Part::Cylinder","C522")
App.ActiveDocument.C522.Radius=0.691831
App.ActiveDocument.C522.Height=20.00
App.ActiveDocument.C522.Angle=360.00 
App.ActiveDocument.C522.Placement=Base.Placement(Base.Vector(25.750399,167.963926,74.689229),Base.Rotation(-0.082508,0.272565,0.000000,0.958593))
App.ActiveDocument.addObject("Part::Cylinder","C523")
App.ActiveDocument.C523.Radius=0.690386
App.ActiveDocument.C523.Height=20.00
App.ActiveDocument.C523.Angle=360.00 
App.ActiveDocument.C523.Placement=Base.Placement(Base.Vector(26.513670,165.200756,74.619285),Base.Rotation(-0.045324,0.282387,0.000000,0.958229))
App.ActiveDocument.addObject("Part::Cylinder","C524")
App.ActiveDocument.C524.Radius=0.688933
App.ActiveDocument.C524.Height=20.00
App.ActiveDocument.C524.Angle=360.00 
App.ActiveDocument.C524.Placement=Base.Placement(Base.Vector(27.223813,160.851979,74.358014),Base.Rotation(-0.014922,0.282561,0.000000,0.959133))
App.ActiveDocument.addObject("Part::Cylinder","C525")
App.ActiveDocument.C525.Radius=0.688731
App.ActiveDocument.C525.Height=20.00
App.ActiveDocument.C525.Angle=360.00 
App.ActiveDocument.C525.Placement=Base.Placement(Base.Vector(27.989426,155.098116,74.311255),Base.Rotation(-0.067056,0.259575,0.000000,0.963392))
App.ActiveDocument.addObject("Part::Cylinder","C526")
App.ActiveDocument.C526.Radius=0.686903
App.ActiveDocument.C526.Height=20.00
App.ActiveDocument.C526.Angle=360.00 
App.ActiveDocument.C526.Placement=Base.Placement(Base.Vector(29.872567,149.442665,74.530213),Base.Rotation(-0.131330,0.244213,0.000000,0.960787))
App.ActiveDocument.addObject("Part::Cylinder","C527")
App.ActiveDocument.C527.Radius=0.688635
App.ActiveDocument.C527.Height=20.00
App.ActiveDocument.C527.Angle=360.00 
App.ActiveDocument.C527.Placement=Base.Placement(Base.Vector(30.613289,145.995304,75.213670),Base.Rotation(-0.090895,0.225407,0.000000,0.970015))
App.ActiveDocument.addObject("Part::Cylinder","C528")
App.ActiveDocument.C528.Radius=0.688013
App.ActiveDocument.C528.Height=20.00
App.ActiveDocument.C528.Angle=360.00 
App.ActiveDocument.C528.Placement=Base.Placement(Base.Vector(31.514243,143.680435,75.108609),Base.Rotation(0.020249,0.214397,0.000000,0.976537))
App.ActiveDocument.addObject("Part::Cylinder","C529")
App.ActiveDocument.C529.Radius=0.729889
App.ActiveDocument.C529.Height=20.00
App.ActiveDocument.C529.Angle=360.00 
App.ActiveDocument.C529.Placement=Base.Placement(Base.Vector(5.384170,178.315467,76.120852),Base.Rotation(-0.252670,-0.007377,0.000000,0.967524))
App.ActiveDocument.addObject("Part::Cylinder","C530")
App.ActiveDocument.C530.Radius=0.726110
App.ActiveDocument.C530.Height=20.00
App.ActiveDocument.C530.Angle=360.00 
App.ActiveDocument.C530.Placement=Base.Placement(Base.Vector(8.962676,176.810023,76.967136),Base.Rotation(-0.243604,0.033310,0.000000,0.969303))
App.ActiveDocument.addObject("Part::Cylinder","C531")
App.ActiveDocument.C531.Radius=0.720704
App.ActiveDocument.C531.Height=20.00
App.ActiveDocument.C531.Angle=360.00 
App.ActiveDocument.C531.Placement=Base.Placement(Base.Vector(11.880365,175.252375,77.304347),Base.Rotation(-0.226920,0.114843,0.000000,0.967119))
App.ActiveDocument.addObject("Part::Cylinder","C532")
App.ActiveDocument.C532.Radius=0.715799
App.ActiveDocument.C532.Height=20.00
App.ActiveDocument.C532.Angle=360.00 
App.ActiveDocument.C532.Placement=Base.Placement(Base.Vector(15.234641,172.966342,77.503958),Base.Rotation(-0.229813,0.137904,0.000000,0.963415))
App.ActiveDocument.addObject("Part::Cylinder","C533")
App.ActiveDocument.C533.Radius=0.710198
App.ActiveDocument.C533.Height=20.00
App.ActiveDocument.C533.Angle=360.00 
App.ActiveDocument.C533.Placement=Base.Placement(Base.Vector(18.891145,171.603311,76.905697),Base.Rotation(-0.161975,0.152393,0.000000,0.974957))
App.ActiveDocument.addObject("Part::Cylinder","C534")
App.ActiveDocument.C534.Radius=0.706767
App.ActiveDocument.C534.Height=20.00
App.ActiveDocument.C534.Angle=360.00 
App.ActiveDocument.C534.Placement=Base.Placement(Base.Vector(21.073119,169.428109,76.723741),Base.Rotation(-0.108988,0.171050,0.000000,0.979216))
App.ActiveDocument.addObject("Part::Cylinder","C535")
App.ActiveDocument.C535.Radius=0.703070
App.ActiveDocument.C535.Height=20.00
App.ActiveDocument.C535.Angle=360.00 
App.ActiveDocument.C535.Placement=Base.Placement(Base.Vector(22.720122,166.863061,76.462846),Base.Rotation(-0.060241,0.201919,0.000000,0.977548))
App.ActiveDocument.addObject("Part::Cylinder","C536")
App.ActiveDocument.C536.Radius=0.700574
App.ActiveDocument.C536.Height=20.00
App.ActiveDocument.C536.Angle=360.00 
App.ActiveDocument.C536.Placement=Base.Placement(Base.Vector(23.675009,164.111815,76.283373),Base.Rotation(-0.028734,0.223762,0.000000,0.974220))
App.ActiveDocument.addObject("Part::Cylinder","C537")
App.ActiveDocument.C537.Radius=0.699913
App.ActiveDocument.C537.Height=20.00
App.ActiveDocument.C537.Angle=360.00 
App.ActiveDocument.C537.Placement=Base.Placement(Base.Vector(23.938590,160.833191,76.265592),Base.Rotation(-0.007873,0.230598,0.000000,0.973017))
App.ActiveDocument.addObject("Part::Cylinder","C538")
App.ActiveDocument.C538.Radius=0.700091
App.ActiveDocument.C538.Height=20.00
App.ActiveDocument.C538.Angle=360.00 
App.ActiveDocument.C538.Placement=Base.Placement(Base.Vector(24.052799,156.410768,76.311655),Base.Rotation(-0.033560,0.224490,0.000000,0.973898))
App.ActiveDocument.addObject("Part::Cylinder","C539")
App.ActiveDocument.C539.Radius=0.698664
App.ActiveDocument.C539.Height=20.00
App.ActiveDocument.C539.Angle=360.00 
App.ActiveDocument.C539.Placement=Base.Placement(Base.Vector(25.439137,150.684409,76.495716),Base.Rotation(-0.105797,0.214895,0.000000,0.970890))
App.ActiveDocument.addObject("Part::Cylinder","C540")
App.ActiveDocument.C540.Radius=0.699637
App.ActiveDocument.C540.Height=20.00
App.ActiveDocument.C540.Angle=360.00 
App.ActiveDocument.C540.Placement=Base.Placement(Base.Vector(26.108548,146.790280,77.187092),Base.Rotation(-0.100208,0.208158,0.000000,0.972948))
App.ActiveDocument.addObject("Part::Cylinder","C541")
App.ActiveDocument.C541.Radius=0.699081
App.ActiveDocument.C541.Height=20.00
App.ActiveDocument.C541.Angle=360.00 
App.ActiveDocument.C541.Placement=Base.Placement(Base.Vector(27.011148,144.500977,77.209375),Base.Rotation(0.006874,0.203955,0.000000,0.978956))
App.ActiveDocument.addObject("Part::Cylinder","C542")
App.ActiveDocument.C542.Radius=0.691579
App.ActiveDocument.C542.Height=20.00
App.ActiveDocument.C542.Angle=360.00 
App.ActiveDocument.C542.Placement=Base.Placement(Base.Vector(29.514407,146.522165,75.661101),Base.Rotation(0.317550,0.115189,0.000000,0.941219))
App.ActiveDocument.addObject("Part::Cylinder","C543")
App.ActiveDocument.C543.Radius=0.734870
App.ActiveDocument.C543.Height=20.00
App.ActiveDocument.C543.Angle=360.00 
App.ActiveDocument.C543.Placement=Base.Placement(Base.Vector(5.607286,175.046701,77.623728),Base.Rotation(-0.174388,-0.027371,0.000000,0.984297))
App.ActiveDocument.addObject("Part::Cylinder","C544")
App.ActiveDocument.C544.Radius=0.731020
App.ActiveDocument.C544.Height=20.00
App.ActiveDocument.C544.Angle=360.00 
App.ActiveDocument.C544.Placement=Base.Placement(Base.Vector(9.030354,173.508882,78.351589),Base.Rotation(-0.161765,0.015489,0.000000,0.986708))
App.ActiveDocument.addObject("Part::Cylinder","C545")
App.ActiveDocument.C545.Radius=0.725851
App.ActiveDocument.C545.Height=20.00
App.ActiveDocument.C545.Angle=360.00 
App.ActiveDocument.C545.Placement=Base.Placement(Base.Vector(11.680497,171.916762,78.557796),Base.Rotation(-0.146703,0.090518,0.000000,0.985030))
App.ActiveDocument.addObject("Part::Cylinder","C546")
App.ActiveDocument.C546.Radius=0.720287
App.ActiveDocument.C546.Height=20.00
App.ActiveDocument.C546.Angle=360.00 
App.ActiveDocument.C546.Placement=Base.Placement(Base.Vector(15.089362,170.027304,78.311424),Base.Rotation(-0.115854,0.114672,0.000000,0.986625))
App.ActiveDocument.addObject("Part::Cylinder","C547")
App.ActiveDocument.C547.Radius=0.716282
App.ActiveDocument.C547.Height=20.00
App.ActiveDocument.C547.Angle=360.00 
App.ActiveDocument.C547.Placement=Base.Placement(Base.Vector(17.592701,167.683390,78.124071),Base.Rotation(-0.076137,0.130893,0.000000,0.988469))
App.ActiveDocument.addObject("Part::Cylinder","C548")
App.ActiveDocument.C548.Radius=0.712393
App.ActiveDocument.C548.Height=20.00
App.ActiveDocument.C548.Angle=360.00 
App.ActiveDocument.C548.Placement=Base.Placement(Base.Vector(19.579295,164.871876,77.869306),Base.Rotation(-0.037697,0.153820,0.000000,0.987380))
App.ActiveDocument.addObject("Part::Cylinder","C549")
App.ActiveDocument.C549.Radius=0.708907
App.ActiveDocument.C549.Height=20.00
App.ActiveDocument.C549.Angle=360.00 
App.ActiveDocument.C549.Placement=Base.Placement(Base.Vector(20.998861,161.508591,77.530226),Base.Rotation(-0.014173,0.176509,0.000000,0.984197))
App.ActiveDocument.addObject("Part::Cylinder","C550")
App.ActiveDocument.C550.Radius=0.710892
App.ActiveDocument.C550.Height=20.00
App.ActiveDocument.C550.Angle=360.00 
App.ActiveDocument.C550.Placement=Base.Placement(Base.Vector(20.236748,157.309998,77.906472),Base.Rotation(-0.023182,0.172592,0.000000,0.984721))
App.ActiveDocument.addObject("Part::Cylinder","C551")
App.ActiveDocument.C551.Radius=0.710114
App.ActiveDocument.C551.Height=20.00
App.ActiveDocument.C551.Angle=360.00 
App.ActiveDocument.C551.Placement=Base.Placement(Base.Vector(21.039271,151.535569,78.256872),Base.Rotation(-0.089431,0.176876,0.000000,0.980162))
App.ActiveDocument.addObject("Part::Cylinder","C552")
App.ActiveDocument.C552.Radius=0.710114
App.ActiveDocument.C552.Height=20.00
App.ActiveDocument.C552.Angle=360.00 
App.ActiveDocument.C552.Placement=Base.Placement(Base.Vector(21.922340,147.145844,78.893264),Base.Rotation(-0.096370,0.181163,0.000000,0.978720))
App.ActiveDocument.addObject("Part::Cylinder","C553")
App.ActiveDocument.C553.Radius=0.710002
App.ActiveDocument.C553.Height=20.00
App.ActiveDocument.C553.Angle=360.00 
App.ActiveDocument.C553.Placement=Base.Placement(Base.Vector(22.683469,145.583563,79.042939),Base.Rotation(0.042489,0.174886,0.000000,0.983671))
App.ActiveDocument.addObject("Part::Cylinder","C554")
App.ActiveDocument.C554.Radius=0.738292
App.ActiveDocument.C554.Height=20.00
App.ActiveDocument.C554.Angle=360.00 
App.ActiveDocument.C554.Placement=Base.Placement(Base.Vector(5.720402,171.017980,78.768621),Base.Rotation(-0.110344,-0.037614,0.000000,0.993181))
App.ActiveDocument.addObject("Part::Cylinder","C555")
App.ActiveDocument.C555.Radius=0.734089
App.ActiveDocument.C555.Height=20.00
App.ActiveDocument.C555.Angle=360.00 
App.ActiveDocument.C555.Placement=Base.Placement(Base.Vector(9.338242,169.445540,79.378672),Base.Rotation(-0.102513,-0.004218,0.000000,0.994723))
App.ActiveDocument.addObject("Part::Cylinder","C556")
App.ActiveDocument.C556.Radius=0.728795
App.ActiveDocument.C556.Height=20.00
App.ActiveDocument.C556.Angle=360.00 
App.ActiveDocument.C556.Placement=Base.Placement(Base.Vector(11.668194,167.564553,79.474544),Base.Rotation(-0.076121,0.083559,0.000000,0.993591))
App.ActiveDocument.addObject("Part::Cylinder","C557")
App.ActiveDocument.C557.Radius=0.724661
App.ActiveDocument.C557.Height=20.00
App.ActiveDocument.C557.Angle=360.00 
App.ActiveDocument.C557.Placement=Base.Placement(Base.Vector(13.983245,165.055397,79.335118),Base.Rotation(-0.052032,0.109186,0.000000,0.992659))
App.ActiveDocument.addObject("Part::Cylinder","C558")
App.ActiveDocument.C558.Radius=0.720503
App.ActiveDocument.C558.Height=20.00
App.ActiveDocument.C558.Angle=360.00 
App.ActiveDocument.C558.Placement=Base.Placement(Base.Vector(16.053630,162.337959,79.019815),Base.Rotation(-0.026406,0.131138,0.000000,0.991012))
App.ActiveDocument.addObject("Part::Cylinder","C559")
App.ActiveDocument.C559.Radius=0.717831
App.ActiveDocument.C559.Height=20.00
App.ActiveDocument.C559.Angle=360.00 
App.ActiveDocument.C559.Placement=Base.Placement(Base.Vector(17.266809,159.059982,78.826771),Base.Rotation(-0.019610,0.148228,0.000000,0.988759))
App.ActiveDocument.addObject("Part::Cylinder","C560")
App.ActiveDocument.C560.Radius=0.720264
App.ActiveDocument.C560.Height=20.00
App.ActiveDocument.C560.Angle=360.00 
App.ActiveDocument.C560.Placement=Base.Placement(Base.Vector(19.107432,153.147511,79.094868),Base.Rotation(-0.070110,0.013793,0.000000,0.997444))
App.ActiveDocument.addObject("Part::Cylinder","C561")
App.ActiveDocument.C561.Radius=0.720526
App.ActiveDocument.C561.Height=20.00
App.ActiveDocument.C561.Angle=360.00 
App.ActiveDocument.C561.Placement=Base.Placement(Base.Vector(17.345392,148.063273,80.314924),Base.Rotation(-0.083117,0.153479,0.000000,0.984650))
App.ActiveDocument.addObject("Part::Cylinder","C562")
App.ActiveDocument.C562.Radius=0.721353
App.ActiveDocument.C562.Height=20.00
App.ActiveDocument.C562.Angle=360.00 
App.ActiveDocument.C562.Placement=Base.Placement(Base.Vector(17.844211,145.405154,80.798012),Base.Rotation(-0.008852,0.149933,0.000000,0.988656))
App.ActiveDocument.addObject("Part::Cylinder","C563")
App.ActiveDocument.C563.Radius=0.740420
App.ActiveDocument.C563.Height=20.00
App.ActiveDocument.C563.Angle=360.00 
App.ActiveDocument.C563.Placement=Base.Placement(Base.Vector(5.777801,166.572837,79.581339),Base.Rotation(-0.066679,-0.040677,0.000000,0.996945))
App.ActiveDocument.addObject("Part::Cylinder","C564")
App.ActiveDocument.C564.Radius=0.736478
App.ActiveDocument.C564.Height=20.00
App.ActiveDocument.C564.Angle=360.00 
App.ActiveDocument.C564.Placement=Base.Placement(Base.Vector(9.400864,164.748616,80.119863),Base.Rotation(-0.053590,-0.024140,0.000000,0.998271))
App.ActiveDocument.addObject("Part::Cylinder","C565")
App.ActiveDocument.C565.Radius=0.731926
App.ActiveDocument.C565.Height=20.00
App.ActiveDocument.C565.Angle=360.00 
App.ActiveDocument.C565.Placement=Base.Placement(Base.Vector(11.104986,162.057034,80.189737),Base.Rotation(-0.041857,0.064203,0.000000,0.997059))
App.ActiveDocument.addObject("Part::Cylinder","C566")
App.ActiveDocument.C566.Radius=0.728108
App.ActiveDocument.C566.Height=20.00
App.ActiveDocument.C566.Angle=360.00 
App.ActiveDocument.C566.Placement=Base.Placement(Base.Vector(12.598641,159.039235,80.098626),Base.Rotation(-0.034639,0.112981,0.000000,0.992993))
App.ActiveDocument.addObject("Part::Cylinder","C567")
App.ActiveDocument.C567.Radius=0.729966
App.ActiveDocument.C567.Height=20.00
App.ActiveDocument.C567.Angle=360.00 
App.ActiveDocument.C567.Placement=Base.Placement(Base.Vector(12.147066,153.068461,80.822664),Base.Rotation(-0.077362,0.116654,0.000000,0.990155))
App.ActiveDocument.addObject("Part::Cylinder","C568")
App.ActiveDocument.C568.Radius=0.729847
App.ActiveDocument.C568.Height=20.00
App.ActiveDocument.C568.Angle=360.00 
App.ActiveDocument.C568.Placement=Base.Placement(Base.Vector(13.282105,147.615784,81.681632),Base.Rotation(-0.088163,0.128363,0.000000,0.987801))
App.ActiveDocument.addObject("Part::Cylinder","C569")
App.ActiveDocument.C569.Radius=0.729155
App.ActiveDocument.C569.Height=20.00
App.ActiveDocument.C569.Angle=360.00 
App.ActiveDocument.C569.Placement=Base.Placement(Base.Vector(13.704941,145.780342,81.448962),Base.Rotation(0.075289,0.120414,0.000000,0.989865))
App.ActiveDocument.addObject("Part::Cylinder","C570")
App.ActiveDocument.C570.Radius=0.741903
App.ActiveDocument.C570.Height=20.00
App.ActiveDocument.C570.Angle=360.00 
App.ActiveDocument.C570.Placement=Base.Placement(Base.Vector(5.570200,161.757763,80.071126),Base.Rotation(-0.042121,-0.041125,0.000000,0.998266))
App.ActiveDocument.addObject("Part::Cylinder","C571")
App.ActiveDocument.C571.Radius=0.738892
App.ActiveDocument.C571.Height=20.00
App.ActiveDocument.C571.Angle=360.00 
App.ActiveDocument.C571.Placement=Base.Placement(Base.Vector(8.523622,159.277518,80.563807),Base.Rotation(-0.041254,-0.033327,0.000000,0.998593))
App.ActiveDocument.addObject("Part::Cylinder","C572")
App.ActiveDocument.C572.Radius=0.735986
App.ActiveDocument.C572.Height=20.00
App.ActiveDocument.C572.Angle=360.00 
App.ActiveDocument.C572.Placement=Base.Placement(Base.Vector(10.050771,156.006987,80.888730),Base.Rotation(-0.054246,0.025552,0.000000,0.998201))
App.ActiveDocument.addObject("Part::Cylinder","C573")
App.ActiveDocument.C573.Radius=0.737039
App.ActiveDocument.C573.Height=20.00
App.ActiveDocument.C573.Angle=360.00 
App.ActiveDocument.C573.Placement=Base.Placement(Base.Vector(10.360951,149.309555,81.908729),Base.Rotation(-0.097028,0.042555,0.000000,0.994372))
App.ActiveDocument.addObject("Part::Cylinder","C574")
App.ActiveDocument.C574.Radius=0.738246
App.ActiveDocument.C574.Height=20.00
App.ActiveDocument.C574.Angle=360.00 
App.ActiveDocument.C574.Placement=Base.Placement(Base.Vector(10.700831,150.018812,83.270145),Base.Rotation(0.203831,0.040642,0.000000,0.978162))
App.ActiveDocument.addObject("Part::Cylinder","C575")
App.ActiveDocument.C575.Radius=0.743278
App.ActiveDocument.C575.Height=20.00
App.ActiveDocument.C575.Angle=360.00 
App.ActiveDocument.C575.Placement=Base.Placement(Base.Vector(5.457720,155.439029,80.568478),Base.Rotation(-0.047907,-0.047941,0.000000,0.997701))
App.ActiveDocument.addObject("Part::Cylinder","C576")
App.ActiveDocument.C576.Radius=0.742212
App.ActiveDocument.C576.Height=20.00
App.ActiveDocument.C576.Angle=360.00 
App.ActiveDocument.C576.Placement=Base.Placement(Base.Vector(7.577877,151.733819,81.260255),Base.Rotation(-0.066508,-0.062796,0.000000,0.995808))
App.ActiveDocument.addObject("Part::Cylinder","C577")
App.ActiveDocument.C577.Radius=0.743630
App.ActiveDocument.C577.Height=20.00
App.ActiveDocument.C577.Angle=360.00 
App.ActiveDocument.C577.Placement=Base.Placement(Base.Vector(8.091147,147.397257,81.984997),Base.Rotation(-0.053400,-0.084645,0.000000,0.994979))
App.ActiveDocument.addObject("Part::Cylinder","C578")
App.ActiveDocument.C578.Radius=0.739176
App.ActiveDocument.C578.Height=20.00
App.ActiveDocument.C578.Angle=360.00 
App.ActiveDocument.C578.Placement=Base.Placement(Base.Vector(7.565362,152.573341,85.887370),Base.Rotation(0.523966,-0.006304,0.000000,0.851716))
App.ActiveDocument.addObject("Part::Cylinder","C579")
App.ActiveDocument.C579.Radius=0.552865
App.ActiveDocument.C579.Height=20.00
App.ActiveDocument.C579.Angle=360.00 
App.ActiveDocument.C579.Placement=Base.Placement(Base.Vector(4.281428,206.418659,-3.804272),Base.Rotation(-0.724931,0.061688,0.000000,0.686054))
App.ActiveDocument.addObject("Part::Cylinder","C580")
App.ActiveDocument.C580.Radius=0.563680
App.ActiveDocument.C580.Height=20.00
App.ActiveDocument.C580.Angle=360.00 
App.ActiveDocument.C580.Placement=Base.Placement(Base.Vector(4.443073,206.054105,-8.428832),Base.Rotation(-0.736624,0.056047,0.000000,0.673976))
App.ActiveDocument.addObject("Part::Cylinder","C581")
App.ActiveDocument.C581.Radius=0.574442
App.ActiveDocument.C581.Height=20.00
App.ActiveDocument.C581.Angle=360.00 
App.ActiveDocument.C581.Placement=Base.Placement(Base.Vector(4.386042,205.563534,-12.913264),Base.Rotation(-0.748042,0.052427,0.000000,0.661577))
App.ActiveDocument.addObject("Part::Cylinder","C582")
App.ActiveDocument.C582.Radius=0.585014
App.ActiveDocument.C582.Height=20.00
App.ActiveDocument.C582.Angle=360.00 
App.ActiveDocument.C582.Placement=Base.Placement(Base.Vector(4.411220,204.919745,-17.329654),Base.Rotation(-0.760339,0.049039,0.000000,0.647673))
App.ActiveDocument.addObject("Part::Cylinder","C583")
App.ActiveDocument.C583.Radius=0.595674
App.ActiveDocument.C583.Height=20.00
App.ActiveDocument.C583.Angle=360.00 
App.ActiveDocument.C583.Placement=Base.Placement(Base.Vector(4.605619,204.073245,-21.904175),Base.Rotation(-0.772880,0.050872,0.000000,0.632509))
App.ActiveDocument.addObject("Part::Cylinder","C584")
App.ActiveDocument.C584.Radius=0.606447
App.ActiveDocument.C584.Height=20.00
App.ActiveDocument.C584.Angle=360.00 
App.ActiveDocument.C584.Placement=Base.Placement(Base.Vector(4.384372,203.104453,-26.252465),Base.Rotation(-0.785909,0.052038,0.000000,0.616149))
App.ActiveDocument.addObject("Part::Cylinder","C585")
App.ActiveDocument.C585.Radius=0.616918
App.ActiveDocument.C585.Height=20.00
App.ActiveDocument.C585.Angle=360.00 
App.ActiveDocument.C585.Placement=Base.Placement(Base.Vector(4.223925,201.973989,-30.411661),Base.Rotation(-0.800662,0.048357,0.000000,0.597162))
App.ActiveDocument.addObject("Part::Cylinder","C586")
App.ActiveDocument.C586.Radius=0.626852
App.ActiveDocument.C586.Height=20.00
App.ActiveDocument.C586.Angle=360.00 
App.ActiveDocument.C586.Placement=Base.Placement(Base.Vector(4.466104,200.604391,-34.487985),Base.Rotation(-0.818831,0.053070,0.000000,0.571577))
App.ActiveDocument.addObject("Part::Cylinder","C587")
App.ActiveDocument.C587.Radius=0.637068
App.ActiveDocument.C587.Height=20.00
App.ActiveDocument.C587.Angle=360.00 
App.ActiveDocument.C587.Placement=Base.Placement(Base.Vector(4.359297,199.045415,-38.272806),Base.Rotation(-0.842036,0.053901,0.000000,0.536721))
App.ActiveDocument.addObject("Part::Cylinder","C588")
App.ActiveDocument.C588.Radius=0.646287
App.ActiveDocument.C588.Height=20.00
App.ActiveDocument.C588.Angle=360.00 
App.ActiveDocument.C588.Placement=Base.Placement(Base.Vector(4.483434,197.252255,-41.663046),Base.Rotation(-0.866976,0.056137,0.000000,0.495178))
App.ActiveDocument.addObject("Part::Cylinder","C589")
App.ActiveDocument.C589.Radius=0.655288
App.ActiveDocument.C589.Height=20.00
App.ActiveDocument.C589.Angle=360.00 
App.ActiveDocument.C589.Placement=Base.Placement(Base.Vector(4.488365,195.104305,-44.855786),Base.Rotation(-0.891669,0.056947,0.000000,0.449091))
App.ActiveDocument.addObject("Part::Cylinder","C590")
App.ActiveDocument.C590.Radius=0.663895
App.ActiveDocument.C590.Height=20.00
App.ActiveDocument.C590.Angle=360.00 
App.ActiveDocument.C590.Placement=Base.Placement(Base.Vector(4.433137,192.454730,-48.088308),Base.Rotation(-0.909144,0.061767,0.000000,0.411876))
App.ActiveDocument.addObject("Part::Cylinder","C591")
App.ActiveDocument.C591.Radius=0.671910
App.ActiveDocument.C591.Height=20.00
App.ActiveDocument.C591.Angle=360.00 
App.ActiveDocument.C591.Placement=Base.Placement(Base.Vector(4.319107,189.513464,-51.240456),Base.Rotation(-0.920232,0.064549,0.000000,0.386013))
App.ActiveDocument.addObject("Part::Cylinder","C592")
App.ActiveDocument.C592.Radius=0.679230
App.ActiveDocument.C592.Height=20.00
App.ActiveDocument.C592.Angle=360.00 
App.ActiveDocument.C592.Placement=Base.Placement(Base.Vector(4.484375,186.438076,-54.145239),Base.Rotation(-0.933760,0.071753,0.000000,0.350634))
App.ActiveDocument.addObject("Part::Cylinder","C593")
App.ActiveDocument.C593.Radius=0.685990
App.ActiveDocument.C593.Height=20.00
App.ActiveDocument.C593.Angle=360.00 
App.ActiveDocument.C593.Placement=Base.Placement(Base.Vector(4.619046,183.252094,-56.634171),Base.Rotation(-0.950283,0.075734,0.000000,0.302038))
App.ActiveDocument.addObject("Part::Cylinder","C594")
App.ActiveDocument.C594.Radius=0.691958
App.ActiveDocument.C594.Height=20.00
App.ActiveDocument.C594.Angle=360.00 
App.ActiveDocument.C594.Placement=Base.Placement(Base.Vector(4.467258,179.885259,-58.752553),Base.Rotation(-0.962195,0.090480,0.000000,0.256894))
App.ActiveDocument.addObject("Part::Cylinder","C595")
App.ActiveDocument.C595.Radius=0.697079
App.ActiveDocument.C595.Height=20.00
App.ActiveDocument.C595.Angle=360.00 
App.ActiveDocument.C595.Placement=Base.Placement(Base.Vector(4.339283,176.064229,-60.774425),Base.Rotation(-0.966152,0.119925,0.000000,0.228404))
App.ActiveDocument.addObject("Part::Cylinder","C596")
App.ActiveDocument.C596.Radius=0.701782
App.ActiveDocument.C596.Height=20.00
App.ActiveDocument.C596.Angle=360.00 
App.ActiveDocument.C596.Placement=Base.Placement(Base.Vector(4.274113,171.761500,-62.798140),Base.Rotation(-0.963735,0.164232,0.000000,0.210339))
App.ActiveDocument.addObject("Part::Cylinder","C597")
App.ActiveDocument.C597.Radius=0.706066
App.ActiveDocument.C597.Height=20.00
App.ActiveDocument.C597.Angle=360.00 
App.ActiveDocument.C597.Placement=Base.Placement(Base.Vector(4.232199,167.490755,-64.617667),Base.Rotation(-0.960976,0.198871,0.000000,0.192289))
App.ActiveDocument.addObject("Part::Cylinder","C598")
App.ActiveDocument.C598.Radius=0.709770
App.ActiveDocument.C598.Height=20.00
App.ActiveDocument.C598.Angle=360.00 
App.ActiveDocument.C598.Placement=Base.Placement(Base.Vector(4.315411,163.294214,-66.153653),Base.Rotation(-0.959318,0.228704,0.000000,0.165538))
App.ActiveDocument.addObject("Part::Cylinder","C599")
App.ActiveDocument.C599.Radius=0.712869
App.ActiveDocument.C599.Height=20.00
App.ActiveDocument.C599.Angle=360.00 
App.ActiveDocument.C599.Placement=Base.Placement(Base.Vector(4.418235,159.247188,-67.370370),Base.Rotation(-0.963914,0.228259,0.000000,0.136993))
App.ActiveDocument.addObject("Part::Cylinder","C600")
App.ActiveDocument.C600.Radius=0.715252
App.ActiveDocument.C600.Height=20.00
App.ActiveDocument.C600.Angle=360.00 
App.ActiveDocument.C600.Placement=Base.Placement(Base.Vector(4.578661,155.158866,-68.370413),Base.Rotation(-0.966115,0.231922,0.000000,0.113287))
App.ActiveDocument.addObject("Part::Cylinder","C601")
App.ActiveDocument.C601.Radius=0.717142
App.ActiveDocument.C601.Height=20.00
App.ActiveDocument.C601.Angle=360.00 
App.ActiveDocument.C601.Placement=Base.Placement(Base.Vector(4.784017,150.785482,-69.236594),Base.Rotation(-0.959908,0.265069,0.000000,0.091192))
App.ActiveDocument.addObject("Part::Cylinder","C602")
App.ActiveDocument.C602.Radius=0.718774
App.ActiveDocument.C602.Height=20.00
App.ActiveDocument.C602.Angle=360.00 
App.ActiveDocument.C602.Placement=Base.Placement(Base.Vector(4.805749,146.502223,-69.909916),Base.Rotation(-0.945384,0.318009,0.000000,0.071551))
App.ActiveDocument.addObject("Part::Cylinder","C603")
App.ActiveDocument.C603.Radius=0.720015
App.ActiveDocument.C603.Height=20.00
App.ActiveDocument.C603.Angle=360.00 
App.ActiveDocument.C603.Placement=Base.Placement(Base.Vector(4.747897,142.227829,-70.393120),Base.Rotation(-0.879797,0.472763,0.000000,0.049527))
App.ActiveDocument.addObject("Part::Cylinder","C604")
App.ActiveDocument.C604.Radius=0.720793
App.ActiveDocument.C604.Height=20.00
App.ActiveDocument.C604.Angle=360.00 
App.ActiveDocument.C604.Placement=Base.Placement(Base.Vector(4.650566,137.971863,-70.663574),Base.Rotation(-0.549334,0.835105,0.000000,0.028852))
App.ActiveDocument.addObject("Part::Cylinder","C605")
App.ActiveDocument.C605.Radius=0.720968
App.ActiveDocument.C605.Height=20.00
App.ActiveDocument.C605.Angle=360.00 
App.ActiveDocument.C605.Placement=Base.Placement(Base.Vector(4.662732,133.723857,-70.692758),Base.Rotation(0.485497,0.873944,0.000000,0.022693))
App.ActiveDocument.addObject("Part::Cylinder","C606")
App.ActiveDocument.C606.Radius=0.720644
App.ActiveDocument.C606.Height=20.00
App.ActiveDocument.C606.Angle=360.00 
App.ActiveDocument.C606.Placement=Base.Placement(Base.Vector(4.685962,129.552817,-70.471729),Base.Rotation(0.979374,0.196151,0.000000,0.048497))
App.ActiveDocument.addObject("Part::Cylinder","C607")
App.ActiveDocument.C607.Radius=0.719609
App.ActiveDocument.C607.Height=20.00
App.ActiveDocument.C607.Angle=360.00 
App.ActiveDocument.C607.Placement=Base.Placement(Base.Vector(4.652691,125.426796,-69.971425),Base.Rotation(0.996253,0.043445,0.000000,0.074788))
App.ActiveDocument.addObject("Part::Cylinder","C608")
App.ActiveDocument.C608.Radius=0.717138
App.ActiveDocument.C608.Height=20.00
App.ActiveDocument.C608.Angle=360.00 
App.ActiveDocument.C608.Placement=Base.Placement(Base.Vector(4.826342,121.398067,-69.175934),Base.Rotation(0.990705,0.068521,0.000000,0.117512))
App.ActiveDocument.addObject("Part::Cylinder","C609")
App.ActiveDocument.C609.Radius=0.714280
App.ActiveDocument.C609.Height=20.00
App.ActiveDocument.C609.Angle=360.00 
App.ActiveDocument.C609.Placement=Base.Placement(Base.Vector(3.812542,117.593375,-68.127708),Base.Rotation(0.946259,0.268473,0.000000,0.180324))
App.ActiveDocument.addObject("Part::Cylinder","C610")
App.ActiveDocument.C610.Radius=0.709829
App.ActiveDocument.C610.Height=20.00
App.ActiveDocument.C610.Angle=360.00 
App.ActiveDocument.C610.Placement=Base.Placement(Base.Vector(2.797222,114.026836,-66.814033),Base.Rotation(0.882368,0.393617,0.000000,0.257861))
App.ActiveDocument.addObject("Part::Cylinder","C611")
App.ActiveDocument.C611.Radius=0.704029
App.ActiveDocument.C611.Height=20.00
App.ActiveDocument.C611.Angle=360.00 
App.ActiveDocument.C611.Placement=Base.Placement(Base.Vector(2.724884,111.095574,-64.994260),Base.Rotation(0.887625,0.324831,0.000000,0.326506))
App.ActiveDocument.addObject("Part::Cylinder","C612")
App.ActiveDocument.C612.Radius=0.697445
App.ActiveDocument.C612.Height=20.00
App.ActiveDocument.C612.Angle=360.00 
App.ActiveDocument.C612.Placement=Base.Placement(Base.Vector(3.611896,108.896948,-62.996752),Base.Rotation(0.906076,0.135507,0.000000,0.400829))
App.ActiveDocument.addObject("Part::Cylinder","C613")
App.ActiveDocument.C613.Radius=0.546890
App.ActiveDocument.C613.Height=20.00
App.ActiveDocument.C613.Angle=360.00 
App.ActiveDocument.C613.Placement=Base.Placement(Base.Vector(8.250384,205.905319,-4.040572),Base.Rotation(-0.714962,0.119112,0.000000,0.688943))
App.ActiveDocument.addObject("Part::Cylinder","C614")
App.ActiveDocument.C614.Radius=0.557542
App.ActiveDocument.C614.Height=20.00
App.ActiveDocument.C614.Angle=360.00 
App.ActiveDocument.C614.Placement=Base.Placement(Base.Vector(8.406202,205.570770,-8.590882),Base.Rotation(-0.727183,0.116098,0.000000,0.676555))
App.ActiveDocument.addObject("Part::Cylinder","C615")
App.ActiveDocument.C615.Radius=0.568658
App.ActiveDocument.C615.Height=20.00
App.ActiveDocument.C615.Angle=360.00 
App.ActiveDocument.C615.Placement=Base.Placement(Base.Vector(8.358756,205.104316,-13.188525),Base.Rotation(-0.740229,0.110414,0.000000,0.663226))
App.ActiveDocument.addObject("Part::Cylinder","C616")
App.ActiveDocument.C616.Radius=0.578899
App.ActiveDocument.C616.Height=20.00
App.ActiveDocument.C616.Angle=360.00 
App.ActiveDocument.C616.Placement=Base.Placement(Base.Vector(8.435047,204.492134,-17.463605),Base.Rotation(-0.753184,0.105919,0.000000,0.649226))
App.ActiveDocument.addObject("Part::Cylinder","C617")
App.ActiveDocument.C617.Radius=0.588870
App.ActiveDocument.C617.Height=20.00
App.ActiveDocument.C617.Angle=360.00 
App.ActiveDocument.C617.Placement=Base.Placement(Base.Vector(8.852328,203.634681,-21.892606),Base.Rotation(-0.764665,0.110950,0.000000,0.634805))
App.ActiveDocument.addObject("Part::Cylinder","C618")
App.ActiveDocument.C618.Radius=0.600024
App.ActiveDocument.C618.Height=20.00
App.ActiveDocument.C618.Angle=360.00 
App.ActiveDocument.C618.Placement=Base.Placement(Base.Vector(8.534078,202.707095,-26.255778),Base.Rotation(-0.779669,0.103587,0.000000,0.617565))
App.ActiveDocument.addObject("Part::Cylinder","C619")
App.ActiveDocument.C619.Radius=0.610278
App.ActiveDocument.C619.Height=20.00
App.ActiveDocument.C619.Angle=360.00 
App.ActiveDocument.C619.Placement=Base.Placement(Base.Vector(8.372364,201.630673,-30.310133),Base.Rotation(-0.794359,0.097525,0.000000,0.599569))
App.ActiveDocument.addObject("Part::Cylinder","C620")
App.ActiveDocument.C620.Radius=0.620013
App.ActiveDocument.C620.Height=20.00
App.ActiveDocument.C620.Angle=360.00 
App.ActiveDocument.C620.Placement=Base.Placement(Base.Vector(8.667153,200.286542,-34.307086),Base.Rotation(-0.812472,0.101105,0.000000,0.574167))
App.ActiveDocument.addObject("Part::Cylinder","C621")
App.ActiveDocument.C621.Radius=0.629859
App.ActiveDocument.C621.Height=20.00
App.ActiveDocument.C621.Angle=360.00 
App.ActiveDocument.C621.Placement=Base.Placement(Base.Vector(8.853484,198.706235,-38.146747),Base.Rotation(-0.833904,0.101391,0.000000,0.542517))
App.ActiveDocument.addObject("Part::Cylinder","C622")
App.ActiveDocument.C622.Radius=0.639137
App.ActiveDocument.C622.Height=20.00
App.ActiveDocument.C622.Angle=360.00 
App.ActiveDocument.C622.Placement=Base.Placement(Base.Vector(9.098990,196.932505,-41.530432),Base.Rotation(-0.861142,0.101627,0.000000,0.498103))
App.ActiveDocument.addObject("Part::Cylinder","C623")
App.ActiveDocument.C623.Radius=0.648039
App.ActiveDocument.C623.Height=20.00
App.ActiveDocument.C623.Angle=360.00 
App.ActiveDocument.C623.Placement=Base.Placement(Base.Vector(9.156066,194.836907,-44.689677),Base.Rotation(-0.885726,0.099086,0.000000,0.453511))
App.ActiveDocument.addObject("Part::Cylinder","C624")
App.ActiveDocument.C624.Radius=0.656443
App.ActiveDocument.C624.Height=20.00
App.ActiveDocument.C624.Angle=360.00 
App.ActiveDocument.C624.Placement=Base.Placement(Base.Vector(9.136014,192.379977,-47.734671),Base.Rotation(-0.905377,0.091522,0.000000,0.414628))
App.ActiveDocument.addObject("Part::Cylinder","C625")
App.ActiveDocument.C625.Radius=0.664762
App.ActiveDocument.C625.Height=20.00
App.ActiveDocument.C625.Angle=360.00 
App.ActiveDocument.C625.Placement=Base.Placement(Base.Vector(8.821096,189.510285,-50.857522),Base.Rotation(-0.917362,0.094473,0.000000,0.386681))
App.ActiveDocument.addObject("Part::Cylinder","C626")
App.ActiveDocument.C626.Radius=0.671744
App.ActiveDocument.C626.Height=20.00
App.ActiveDocument.C626.Angle=360.00 
App.ActiveDocument.C626.Placement=Base.Placement(Base.Vector(9.068136,186.466224,-53.718276),Base.Rotation(-0.928699,0.117195,0.000000,0.351828))
App.ActiveDocument.addObject("Part::Cylinder","C627")
App.ActiveDocument.C627.Radius=0.678205
App.ActiveDocument.C627.Height=20.00
App.ActiveDocument.C627.Angle=360.00 
App.ActiveDocument.C627.Placement=Base.Placement(Base.Vector(9.031732,183.485761,-56.093716),Base.Rotation(-0.940100,0.147351,0.000000,0.307408))
App.ActiveDocument.addObject("Part::Cylinder","C628")
App.ActiveDocument.C628.Radius=0.684127
App.ActiveDocument.C628.Height=20.00
App.ActiveDocument.C628.Angle=360.00 
App.ActiveDocument.C628.Placement=Base.Placement(Base.Vector(8.778311,180.344711,-58.136735),Base.Rotation(-0.948203,0.179204,0.000000,0.262293))
App.ActiveDocument.addObject("Part::Cylinder","C629")
App.ActiveDocument.C629.Radius=0.689122
App.ActiveDocument.C629.Height=20.00
App.ActiveDocument.C629.Angle=360.00 
App.ActiveDocument.C629.Placement=Base.Placement(Base.Vector(8.671360,176.686900,-60.083068),Base.Rotation(-0.947904,0.218513,0.000000,0.231797))
App.ActiveDocument.addObject("Part::Cylinder","C630")
App.ActiveDocument.C630.Radius=0.694000
App.ActiveDocument.C630.Height=20.00
App.ActiveDocument.C630.Angle=360.00 
App.ActiveDocument.C630.Placement=Base.Placement(Base.Vector(8.305743,172.706878,-61.967455),Base.Rotation(-0.942302,0.257886,0.000000,0.213453))
App.ActiveDocument.addObject("Part::Cylinder","C631")
App.ActiveDocument.C631.Radius=0.698029
App.ActiveDocument.C631.Height=20.00
App.ActiveDocument.C631.Angle=360.00 
App.ActiveDocument.C631.Placement=Base.Placement(Base.Vector(8.316824,168.492175,-63.755381),Base.Rotation(-0.932794,0.299566,0.000000,0.200388))
App.ActiveDocument.addObject("Part::Cylinder","C632")
App.ActiveDocument.C632.Radius=0.701689
App.ActiveDocument.C632.Height=20.00
App.ActiveDocument.C632.Angle=360.00 
App.ActiveDocument.C632.Placement=Base.Placement(Base.Vector(8.364548,164.392681,-65.326121),Base.Rotation(-0.921140,0.344604,0.000000,0.180967))
App.ActiveDocument.addObject("Part::Cylinder","C633")
App.ActiveDocument.C633.Radius=0.704835
App.ActiveDocument.C633.Height=20.00
App.ActiveDocument.C633.Angle=360.00 
App.ActiveDocument.C633.Placement=Base.Placement(Base.Vector(8.469869,160.321304,-66.659696),Base.Rotation(-0.906727,0.390824,0.000000,0.158441))
App.ActiveDocument.addObject("Part::Cylinder","C634")
App.ActiveDocument.C634.Radius=0.707332
App.ActiveDocument.C634.Height=20.00
App.ActiveDocument.C634.Angle=360.00 
App.ActiveDocument.C634.Placement=Base.Placement(Base.Vector(8.692715,156.110839,-67.779752),Base.Rotation(-0.880384,0.454758,0.000000,0.134607))
App.ActiveDocument.addObject("Part::Cylinder","C635")
App.ActiveDocument.C635.Radius=0.709412
App.ActiveDocument.C635.Height=20.00
App.ActiveDocument.C635.Angle=360.00 
App.ActiveDocument.C635.Placement=Base.Placement(Base.Vector(8.879653,151.736734,-68.713263),Base.Rotation(-0.840301,0.530229,0.000000,0.112919))
App.ActiveDocument.addObject("Part::Cylinder","C636")
App.ActiveDocument.C636.Radius=0.711458
App.ActiveDocument.C636.Height=20.00
App.ActiveDocument.C636.Angle=360.00 
App.ActiveDocument.C636.Placement=Base.Placement(Base.Vector(8.781597,147.423681,-69.462527),Base.Rotation(-0.791169,0.604408,0.000000,0.093500))
App.ActiveDocument.addObject("Part::Cylinder","C637")
App.ActiveDocument.C637.Radius=0.712743
App.ActiveDocument.C637.Height=20.00
App.ActiveDocument.C637.Angle=360.00 
App.ActiveDocument.C637.Placement=Base.Placement(Base.Vector(8.826864,143.087427,-69.999122),Base.Rotation(-0.668240,0.740154,0.000000,0.075012))
App.ActiveDocument.addObject("Part::Cylinder","C638")
App.ActiveDocument.C638.Radius=0.713416
App.ActiveDocument.C638.Height=20.00
App.ActiveDocument.C638.Angle=360.00 
App.ActiveDocument.C638.Placement=Base.Placement(Base.Vector(8.943664,138.714846,-70.306123),Base.Rotation(-0.400622,0.914376,0.000000,0.058474))
App.ActiveDocument.addObject("Part::Cylinder","C639")
App.ActiveDocument.C639.Radius=0.714235
App.ActiveDocument.C639.Height=20.00
App.ActiveDocument.C639.Angle=360.00 
App.ActiveDocument.C639.Placement=Base.Placement(Base.Vector(8.726763,134.396312,-70.425844),Base.Rotation(0.031234,0.998469,0.000000,0.045659))
App.ActiveDocument.addObject("Part::Cylinder","C640")
App.ActiveDocument.C640.Radius=0.714053
App.ActiveDocument.C640.Height=20.00
App.ActiveDocument.C640.Angle=360.00 
App.ActiveDocument.C640.Placement=Base.Placement(Base.Vector(8.806824,129.974666,-70.294986),Base.Rotation(0.661332,0.748464,0.000000,0.049416))
App.ActiveDocument.addObject("Part::Cylinder","C641")
App.ActiveDocument.C641.Radius=0.713143
App.ActiveDocument.C641.Height=20.00
App.ActiveDocument.C641.Angle=360.00 
App.ActiveDocument.C641.Placement=Base.Placement(Base.Vector(8.928787,125.715101,-69.906835),Base.Rotation(0.911135,0.405992,0.000000,0.070733))
App.ActiveDocument.addObject("Part::Cylinder","C642")
App.ActiveDocument.C642.Radius=0.710638
App.ActiveDocument.C642.Height=20.00
App.ActiveDocument.C642.Angle=360.00 
App.ActiveDocument.C642.Placement=Base.Placement(Base.Vector(8.847031,122.242417,-69.253017),Base.Rotation(0.937983,0.314461,0.000000,0.145952))
App.ActiveDocument.addObject("Part::Cylinder","C643")
App.ActiveDocument.C643.Radius=0.707440
App.ActiveDocument.C643.Height=20.00
App.ActiveDocument.C643.Angle=360.00 
App.ActiveDocument.C643.Placement=Base.Placement(Base.Vector(8.151230,118.913080,-68.150530),Base.Rotation(0.916580,0.339998,0.000000,0.210436))
App.ActiveDocument.addObject("Part::Cylinder","C644")
App.ActiveDocument.C644.Radius=0.703081
App.ActiveDocument.C644.Height=20.00
App.ActiveDocument.C644.Angle=360.00 
App.ActiveDocument.C644.Placement=Base.Placement(Base.Vector(7.811099,115.379790,-66.498956),Base.Rotation(0.911423,0.323727,0.000000,0.253985))
App.ActiveDocument.addObject("Part::Cylinder","C645")
App.ActiveDocument.C645.Radius=0.698058
App.ActiveDocument.C645.Height=20.00
App.ActiveDocument.C645.Angle=360.00 
App.ActiveDocument.C645.Placement=Base.Placement(Base.Vector(7.788132,111.912320,-64.485288),Base.Rotation(0.921318,0.261555,0.000000,0.287685))
App.ActiveDocument.addObject("Part::Cylinder","C646")
App.ActiveDocument.C646.Radius=0.691956
App.ActiveDocument.C646.Height=20.00
App.ActiveDocument.C646.Angle=360.00 
App.ActiveDocument.C646.Placement=Base.Placement(Base.Vector(8.228000,109.044127,-62.369615),Base.Rotation(0.924751,0.185359,0.000000,0.332382))
App.ActiveDocument.addObject("Part::Cylinder","C647")
App.ActiveDocument.C647.Radius=0.540553
App.ActiveDocument.C647.Height=20.00
App.ActiveDocument.C647.Angle=360.00 
App.ActiveDocument.C647.Placement=Base.Placement(Base.Vector(12.186551,205.085016,-4.100851),Base.Rotation(-0.700001,0.174926,0.000000,0.692387))
App.ActiveDocument.addObject("Part::Cylinder","C648")
App.ActiveDocument.C648.Radius=0.551430
App.ActiveDocument.C648.Height=20.00
App.ActiveDocument.C648.Angle=360.00 
App.ActiveDocument.C648.Placement=Base.Placement(Base.Vector(12.319424,204.777029,-8.693137),Base.Rotation(-0.713869,0.169055,0.000000,0.679567))
App.ActiveDocument.addObject("Part::Cylinder","C649")
App.ActiveDocument.C649.Radius=0.562232
App.ActiveDocument.C649.Height=20.00
App.ActiveDocument.C649.Angle=360.00 
App.ActiveDocument.C649.Placement=Base.Placement(Base.Vector(12.376932,204.328147,-13.235405),Base.Rotation(-0.726618,0.166248,0.000000,0.666624))
App.ActiveDocument.addObject("Part::Cylinder","C650")
App.ActiveDocument.C650.Radius=0.572773
App.ActiveDocument.C650.Height=20.00
App.ActiveDocument.C650.Angle=360.00 
App.ActiveDocument.C650.Placement=Base.Placement(Base.Vector(12.467544,203.714195,-17.670347),Base.Rotation(-0.739454,0.164629,0.000000,0.652767))
App.ActiveDocument.addObject("Part::Cylinder","C651")
App.ActiveDocument.C651.Radius=0.582856
App.ActiveDocument.C651.Height=20.00
App.ActiveDocument.C651.Angle=360.00 
App.ActiveDocument.C651.Placement=Base.Placement(Base.Vector(12.953598,202.823336,-22.127666),Base.Rotation(-0.752390,0.168185,0.000000,0.636885))
App.ActiveDocument.addObject("Part::Cylinder","C652")
App.ActiveDocument.C652.Radius=0.593971
App.ActiveDocument.C652.Height=20.00
App.ActiveDocument.C652.Angle=360.00 
App.ActiveDocument.C652.Placement=Base.Placement(Base.Vector(12.446657,201.997724,-26.396248),Base.Rotation(-0.766782,0.165191,0.000000,0.620288))
App.ActiveDocument.addObject("Part::Cylinder","C653")
App.ActiveDocument.C653.Radius=0.603996
App.ActiveDocument.C653.Height=20.00
App.ActiveDocument.C653.Angle=360.00 
App.ActiveDocument.C653.Placement=Base.Placement(Base.Vector(12.512659,200.876296,-30.500961),Base.Rotation(-0.781324,0.170898,0.000000,0.600271))
App.ActiveDocument.addObject("Part::Cylinder","C654")
App.ActiveDocument.C654.Radius=0.613489
App.ActiveDocument.C654.Height=20.00
App.ActiveDocument.C654.Angle=360.00 
App.ActiveDocument.C654.Placement=Base.Placement(Base.Vector(12.767296,199.534220,-34.428090),Base.Rotation(-0.796866,0.176804,0.000000,0.577707))
App.ActiveDocument.addObject("Part::Cylinder","C655")
App.ActiveDocument.C655.Radius=0.622941
App.ActiveDocument.C655.Height=20.00
App.ActiveDocument.C655.Angle=360.00 
App.ActiveDocument.C655.Placement=Base.Placement(Base.Vector(12.860147,198.039715,-38.099570),Base.Rotation(-0.815583,0.188016,0.000000,0.547242))
App.ActiveDocument.addObject("Part::Cylinder","C656")
App.ActiveDocument.C656.Radius=0.632937
App.ActiveDocument.C656.Height=20.00
App.ActiveDocument.C656.Angle=360.00 
App.ActiveDocument.C656.Placement=Base.Placement(Base.Vector(12.795906,196.268281,-41.621609),Base.Rotation(-0.842220,0.187987,0.000000,0.505298))
App.ActiveDocument.addObject("Part::Cylinder","C657")
App.ActiveDocument.C657.Radius=0.641151
App.ActiveDocument.C657.Height=20.00
App.ActiveDocument.C657.Angle=360.00 
App.ActiveDocument.C657.Placement=Base.Placement(Base.Vector(13.219942,194.178847,-44.716466),Base.Rotation(-0.865051,0.194560,0.000000,0.462421))
App.ActiveDocument.addObject("Part::Cylinder","C658")
App.ActiveDocument.C658.Radius=0.650279
App.ActiveDocument.C658.Height=20.00
App.ActiveDocument.C658.Angle=360.00 
App.ActiveDocument.C658.Placement=Base.Placement(Base.Vector(12.979370,191.790364,-47.786310),Base.Rotation(-0.889752,0.179339,0.000000,0.419736))
App.ActiveDocument.addObject("Part::Cylinder","C659")
App.ActiveDocument.C659.Radius=0.657532
App.ActiveDocument.C659.Height=20.00
App.ActiveDocument.C659.Angle=360.00 
App.ActiveDocument.C659.Placement=Base.Placement(Base.Vector(13.181632,189.014487,-50.710978),Base.Rotation(-0.900132,0.197323,0.000000,0.388364))
App.ActiveDocument.addObject("Part::Cylinder","C660")
App.ActiveDocument.C660.Radius=0.664766
App.ActiveDocument.C660.Height=20.00
App.ActiveDocument.C660.Angle=360.00 
App.ActiveDocument.C660.Placement=Base.Placement(Base.Vector(13.099909,186.087768,-53.430899),Base.Rotation(-0.908785,0.224703,0.000000,0.351595))
App.ActiveDocument.addObject("Part::Cylinder","C661")
App.ActiveDocument.C661.Radius=0.670987
App.ActiveDocument.C661.Height=20.00
App.ActiveDocument.C661.Angle=360.00 
App.ActiveDocument.C661.Placement=Base.Placement(Base.Vector(13.162755,183.019661,-55.781974),Base.Rotation(-0.913117,0.264663,0.000000,0.310114))
App.ActiveDocument.addObject("Part::Cylinder","C662")
App.ActiveDocument.C662.Radius=0.677078
App.ActiveDocument.C662.Height=20.00
App.ActiveDocument.C662.Angle=360.00 
App.ActiveDocument.C662.Placement=Base.Placement(Base.Vector(13.036272,179.654247,-57.913111),Base.Rotation(-0.916324,0.300920,0.000000,0.264192))
App.ActiveDocument.addObject("Part::Cylinder","C663")
App.ActiveDocument.C663.Radius=0.682074
App.ActiveDocument.C663.Height=20.00
App.ActiveDocument.C663.Angle=360.00 
App.ActiveDocument.C663.Placement=Base.Placement(Base.Vector(12.951871,176.023323,-59.798041),Base.Rotation(-0.914388,0.330689,0.000000,0.233539))
App.ActiveDocument.addObject("Part::Cylinder","C664")
App.ActiveDocument.C664.Radius=0.687064
App.ActiveDocument.C664.Height=20.00
App.ActiveDocument.C664.Angle=360.00 
App.ActiveDocument.C664.Placement=Base.Placement(Base.Vector(12.583316,172.047725,-61.650827),Base.Rotation(-0.909730,0.355971,0.000000,0.213718))
App.ActiveDocument.addObject("Part::Cylinder","C665")
App.ActiveDocument.C665.Radius=0.690648
App.ActiveDocument.C665.Height=20.00
App.ActiveDocument.C665.Angle=360.00 
App.ActiveDocument.C665.Placement=Base.Placement(Base.Vector(12.678986,167.885809,-63.341106),Base.Rotation(-0.886457,0.416157,0.000000,0.202503))
App.ActiveDocument.addObject("Part::Cylinder","C666")
App.ActiveDocument.C666.Radius=0.694008
App.ActiveDocument.C666.Height=20.00
App.ActiveDocument.C666.Angle=360.00 
App.ActiveDocument.C666.Placement=Base.Placement(Base.Vector(12.826995,163.604307,-64.901850),Base.Rotation(-0.858334,0.477633,0.000000,0.187427))
App.ActiveDocument.addObject("Part::Cylinder","C667")
App.ActiveDocument.C667.Radius=0.697366
App.ActiveDocument.C667.Height=20.00
App.ActiveDocument.C667.Angle=360.00 
App.ActiveDocument.C667.Placement=Base.Placement(Base.Vector(12.721904,159.436166,-66.256036),Base.Rotation(-0.817761,0.550608,0.000000,0.167624))
App.ActiveDocument.addObject("Part::Cylinder","C668")
App.ActiveDocument.C668.Radius=0.699705
App.ActiveDocument.C668.Height=20.00
App.ActiveDocument.C668.Angle=360.00 
App.ActiveDocument.C668.Placement=Base.Placement(Base.Vector(12.859621,155.254604,-67.340724),Base.Rotation(-0.754146,0.639203,0.000000,0.150610))
App.ActiveDocument.addObject("Part::Cylinder","C669")
App.ActiveDocument.C669.Radius=0.701673
App.ActiveDocument.C669.Height=20.00
App.ActiveDocument.C669.Angle=360.00 
App.ActiveDocument.C669.Placement=Base.Placement(Base.Vector(12.896324,151.118139,-68.213041),Base.Rotation(-0.673721,0.726233,0.000000,0.136696))
App.ActiveDocument.addObject("Part::Cylinder","C670")
App.ActiveDocument.C670.Radius=0.703359
App.ActiveDocument.C670.Height=20.00
App.ActiveDocument.C670.Angle=360.00 
App.ActiveDocument.C670.Placement=Base.Placement(Base.Vector(12.929464,146.700365,-68.942136),Base.Rotation(-0.567328,0.814210,0.000000,0.123294))
App.ActiveDocument.addObject("Part::Cylinder","C671")
App.ActiveDocument.C671.Radius=0.704715
App.ActiveDocument.C671.Height=20.00
App.ActiveDocument.C671.Angle=360.00 
App.ActiveDocument.C671.Placement=Base.Placement(Base.Vector(12.892555,142.361000,-69.470396),Base.Rotation(-0.416989,0.902147,0.000000,0.110688))
App.ActiveDocument.addObject("Part::Cylinder","C672")
App.ActiveDocument.C672.Radius=0.705617
App.ActiveDocument.C672.Height=20.00
App.ActiveDocument.C672.Angle=360.00 
App.ActiveDocument.C672.Placement=Base.Placement(Base.Vector(12.878281,137.979496,-69.787379),Base.Rotation(-0.249604,0.963145,0.000000,0.100243))
App.ActiveDocument.addObject("Part::Cylinder","C673")
App.ActiveDocument.C673.Radius=0.706485
App.ActiveDocument.C673.Height=20.00
App.ActiveDocument.C673.Angle=360.00 
App.ActiveDocument.C673.Placement=Base.Placement(Base.Vector(12.652421,133.582537,-69.936074),Base.Rotation(0.012454,0.995788,0.000000,0.090834))
App.ActiveDocument.addObject("Part::Cylinder","C674")
App.ActiveDocument.C674.Radius=0.706298
App.ActiveDocument.C674.Height=20.00
App.ActiveDocument.C674.Angle=360.00 
App.ActiveDocument.C674.Placement=Base.Placement(Base.Vector(12.897953,129.266615,-69.789123),Base.Rotation(0.340694,0.936682,0.000000,0.080961))
App.ActiveDocument.addObject("Part::Cylinder","C675")
App.ActiveDocument.C675.Radius=0.705385
App.ActiveDocument.C675.Height=20.00
App.ActiveDocument.C675.Angle=360.00 
App.ActiveDocument.C675.Placement=Base.Placement(Base.Vector(12.640540,125.405131,-69.478354),Base.Rotation(0.693440,0.710598,0.000000,0.119125))
App.ActiveDocument.addObject("Part::Cylinder","C676")
App.ActiveDocument.C676.Radius=0.702077
App.ActiveDocument.C676.Height=20.00
App.ActiveDocument.C676.Angle=360.00 
App.ActiveDocument.C676.Placement=Base.Placement(Base.Vector(12.436384,122.338034,-68.684419),Base.Rotation(0.822830,0.530431,0.000000,0.203942))
App.ActiveDocument.addObject("Part::Cylinder","C677")
App.ActiveDocument.C677.Radius=0.698335
App.ActiveDocument.C677.Height=20.00
App.ActiveDocument.C677.Angle=360.00 
App.ActiveDocument.C677.Placement=Base.Placement(Base.Vector(12.158175,118.672459,-67.198586),Base.Rotation(0.851472,0.465674,0.000000,0.241130))
App.ActiveDocument.addObject("Part::Cylinder","C678")
App.ActiveDocument.C678.Radius=0.693664
App.ActiveDocument.C678.Height=20.00
App.ActiveDocument.C678.Angle=360.00 
App.ActiveDocument.C678.Placement=Base.Placement(Base.Vector(12.145063,114.950010,-65.339752),Base.Rotation(0.867316,0.419672,0.000000,0.267654))
App.ActiveDocument.addObject("Part::Cylinder","C679")
App.ActiveDocument.C679.Radius=0.688741
App.ActiveDocument.C679.Height=20.00
App.ActiveDocument.C679.Angle=360.00 
App.ActiveDocument.C679.Placement=Base.Placement(Base.Vector(12.024370,111.487900,-63.358545),Base.Rotation(0.873797,0.386665,0.000000,0.294905))
App.ActiveDocument.addObject("Part::Cylinder","C680")
App.ActiveDocument.C680.Radius=0.682470
App.ActiveDocument.C680.Height=20.00
App.ActiveDocument.C680.Angle=360.00 
App.ActiveDocument.C680.Placement=Base.Placement(Base.Vector(12.295147,108.422409,-61.077518),Base.Rotation(0.894186,0.290176,0.000000,0.340924))
App.ActiveDocument.addObject("Part::Cylinder","C681")
App.ActiveDocument.C681.Radius=0.534569
App.ActiveDocument.C681.Height=20.00
App.ActiveDocument.C681.Angle=360.00 
App.ActiveDocument.C681.Placement=Base.Placement(Base.Vector(16.291605,203.916553,-4.303055),Base.Rotation(-0.684984,0.216363,0.000000,0.695689))
App.ActiveDocument.addObject("Part::Cylinder","C682")
App.ActiveDocument.C682.Radius=0.544846
App.ActiveDocument.C682.Height=20.00
App.ActiveDocument.C682.Angle=360.00 
App.ActiveDocument.C682.Placement=Base.Placement(Base.Vector(16.519850,203.621333,-8.751361),Base.Rotation(-0.696718,0.217010,0.000000,0.683733))
App.ActiveDocument.addObject("Part::Cylinder","C683")
App.ActiveDocument.C683.Radius=0.555622
App.ActiveDocument.C683.Height=20.00
App.ActiveDocument.C683.Angle=360.00 
App.ActiveDocument.C683.Placement=Base.Placement(Base.Vector(16.606543,203.199737,-13.275188),Base.Rotation(-0.710486,0.214750,0.000000,0.670143))
App.ActiveDocument.addObject("Part::Cylinder","C684")
App.ActiveDocument.C684.Radius=0.565993
App.ActiveDocument.C684.Height=20.00
App.ActiveDocument.C684.Angle=360.00 
App.ActiveDocument.C684.Placement=Base.Placement(Base.Vector(16.511288,202.689304,-17.516950),Base.Rotation(-0.723550,0.213992,0.000000,0.656264))
App.ActiveDocument.addObject("Part::Cylinder","C685")
App.ActiveDocument.C685.Radius=0.575705
App.ActiveDocument.C685.Height=20.00
App.ActiveDocument.C685.Angle=360.00 
App.ActiveDocument.C685.Placement=Base.Placement(Base.Vector(17.028217,201.804059,-21.849886),Base.Rotation(-0.735009,0.224699,0.000000,0.639744))
App.ActiveDocument.addObject("Part::Cylinder","C686")
App.ActiveDocument.C686.Radius=0.587239
App.ActiveDocument.C686.Height=20.00
App.ActiveDocument.C686.Angle=360.00 
App.ActiveDocument.C686.Placement=Base.Placement(Base.Vector(16.507401,201.016025,-26.204463),Base.Rotation(-0.752576,0.220755,0.000000,0.620401))
App.ActiveDocument.addObject("Part::Cylinder","C687")
App.ActiveDocument.C687.Radius=0.597097
App.ActiveDocument.C687.Height=20.00
App.ActiveDocument.C687.Angle=360.00 
App.ActiveDocument.C687.Placement=Base.Placement(Base.Vector(16.775015,199.800026,-30.401372),Base.Rotation(-0.765055,0.228298,0.000000,0.602138))
App.ActiveDocument.addObject("Part::Cylinder","C688")
App.ActiveDocument.C688.Radius=0.607185
App.ActiveDocument.C688.Height=20.00
App.ActiveDocument.C688.Angle=360.00 
App.ActiveDocument.C688.Placement=Base.Placement(Base.Vector(16.849578,198.413233,-34.495188),Base.Rotation(-0.779358,0.239518,0.000000,0.578992))
App.ActiveDocument.addObject("Part::Cylinder","C689")
App.ActiveDocument.C689.Radius=0.616589
App.ActiveDocument.C689.Height=20.00
App.ActiveDocument.C689.Angle=360.00 
App.ActiveDocument.C689.Placement=Base.Placement(Base.Vector(17.015424,196.850102,-38.198554),Base.Rotation(-0.797205,0.246924,0.000000,0.550902))
App.ActiveDocument.addObject("Part::Cylinder","C690")
App.ActiveDocument.C690.Radius=0.626508
App.ActiveDocument.C690.Height=20.00
App.ActiveDocument.C690.Angle=360.00 
App.ActiveDocument.C690.Placement=Base.Placement(Base.Vector(16.862588,195.138108,-41.649146),Base.Rotation(-0.821992,0.255558,0.000000,0.508939))
App.ActiveDocument.addObject("Part::Cylinder","C691")
App.ActiveDocument.C691.Radius=0.635401
App.ActiveDocument.C691.Height=20.00
App.ActiveDocument.C691.Angle=360.00 
App.ActiveDocument.C691.Placement=Base.Placement(Base.Vector(17.280214,192.810152,-45.041245),Base.Rotation(-0.842436,0.272132,0.000000,0.465022))
App.ActiveDocument.addObject("Part::Cylinder","C692")
App.ActiveDocument.C692.Radius=0.643938
App.ActiveDocument.C692.Height=20.00
App.ActiveDocument.C692.Angle=360.00 
App.ActiveDocument.C692.Placement=Base.Placement(Base.Vector(16.998639,190.598583,-47.912320),Base.Rotation(-0.861963,0.278087,0.000000,0.423895))
App.ActiveDocument.addObject("Part::Cylinder","C693")
App.ActiveDocument.C693.Radius=0.650582
App.ActiveDocument.C693.Height=20.00
App.ActiveDocument.C693.Angle=360.00 
App.ActiveDocument.C693.Placement=Base.Placement(Base.Vector(17.462687,187.848847,-50.632287),Base.Rotation(-0.870134,0.303243,0.000000,0.388472))
App.ActiveDocument.addObject("Part::Cylinder","C694")
App.ActiveDocument.C694.Radius=0.657727
App.ActiveDocument.C694.Height=20.00
App.ActiveDocument.C694.Angle=360.00 
App.ActiveDocument.C694.Placement=Base.Placement(Base.Vector(17.401090,184.904515,-53.273410),Base.Rotation(-0.875121,0.333243,0.000000,0.350874))
App.ActiveDocument.addObject("Part::Cylinder","C695")
App.ActiveDocument.C695.Radius=0.663896
App.ActiveDocument.C695.Height=20.00
App.ActiveDocument.C695.Angle=360.00 
App.ActiveDocument.C695.Placement=Base.Placement(Base.Vector(17.492790,181.746719,-55.580114),Base.Rotation(-0.872023,0.379675,0.000000,0.308906))
App.ActiveDocument.addObject("Part::Cylinder","C696")
App.ActiveDocument.C696.Radius=0.669803
App.ActiveDocument.C696.Height=20.00
App.ActiveDocument.C696.Angle=360.00 
App.ActiveDocument.C696.Placement=Base.Placement(Base.Vector(17.298731,178.396924,-57.652117),Base.Rotation(-0.865283,0.422543,0.000000,0.269707))
App.ActiveDocument.addObject("Part::Cylinder","C697")
App.ActiveDocument.C697.Radius=0.675038
App.ActiveDocument.C697.Height=20.00
App.ActiveDocument.C697.Angle=360.00 
App.ActiveDocument.C697.Placement=Base.Placement(Base.Vector(17.104449,174.641843,-59.559684),Base.Rotation(-0.850847,0.468435,0.000000,0.237965))
App.ActiveDocument.addObject("Part::Cylinder","C698")
App.ActiveDocument.C698.Radius=0.679847
App.ActiveDocument.C698.Height=20.00
App.ActiveDocument.C698.Angle=360.00 
App.ActiveDocument.C698.Placement=Base.Placement(Base.Vector(16.659519,170.719783,-61.341125),Base.Rotation(-0.827904,0.515743,0.000000,0.220418))
App.ActiveDocument.addObject("Part::Cylinder","C699")
App.ActiveDocument.C699.Radius=0.682735
App.ActiveDocument.C699.Height=20.00
App.ActiveDocument.C699.Angle=360.00 
App.ActiveDocument.C699.Placement=Base.Placement(Base.Vector(16.829202,166.772525,-62.822195),Base.Rotation(-0.781481,0.586536,0.000000,0.212752))
App.ActiveDocument.addObject("Part::Cylinder","C700")
App.ActiveDocument.C700.Radius=0.685867
App.ActiveDocument.C700.Height=20.00
App.ActiveDocument.C700.Angle=360.00 
App.ActiveDocument.C700.Placement=Base.Placement(Base.Vector(16.789025,162.609229,-64.270967),Base.Rotation(-0.718525,0.665045,0.000000,0.203558))
App.ActiveDocument.addObject("Part::Cylinder","C701")
App.ActiveDocument.C701.Radius=0.688889
App.ActiveDocument.C701.Height=20.00
App.ActiveDocument.C701.Angle=360.00 
App.ActiveDocument.C701.Placement=Base.Placement(Base.Vector(16.584531,158.431863,-65.568978),Base.Rotation(-0.636907,0.745943,0.000000,0.194726))
App.ActiveDocument.addObject("Part::Cylinder","C702")
App.ActiveDocument.C702.Radius=0.691327
App.ActiveDocument.C702.Height=20.00
App.ActiveDocument.C702.Angle=360.00 
App.ActiveDocument.C702.Placement=Base.Placement(Base.Vector(16.408640,154.263053,-66.643838),Base.Rotation(-0.531722,0.825722,0.000000,0.188296))
App.ActiveDocument.addObject("Part::Cylinder","C703")
App.ActiveDocument.C703.Radius=0.693013
App.ActiveDocument.C703.Height=20.00
App.ActiveDocument.C703.Angle=360.00 
App.ActiveDocument.C703.Placement=Base.Placement(Base.Vector(16.430425,150.090890,-67.449729),Base.Rotation(-0.441571,0.878329,0.000000,0.183174))
App.ActiveDocument.addObject("Part::Cylinder","C704")
App.ActiveDocument.C704.Radius=0.694343
App.ActiveDocument.C704.Height=20.00
App.ActiveDocument.C704.Angle=360.00 
App.ActiveDocument.C704.Placement=Base.Placement(Base.Vector(16.424781,145.680725,-68.127855),Base.Rotation(-0.334128,0.924825,0.000000,0.181817))
App.ActiveDocument.addObject("Part::Cylinder","C705")
App.ActiveDocument.C705.Radius=0.695703
App.ActiveDocument.C705.Height=20.00
App.ActiveDocument.C705.Angle=360.00 
App.ActiveDocument.C705.Placement=Base.Placement(Base.Vector(16.308845,141.438220,-68.640625),Base.Rotation(-0.241691,0.954165,0.000000,0.176506))
App.ActiveDocument.addObject("Part::Cylinder","C706")
App.ActiveDocument.C706.Radius=0.696426
App.ActiveDocument.C706.Height=20.00
App.ActiveDocument.C706.Angle=360.00 
App.ActiveDocument.C706.Placement=Base.Placement(Base.Vector(16.333046,137.135309,-68.913152),Base.Rotation(-0.124277,0.977564,0.000000,0.170071))
App.ActiveDocument.addObject("Part::Cylinder","C707")
App.ActiveDocument.C707.Radius=0.696949
App.ActiveDocument.C707.Height=20.00
App.ActiveDocument.C707.Angle=360.00 
App.ActiveDocument.C707.Placement=Base.Placement(Base.Vector(16.209328,132.947647,-69.017734),Base.Rotation(0.036349,0.985441,0.000000,0.166084))
App.ActiveDocument.addObject("Part::Cylinder","C708")
App.ActiveDocument.C708.Radius=0.696924
App.ActiveDocument.C708.Height=20.00
App.ActiveDocument.C708.Angle=360.00 
App.ActiveDocument.C708.Placement=Base.Placement(Base.Vector(15.999060,128.583834,-68.913069),Base.Rotation(0.238153,0.956036,0.000000,0.171112))
App.ActiveDocument.addObject("Part::Cylinder","C709")
App.ActiveDocument.C709.Radius=0.695601
App.ActiveDocument.C709.Height=20.00
App.ActiveDocument.C709.Angle=360.00 
App.ActiveDocument.C709.Placement=Base.Placement(Base.Vector(15.795885,125.335033,-68.555501),Base.Rotation(0.543322,0.813076,0.000000,0.209068))
App.ActiveDocument.addObject("Part::Cylinder","C710")
App.ActiveDocument.C710.Radius=0.691854
App.ActiveDocument.C710.Height=20.00
App.ActiveDocument.C710.Angle=360.00 
App.ActiveDocument.C710.Placement=Base.Placement(Base.Vector(15.985402,121.958815,-67.382119),Base.Rotation(0.694331,0.673661,0.000000,0.253151))
App.ActiveDocument.addObject("Part::Cylinder","C711")
App.ActiveDocument.C711.Radius=0.688265
App.ActiveDocument.C711.Height=20.00
App.ActiveDocument.C711.Angle=360.00 
App.ActiveDocument.C711.Placement=Base.Placement(Base.Vector(15.833680,118.246363,-65.782269),Base.Rotation(0.744338,0.610450,0.000000,0.270762))
App.ActiveDocument.addObject("Part::Cylinder","C712")
App.ActiveDocument.C712.Radius=0.683796
App.ActiveDocument.C712.Height=20.00
App.ActiveDocument.C712.Angle=360.00 
App.ActiveDocument.C712.Placement=Base.Placement(Base.Vector(15.917233,114.785955,-63.975090),Base.Rotation(0.784789,0.546643,0.000000,0.292041))
App.ActiveDocument.addObject("Part::Cylinder","C713")
App.ActiveDocument.C713.Radius=0.678601
App.ActiveDocument.C713.Height=20.00
App.ActiveDocument.C713.Angle=360.00 
App.ActiveDocument.C713.Placement=Base.Placement(Base.Vector(15.793355,111.296849,-61.933914),Base.Rotation(0.802660,0.502038,0.000000,0.322017))
App.ActiveDocument.addObject("Part::Cylinder","C714")
App.ActiveDocument.C714.Radius=0.672837
App.ActiveDocument.C714.Height=20.00
App.ActiveDocument.C714.Angle=360.00 
App.ActiveDocument.C714.Placement=Base.Placement(Base.Vector(15.911329,108.286227,-59.729394),Base.Rotation(0.833582,0.421463,0.000000,0.357085))
App.ActiveDocument.addObject("Part::Cylinder","C715")
App.ActiveDocument.C715.Radius=0.528303
App.ActiveDocument.C715.Height=20.00
App.ActiveDocument.C715.Angle=360.00 
App.ActiveDocument.C715.Placement=Base.Placement(Base.Vector(19.948792,202.607292,-4.188226),Base.Rotation(-0.663305,0.268015,0.000000,0.698709))
App.ActiveDocument.addObject("Part::Cylinder","C716")
App.ActiveDocument.C716.Radius=0.538647
App.ActiveDocument.C716.Height=20.00
App.ActiveDocument.C716.Angle=360.00 
App.ActiveDocument.C716.Placement=Base.Placement(Base.Vector(20.307768,202.269148,-8.783286),Base.Rotation(-0.673186,0.274071,0.000000,0.686808))
App.ActiveDocument.addObject("Part::Cylinder","C717")
App.ActiveDocument.C717.Radius=0.549479
App.ActiveDocument.C717.Height=20.00
App.ActiveDocument.C717.Angle=360.00 
App.ActiveDocument.C717.Placement=Base.Placement(Base.Vector(20.322387,201.899823,-13.318029),Base.Rotation(-0.686078,0.273990,0.000000,0.673963))
App.ActiveDocument.addObject("Part::Cylinder","C718")
App.ActiveDocument.C718.Radius=0.559775
App.ActiveDocument.C718.Height=20.00
App.ActiveDocument.C718.Angle=360.00 
App.ActiveDocument.C718.Placement=Base.Placement(Base.Vector(20.381165,201.359467,-17.600566),Base.Rotation(-0.699480,0.276462,0.000000,0.659011))
App.ActiveDocument.addObject("Part::Cylinder","C719")
App.ActiveDocument.C719.Radius=0.569689
App.ActiveDocument.C719.Height=20.00
App.ActiveDocument.C719.Angle=360.00 
App.ActiveDocument.C719.Placement=Base.Placement(Base.Vector(20.874266,200.427488,-22.002268),Base.Rotation(-0.710282,0.287251,0.000000,0.642640))
App.ActiveDocument.addObject("Part::Cylinder","C720")
App.ActiveDocument.C720.Radius=0.581036
App.ActiveDocument.C720.Height=20.00
App.ActiveDocument.C720.Angle=360.00 
App.ActiveDocument.C720.Placement=Base.Placement(Base.Vector(20.320569,199.727428,-26.237905),Base.Rotation(-0.728906,0.282479,0.000000,0.623620))
App.ActiveDocument.addObject("Part::Cylinder","C721")
App.ActiveDocument.C721.Radius=0.590833
App.ActiveDocument.C721.Height=20.00
App.ActiveDocument.C721.Angle=360.00 
App.ActiveDocument.C721.Placement=Base.Placement(Base.Vector(20.611216,198.484146,-30.402919),Base.Rotation(-0.740517,0.294410,0.000000,0.604117))
App.ActiveDocument.addObject("Part::Cylinder","C722")
App.ActiveDocument.C722.Radius=0.600023
App.ActiveDocument.C722.Height=20.00
App.ActiveDocument.C722.Angle=360.00 
App.ActiveDocument.C722.Placement=Base.Placement(Base.Vector(20.890955,197.078091,-34.279868),Base.Rotation(-0.751883,0.305526,0.000000,0.584231))
App.ActiveDocument.addObject("Part::Cylinder","C723")
App.ActiveDocument.C723.Radius=0.609998
App.ActiveDocument.C723.Height=20.00
App.ActiveDocument.C723.Angle=360.00 
App.ActiveDocument.C723.Placement=Base.Placement(Base.Vector(20.887117,195.550808,-38.021717),Base.Rotation(-0.771044,0.319097,0.000000,0.551060))
App.ActiveDocument.addObject("Part::Cylinder","C724")
App.ActiveDocument.C724.Radius=0.620350
App.ActiveDocument.C724.Height=20.00
App.ActiveDocument.C724.Angle=360.00 
App.ActiveDocument.C724.Placement=Base.Placement(Base.Vector(20.757294,193.687255,-41.749009),Base.Rotation(-0.793086,0.328013,0.000000,0.513247))
App.ActiveDocument.addObject("Part::Cylinder","C725")
App.ActiveDocument.C725.Radius=0.628493
App.ActiveDocument.C725.Height=20.00
App.ActiveDocument.C725.Angle=360.00 
App.ActiveDocument.C725.Placement=Base.Placement(Base.Vector(21.238086,191.436100,-44.878835),Base.Rotation(-0.808018,0.354438,0.000000,0.470617))
App.ActiveDocument.addObject("Part::Cylinder","C726")
App.ActiveDocument.C726.Radius=0.637168
App.ActiveDocument.C726.Height=20.00
App.ActiveDocument.C726.Angle=360.00 
App.ActiveDocument.C726.Placement=Base.Placement(Base.Vector(20.969346,189.186133,-47.810056),Base.Rotation(-0.824323,0.369148,0.000000,0.429210))
App.ActiveDocument.addObject("Part::Cylinder","C727")
App.ActiveDocument.C727.Radius=0.643687
App.ActiveDocument.C727.Height=20.00
App.ActiveDocument.C727.Angle=360.00 
App.ActiveDocument.C727.Placement=Base.Placement(Base.Vector(21.484537,186.301493,-50.519081),Base.Rotation(-0.822934,0.410279,0.000000,0.393002))
App.ActiveDocument.addObject("Part::Cylinder","C728")
App.ActiveDocument.C728.Radius=0.650442
App.ActiveDocument.C728.Height=20.00
App.ActiveDocument.C728.Angle=360.00 
App.ActiveDocument.C728.Placement=Base.Placement(Base.Vector(21.461848,183.423320,-53.000277),Base.Rotation(-0.819660,0.448834,0.000000,0.355957))
App.ActiveDocument.addObject("Part::Cylinder","C729")
App.ActiveDocument.C729.Radius=0.656337
App.ActiveDocument.C729.Height=20.00
App.ActiveDocument.C729.Angle=360.00 
App.ActiveDocument.C729.Placement=Base.Placement(Base.Vector(21.657228,180.221141,-55.197241),Base.Rotation(-0.810537,0.493634,0.000000,0.315207))
App.ActiveDocument.addObject("Part::Cylinder","C730")
App.ActiveDocument.C730.Radius=0.662144
App.ActiveDocument.C730.Height=20.00
App.ActiveDocument.C730.Angle=360.00 
App.ActiveDocument.C730.Placement=Base.Placement(Base.Vector(21.457927,176.933792,-57.176087),Base.Rotation(-0.800776,0.530505,0.000000,0.278068))
App.ActiveDocument.addObject("Part::Cylinder","C731")
App.ActiveDocument.C731.Radius=0.667428
App.ActiveDocument.C731.Height=20.00
App.ActiveDocument.C731.Angle=360.00 
App.ActiveDocument.C731.Placement=Base.Placement(Base.Vector(21.158904,173.283928,-59.015475),Base.Rotation(-0.773903,0.583463,0.000000,0.246263))
App.ActiveDocument.addObject("Part::Cylinder","C732")
App.ActiveDocument.C732.Radius=0.671611
App.ActiveDocument.C732.Height=20.00
App.ActiveDocument.C732.Angle=360.00 
App.ActiveDocument.C732.Placement=Base.Placement(Base.Vector(20.841088,169.601065,-60.597028),Base.Rotation(-0.730647,0.643335,0.000000,0.228637))
App.ActiveDocument.addObject("Part::Cylinder","C733")
App.ActiveDocument.C733.Radius=0.673997
App.ActiveDocument.C733.Height=20.00
App.ActiveDocument.C733.Angle=360.00 
App.ActiveDocument.C733.Placement=Base.Placement(Base.Vector(20.984313,165.731438,-61.900110),Base.Rotation(-0.650298,0.726120,0.000000,0.223298))
App.ActiveDocument.addObject("Part::Cylinder","C734")
App.ActiveDocument.C734.Radius=0.677050
App.ActiveDocument.C734.Height=20.00
App.ActiveDocument.C734.Angle=360.00 
App.ActiveDocument.C734.Placement=Base.Placement(Base.Vector(20.661446,161.586845,-63.261151),Base.Rotation(-0.554413,0.802256,0.000000,0.221384))
App.ActiveDocument.addObject("Part::Cylinder","C735")
App.ActiveDocument.C735.Radius=0.679754
App.ActiveDocument.C735.Height=20.00
App.ActiveDocument.C735.Angle=360.00 
App.ActiveDocument.C735.Placement=Base.Placement(Base.Vector(20.341782,157.309841,-64.465787),Base.Rotation(-0.461538,0.858803,0.000000,0.222352))
App.ActiveDocument.addObject("Part::Cylinder","C736")
App.ActiveDocument.C736.Radius=0.681777
App.ActiveDocument.C736.Height=20.00
App.ActiveDocument.C736.Angle=360.00 
App.ActiveDocument.C736.Placement=Base.Placement(Base.Vector(20.220575,153.075130,-65.402367),Base.Rotation(-0.384415,0.896099,0.000000,0.221882))
App.ActiveDocument.addObject("Part::Cylinder","C737")
App.ActiveDocument.C737.Radius=0.683403
App.ActiveDocument.C737.Height=20.00
App.ActiveDocument.C737.Angle=360.00 
App.ActiveDocument.C737.Placement=Base.Placement(Base.Vector(20.053992,148.845961,-66.200477),Base.Rotation(-0.296475,0.928013,0.000000,0.225599))
App.ActiveDocument.addObject("Part::Cylinder","C738")
App.ActiveDocument.C738.Radius=0.684349
App.ActiveDocument.C738.Height=20.00
App.ActiveDocument.C738.Angle=360.00 
App.ActiveDocument.C738.Placement=Base.Placement(Base.Vector(20.146991,144.561863,-66.731722),Base.Rotation(-0.229487,0.946869,0.000000,0.225335))
App.ActiveDocument.addObject("Part::Cylinder","C739")
App.ActiveDocument.C739.Radius=0.685654
App.ActiveDocument.C739.Height=20.00
App.ActiveDocument.C739.Angle=360.00 
App.ActiveDocument.C739.Placement=Base.Placement(Base.Vector(19.900260,140.424478,-67.248346),Base.Rotation(-0.157766,0.961031,0.000000,0.227001))
App.ActiveDocument.addObject("Part::Cylinder","C740")
App.ActiveDocument.C740.Radius=0.686453
App.ActiveDocument.C740.Height=20.00
App.ActiveDocument.C740.Angle=360.00 
App.ActiveDocument.C740.Placement=Base.Placement(Base.Vector(19.832101,136.164584,-67.500869),Base.Rotation(-0.047841,0.973881,0.000000,0.221964))
App.ActiveDocument.addObject("Part::Cylinder","C741")
App.ActiveDocument.C741.Radius=0.686939
App.ActiveDocument.C741.Height=20.00
App.ActiveDocument.C741.Angle=360.00 
App.ActiveDocument.C741.Placement=Base.Placement(Base.Vector(19.511937,132.064321,-67.649466),Base.Rotation(0.043551,0.972703,0.000000,0.227932))
App.ActiveDocument.addObject("Part::Cylinder","C742")
App.ActiveDocument.C742.Radius=0.686260
App.ActiveDocument.C742.Height=20.00
App.ActiveDocument.C742.Angle=360.00 
App.ActiveDocument.C742.Placement=Base.Placement(Base.Vector(19.286233,128.085168,-67.503510),Base.Rotation(0.237194,0.939632,0.000000,0.246640))
App.ActiveDocument.addObject("Part::Cylinder","C743")
App.ActiveDocument.C743.Radius=0.684644
App.ActiveDocument.C743.Height=20.00
App.ActiveDocument.C743.Angle=360.00 
App.ActiveDocument.C743.Placement=Base.Placement(Base.Vector(19.264482,124.781828,-66.895667),Base.Rotation(0.455390,0.849470,0.000000,0.266499))
App.ActiveDocument.addObject("Part::Cylinder","C744")
App.ActiveDocument.C744.Radius=0.681091
App.ActiveDocument.C744.Height=20.00
App.ActiveDocument.C744.Angle=360.00 
App.ActiveDocument.C744.Placement=Base.Placement(Base.Vector(19.512899,121.403459,-65.541165),Base.Rotation(0.591860,0.753112,0.000000,0.287271))
App.ActiveDocument.addObject("Part::Cylinder","C745")
App.ActiveDocument.C745.Radius=0.677223
App.ActiveDocument.C745.Height=20.00
App.ActiveDocument.C745.Angle=360.00 
App.ActiveDocument.C745.Placement=Base.Placement(Base.Vector(19.388966,117.925599,-63.977084),Base.Rotation(0.653252,0.690252,0.000000,0.311149))
App.ActiveDocument.addObject("Part::Cylinder","C746")
App.ActiveDocument.C746.Radius=0.672144
App.ActiveDocument.C746.Height=20.00
App.ActiveDocument.C746.Angle=360.00 
App.ActiveDocument.C746.Placement=Base.Placement(Base.Vector(19.205867,114.221540,-62.063870),Base.Rotation(0.673857,0.655234,0.000000,0.341446))
App.ActiveDocument.addObject("Part::Cylinder","C747")
App.ActiveDocument.C747.Radius=0.666845
App.ActiveDocument.C747.Height=20.00
App.ActiveDocument.C747.Angle=360.00 
App.ActiveDocument.C747.Placement=Base.Placement(Base.Vector(19.144616,110.793597,-59.913331),Base.Rotation(0.692639,0.624518,0.000000,0.360872))
App.ActiveDocument.addObject("Part::Cylinder","C748")
App.ActiveDocument.C748.Radius=0.662238
App.ActiveDocument.C748.Height=20.00
App.ActiveDocument.C748.Angle=360.00 
App.ActiveDocument.C748.Placement=Base.Placement(Base.Vector(19.609794,108.961766,-58.807492),Base.Rotation(0.812041,0.374544,0.000000,0.447555))
App.ActiveDocument.addObject("Part::Cylinder","C749")
App.ActiveDocument.C749.Radius=0.522033
App.ActiveDocument.C749.Height=20.00
App.ActiveDocument.C749.Angle=360.00 
App.ActiveDocument.C749.Placement=Base.Placement(Base.Vector(23.896795,200.831683,-4.164849),Base.Rotation(-0.641305,0.311591,0.000000,0.701170))
App.ActiveDocument.addObject("Part::Cylinder","C750")
App.ActiveDocument.C750.Radius=0.532648
App.ActiveDocument.C750.Height=20.00
App.ActiveDocument.C750.Angle=360.00 
App.ActiveDocument.C750.Placement=Base.Placement(Base.Vector(24.151924,200.545860,-8.818270),Base.Rotation(-0.651221,0.316569,0.000000,0.689707))
App.ActiveDocument.addObject("Part::Cylinder","C751")
App.ActiveDocument.C751.Radius=0.543400
App.ActiveDocument.C751.Height=20.00
App.ActiveDocument.C751.Angle=360.00 
App.ActiveDocument.C751.Placement=Base.Placement(Base.Vector(24.245446,200.164689,-13.370621),Base.Rotation(-0.663468,0.319603,0.000000,0.676509))
App.ActiveDocument.addObject("Part::Cylinder","C752")
App.ActiveDocument.C752.Radius=0.553651
App.ActiveDocument.C752.Height=20.00
App.ActiveDocument.C752.Angle=360.00 
App.ActiveDocument.C752.Placement=Base.Placement(Base.Vector(24.372229,199.601534,-17.661320),Base.Rotation(-0.676682,0.324804,0.000000,0.660760))
App.ActiveDocument.addObject("Part::Cylinder","C753")
App.ActiveDocument.C753.Radius=0.563652
App.ActiveDocument.C753.Height=20.00
App.ActiveDocument.C753.Angle=360.00 
App.ActiveDocument.C753.Placement=Base.Placement(Base.Vector(24.813020,198.666047,-22.043703),Base.Rotation(-0.688443,0.332325,0.000000,0.644675))
App.ActiveDocument.addObject("Part::Cylinder","C754")
App.ActiveDocument.C754.Radius=0.574703
App.ActiveDocument.C754.Height=20.00
App.ActiveDocument.C754.Angle=360.00 
App.ActiveDocument.C754.Placement=Base.Placement(Base.Vector(24.198483,198.060486,-26.164081),Base.Rotation(-0.704270,0.334525,0.000000,0.626176))
App.ActiveDocument.addObject("Part::Cylinder","C755")
App.ActiveDocument.C755.Radius=0.583852
App.ActiveDocument.C755.Height=20.00
App.ActiveDocument.C755.Angle=360.00 
App.ActiveDocument.C755.Placement=Base.Placement(Base.Vector(24.640811,196.766589,-30.129780),Base.Rotation(-0.714090,0.349737,0.000000,0.606431))
App.ActiveDocument.addObject("Part::Cylinder","C756")
App.ActiveDocument.C756.Radius=0.593318
App.ActiveDocument.C756.Height=20.00
App.ActiveDocument.C756.Angle=360.00 
App.ActiveDocument.C756.Placement=Base.Placement(Base.Vector(24.834517,195.342924,-34.077447),Base.Rotation(-0.723436,0.365219,0.000000,0.585880))
App.ActiveDocument.addObject("Part::Cylinder","C757")
App.ActiveDocument.C757.Radius=0.603503
App.ActiveDocument.C757.Height=20.00
App.ActiveDocument.C757.Angle=360.00 
App.ActiveDocument.C757.Placement=Base.Placement(Base.Vector(24.659093,193.836830,-37.927417),Base.Rotation(-0.737283,0.382038,0.000000,0.557190))
App.ActiveDocument.addObject("Part::Cylinder","C758")
App.ActiveDocument.C758.Radius=0.613325
App.ActiveDocument.C758.Height=20.00
App.ActiveDocument.C758.Angle=360.00 
App.ActiveDocument.C758.Placement=Base.Placement(Base.Vector(24.580079,192.011307,-41.512793),Base.Rotation(-0.752712,0.403078,0.000000,0.520531))
App.ActiveDocument.addObject("Part::Cylinder","C759")
App.ActiveDocument.C759.Radius=0.621176
App.ActiveDocument.C759.Height=20.00
App.ActiveDocument.C759.Angle=360.00 
App.ActiveDocument.C759.Placement=Base.Placement(Base.Vector(24.957122,189.822675,-44.534513),Base.Rotation(-0.760814,0.434166,0.000000,0.482351))
App.ActiveDocument.addObject("Part::Cylinder","C760")
App.ActiveDocument.C760.Radius=0.629743
App.ActiveDocument.C760.Height=20.00
App.ActiveDocument.C760.Angle=360.00 
App.ActiveDocument.C760.Placement=Base.Placement(Base.Vector(24.755145,187.586085,-47.431052),Base.Rotation(-0.768200,0.466749,0.000000,0.438194))
App.ActiveDocument.addObject("Part::Cylinder","C761")
App.ActiveDocument.C761.Radius=0.636008
App.ActiveDocument.C761.Height=20.00
App.ActiveDocument.C761.Angle=360.00 
App.ActiveDocument.C761.Placement=Base.Placement(Base.Vector(25.256415,184.720357,-50.001692),Base.Rotation(-0.757777,0.513673,0.000000,0.402385))
App.ActiveDocument.addObject("Part::Cylinder","C762")
App.ActiveDocument.C762.Radius=0.642290
App.ActiveDocument.C762.Height=20.00
App.ActiveDocument.C762.Angle=360.00 
App.ActiveDocument.C762.Placement=Base.Placement(Base.Vector(25.337383,181.757278,-52.410327),Base.Rotation(-0.743454,0.556602,0.000000,0.370770))
App.ActiveDocument.addObject("Part::Cylinder","C763")
App.ActiveDocument.C763.Radius=0.648225
App.ActiveDocument.C763.Height=20.00
App.ActiveDocument.C763.Angle=360.00 
App.ActiveDocument.C763.Placement=Base.Placement(Base.Vector(25.372910,178.630288,-54.528398),Base.Rotation(-0.723237,0.605251,0.000000,0.332566))
App.ActiveDocument.addObject("Part::Cylinder","C764")
App.ActiveDocument.C764.Radius=0.653915
App.ActiveDocument.C764.Height=20.00
App.ActiveDocument.C764.Angle=360.00 
App.ActiveDocument.C764.Placement=Base.Placement(Base.Vector(25.111549,175.326675,-56.503196),Base.Rotation(-0.686543,0.662511,0.000000,0.299561))
App.ActiveDocument.addObject("Part::Cylinder","C765")
App.ActiveDocument.C765.Radius=0.658597
App.ActiveDocument.C765.Height=20.00
App.ActiveDocument.C765.Angle=360.00 
App.ActiveDocument.C765.Placement=Base.Placement(Base.Vector(24.893139,171.871274,-58.168244),Base.Rotation(-0.638376,0.719710,0.000000,0.272934))
App.ActiveDocument.addObject("Part::Cylinder","C766")
App.ActiveDocument.C766.Radius=0.662643
App.ActiveDocument.C766.Height=20.00
App.ActiveDocument.C766.Angle=360.00 
App.ActiveDocument.C766.Placement=Base.Placement(Base.Vector(24.658502,168.091917,-59.653679),Base.Rotation(-0.572633,0.779991,0.000000,0.252400))
App.ActiveDocument.addObject("Part::Cylinder","C767")
App.ActiveDocument.C767.Radius=0.665128
App.ActiveDocument.C767.Height=20.00
App.ActiveDocument.C767.Angle=360.00 
App.ActiveDocument.C767.Placement=Base.Placement(Base.Vector(24.665069,164.161851,-60.828176),Base.Rotation(-0.493090,0.834401,0.000000,0.246246))
App.ActiveDocument.addObject("Part::Cylinder","C768")
App.ActiveDocument.C768.Radius=0.667786
App.ActiveDocument.C768.Height=20.00
App.ActiveDocument.C768.Angle=360.00 
App.ActiveDocument.C768.Placement=Base.Placement(Base.Vector(24.416479,160.084016,-61.961792),Base.Rotation(-0.410694,0.878641,0.000000,0.243555))
App.ActiveDocument.addObject("Part::Cylinder","C769")
App.ActiveDocument.C769.Radius=0.669634
App.ActiveDocument.C769.Height=20.00
App.ActiveDocument.C769.Angle=360.00 
App.ActiveDocument.C769.Placement=Base.Placement(Base.Vector(24.294630,155.811815,-62.906458),Base.Rotation(-0.333369,0.909655,0.000000,0.247777))
App.ActiveDocument.addObject("Part::Cylinder","C770")
App.ActiveDocument.C770.Radius=0.671547
App.ActiveDocument.C770.Height=20.00
App.ActiveDocument.C770.Angle=360.00 
App.ActiveDocument.C770.Placement=Base.Placement(Base.Vector(23.995006,151.508218,-63.786817),Base.Rotation(-0.253527,0.933528,0.000000,0.253474))
App.ActiveDocument.addObject("Part::Cylinder","C771")
App.ActiveDocument.C771.Radius=0.672574
App.ActiveDocument.C771.Height=20.00
App.ActiveDocument.C771.Angle=360.00 
App.ActiveDocument.C771.Placement=Base.Placement(Base.Vector(23.949754,147.286669,-64.367318),Base.Rotation(-0.200226,0.945069,0.000000,0.258367))
App.ActiveDocument.addObject("Part::Cylinder","C772")
App.ActiveDocument.C772.Radius=0.673536
App.ActiveDocument.C772.Height=20.00
App.ActiveDocument.C772.Angle=360.00 
App.ActiveDocument.C772.Placement=Base.Placement(Base.Vector(23.661255,143.064904,-64.934193),Base.Rotation(-0.112725,0.956075,0.000000,0.270579))
App.ActiveDocument.addObject("Part::Cylinder","C773")
App.ActiveDocument.C773.Radius=0.674245
App.ActiveDocument.C773.Height=20.00
App.ActiveDocument.C773.Angle=360.00 
App.ActiveDocument.C773.Placement=Base.Placement(Base.Vector(23.442847,138.841537,-65.304099),Base.Rotation(-0.064896,0.958323,0.000000,0.278218))
App.ActiveDocument.addObject("Part::Cylinder","C774")
App.ActiveDocument.C774.Radius=0.675253
App.ActiveDocument.C774.Height=20.00
App.ActiveDocument.C774.Angle=360.00 
App.ActiveDocument.C774.Placement=Base.Placement(Base.Vector(22.920981,134.790439,-65.685669),Base.Rotation(0.016712,0.957246,0.000000,0.288792))
App.ActiveDocument.addObject("Part::Cylinder","C775")
App.ActiveDocument.C775.Radius=0.675161
App.ActiveDocument.C775.Height=20.00
App.ActiveDocument.C775.Angle=360.00 
App.ActiveDocument.C775.Placement=Base.Placement(Base.Vector(22.657439,130.918307,-65.708223),Base.Rotation(0.101478,0.948620,0.000000,0.299704))
App.ActiveDocument.addObject("Part::Cylinder","C776")
App.ActiveDocument.C776.Radius=0.674289
App.ActiveDocument.C776.Height=20.00
App.ActiveDocument.C776.Angle=360.00 
App.ActiveDocument.C776.Placement=Base.Placement(Base.Vector(22.304796,127.148388,-65.515465),Base.Rotation(0.244225,0.914456,0.000000,0.322682))
App.ActiveDocument.addObject("Part::Cylinder","C777")
App.ActiveDocument.C777.Radius=0.672404
App.ActiveDocument.C777.Height=20.00
App.ActiveDocument.C777.Angle=360.00 
App.ActiveDocument.C777.Placement=Base.Placement(Base.Vector(22.277082,123.795432,-64.710736),Base.Rotation(0.356293,0.873278,0.000000,0.332325))
App.ActiveDocument.addObject("Part::Cylinder","C778")
App.ActiveDocument.C778.Radius=0.668362
App.ActiveDocument.C778.Height=20.00
App.ActiveDocument.C778.Angle=360.00 
App.ActiveDocument.C778.Placement=Base.Placement(Base.Vector(22.547756,120.751060,-63.310979),Base.Rotation(0.458549,0.815211,0.000000,0.353784))
App.ActiveDocument.addObject("Part::Cylinder","C779")
App.ActiveDocument.C779.Radius=0.664806
App.ActiveDocument.C779.Height=20.00
App.ActiveDocument.C779.Angle=360.00 
App.ActiveDocument.C779.Placement=Base.Placement(Base.Vector(22.431082,117.238506,-61.635521),Base.Rotation(0.547208,0.752978,0.000000,0.365498))
App.ActiveDocument.addObject("Part::Cylinder","C780")
App.ActiveDocument.C780.Radius=0.659647
App.ActiveDocument.C780.Height=20.00
App.ActiveDocument.C780.Angle=360.00 
App.ActiveDocument.C780.Placement=Base.Placement(Base.Vector(22.788964,114.252448,-59.608309),Base.Rotation(0.592732,0.711418,0.000000,0.377562))
App.ActiveDocument.addObject("Part::Cylinder","C781")
App.ActiveDocument.C781.Radius=0.655075
App.ActiveDocument.C781.Height=20.00
App.ActiveDocument.C781.Angle=360.00 
App.ActiveDocument.C781.Placement=Base.Placement(Base.Vector(22.543756,110.703411,-57.449640),Base.Rotation(0.619387,0.683816,0.000000,0.385688))
App.ActiveDocument.addObject("Part::Cylinder","C782")
App.ActiveDocument.C782.Radius=0.651063
App.ActiveDocument.C782.Height=20.00
App.ActiveDocument.C782.Angle=360.00 
App.ActiveDocument.C782.Placement=Base.Placement(Base.Vector(23.471588,109.722230,-57.370625),Base.Rotation(0.787541,0.345100,0.000000,0.510574))
App.ActiveDocument.addObject("Part::Cylinder","C783")
App.ActiveDocument.C783.Radius=0.516239
App.ActiveDocument.C783.Height=20.00
App.ActiveDocument.C783.Angle=360.00 
App.ActiveDocument.C783.Placement=Base.Placement(Base.Vector(27.814036,198.802969,-4.197076),Base.Rotation(-0.624085,0.341729,0.000000,0.702666))
App.ActiveDocument.addObject("Part::Cylinder","C784")
App.ActiveDocument.C784.Radius=0.526600
App.ActiveDocument.C784.Height=20.00
App.ActiveDocument.C784.Angle=360.00 
App.ActiveDocument.C784.Placement=Base.Placement(Base.Vector(28.042137,198.541283,-8.735165),Base.Rotation(-0.633182,0.347286,0.000000,0.691718))
App.ActiveDocument.addObject("Part::Cylinder","C785")
App.ActiveDocument.C785.Radius=0.537415
App.ActiveDocument.C785.Height=20.00
App.ActiveDocument.C785.Angle=360.00 
App.ActiveDocument.C785.Placement=Base.Placement(Base.Vector(28.195811,198.138836,-13.377146),Base.Rotation(-0.643730,0.353706,0.000000,0.678604))
App.ActiveDocument.addObject("Part::Cylinder","C786")
App.ActiveDocument.C786.Radius=0.547679
App.ActiveDocument.C786.Height=20.00
App.ActiveDocument.C786.Angle=360.00 
App.ActiveDocument.C786.Placement=Base.Placement(Base.Vector(28.324222,197.577360,-17.691010),Base.Rotation(-0.655769,0.360878,0.000000,0.663124))
App.ActiveDocument.addObject("Part::Cylinder","C787")
App.ActiveDocument.C787.Radius=0.557760
App.ActiveDocument.C787.Height=20.00
App.ActiveDocument.C787.Angle=360.00 
App.ActiveDocument.C787.Placement=Base.Placement(Base.Vector(28.611840,196.704763,-21.999429),Base.Rotation(-0.666584,0.372571,0.000000,0.645645))
App.ActiveDocument.addObject("Part::Cylinder","C788")
App.ActiveDocument.C788.Radius=0.568404
App.ActiveDocument.C788.Height=20.00
App.ActiveDocument.C788.Angle=360.00 
App.ActiveDocument.C788.Placement=Base.Placement(Base.Vector(28.147062,196.065644,-26.050219),Base.Rotation(-0.680187,0.379610,0.000000,0.627089))
App.ActiveDocument.addObject("Part::Cylinder","C789")
App.ActiveDocument.C789.Radius=0.577451
App.ActiveDocument.C789.Height=20.00
App.ActiveDocument.C789.Angle=360.00 
App.ActiveDocument.C789.Placement=Base.Placement(Base.Vector(28.563618,194.726099,-29.996349),Base.Rotation(-0.686295,0.398956,0.000000,0.608140))
App.ActiveDocument.addObject("Part::Cylinder","C790")
App.ActiveDocument.C790.Radius=0.587176
App.ActiveDocument.C790.Height=20.00
App.ActiveDocument.C790.Angle=360.00 
App.ActiveDocument.C790.Placement=Base.Placement(Base.Vector(28.598227,193.331697,-33.933824),Base.Rotation(-0.693092,0.420622,0.000000,0.585406))
App.ActiveDocument.addObject("Part::Cylinder","C791")
App.ActiveDocument.C791.Radius=0.597158
App.ActiveDocument.C791.Height=20.00
App.ActiveDocument.C791.Angle=360.00 
App.ActiveDocument.C791.Placement=Base.Placement(Base.Vector(28.517282,191.691513,-37.822572),Base.Rotation(-0.701015,0.443244,0.000000,0.558671))
App.ActiveDocument.addObject("Part::Cylinder","C792")
App.ActiveDocument.C792.Radius=0.606522
App.ActiveDocument.C792.Height=20.00
App.ActiveDocument.C792.Angle=360.00 
App.ActiveDocument.C792.Placement=Base.Placement(Base.Vector(28.450762,189.888134,-41.188679),Base.Rotation(-0.710696,0.473654,0.000000,0.520156))
App.ActiveDocument.addObject("Part::Cylinder","C793")
App.ActiveDocument.C793.Radius=0.614644
App.ActiveDocument.C793.Height=20.00
App.ActiveDocument.C793.Angle=360.00 
App.ActiveDocument.C793.Placement=Base.Placement(Base.Vector(28.641157,187.607399,-44.305231),Base.Rotation(-0.704843,0.519314,0.000000,0.483228))
App.ActiveDocument.addObject("Part::Cylinder","C794")
App.ActiveDocument.C794.Radius=0.622308
App.ActiveDocument.C794.Height=20.00
App.ActiveDocument.C794.Angle=360.00 
App.ActiveDocument.C794.Placement=Base.Placement(Base.Vector(28.573243,185.323305,-47.038983),Base.Rotation(-0.702937,0.552741,0.000000,0.447613))
App.ActiveDocument.addObject("Part::Cylinder","C795")
App.ActiveDocument.C795.Radius=0.628316
App.ActiveDocument.C795.Height=20.00
App.ActiveDocument.C795.Angle=360.00 
App.ActiveDocument.C795.Placement=Base.Placement(Base.Vector(28.965244,182.495486,-49.434095),Base.Rotation(-0.683753,0.601114,0.000000,0.413695))
App.ActiveDocument.addObject("Part::Cylinder","C796")
App.ActiveDocument.C796.Radius=0.634636
App.ActiveDocument.C796.Height=20.00
App.ActiveDocument.C796.Angle=360.00 
App.ActiveDocument.C796.Placement=Base.Placement(Base.Vector(29.012487,179.438394,-51.790625),Base.Rotation(-0.657132,0.650739,0.000000,0.380416))
App.ActiveDocument.addObject("Part::Cylinder","C797")
App.ActiveDocument.C797.Radius=0.640604
App.ActiveDocument.C797.Height=20.00
App.ActiveDocument.C797.Angle=360.00 
App.ActiveDocument.C797.Placement=Base.Placement(Base.Vector(28.810661,176.309511,-53.898489),Base.Rotation(-0.615433,0.706978,0.000000,0.348459))
App.ActiveDocument.addObject("Part::Cylinder","C798")
App.ActiveDocument.C798.Radius=0.645608
App.ActiveDocument.C798.Height=20.00
App.ActiveDocument.C798.Angle=360.00 
App.ActiveDocument.C798.Placement=Base.Placement(Base.Vector(28.628224,173.022679,-55.690908),Base.Rotation(-0.571492,0.754275,0.000000,0.323212))
App.ActiveDocument.addObject("Part::Cylinder","C799")
App.ActiveDocument.C799.Radius=0.650125
App.ActiveDocument.C799.Height=20.00
App.ActiveDocument.C799.Angle=360.00 
App.ActiveDocument.C799.Placement=Base.Placement(Base.Vector(28.375908,169.657558,-57.216425),Base.Rotation(-0.508197,0.808482,0.000000,0.296803))
App.ActiveDocument.addObject("Part::Cylinder","C800")
App.ActiveDocument.C800.Radius=0.652859
App.ActiveDocument.C800.Height=20.00
App.ActiveDocument.C800.Angle=360.00 
App.ActiveDocument.C800.Placement=Base.Placement(Base.Vector(28.401461,165.997552,-58.396097),Base.Rotation(-0.425429,0.858915,0.000000,0.285087))
App.ActiveDocument.addObject("Part::Cylinder","C801")
App.ActiveDocument.C801.Radius=0.655373
App.ActiveDocument.C801.Height=20.00
App.ActiveDocument.C801.Angle=360.00 
App.ActiveDocument.C801.Placement=Base.Placement(Base.Vector(28.273037,162.068848,-59.487814),Base.Rotation(-0.344959,0.895687,0.000000,0.280621))
App.ActiveDocument.addObject("Part::Cylinder","C802")
App.ActiveDocument.C802.Radius=0.657741
App.ActiveDocument.C802.Height=20.00
App.ActiveDocument.C802.Angle=360.00 
App.ActiveDocument.C802.Placement=Base.Placement(Base.Vector(28.013849,158.033681,-60.466473),Base.Rotation(-0.267793,0.922110,0.000000,0.279284))
App.ActiveDocument.addObject("Part::Cylinder","C803")
App.ActiveDocument.C803.Radius=0.659287
App.ActiveDocument.C803.Height=20.00
App.ActiveDocument.C803.Angle=360.00 
App.ActiveDocument.C803.Placement=Base.Placement(Base.Vector(27.883000,153.955476,-61.188327),Base.Rotation(-0.209620,0.936370,0.000000,0.281551))
App.ActiveDocument.addObject("Part::Cylinder","C804")
App.ActiveDocument.C804.Radius=0.660564
App.ActiveDocument.C804.Height=20.00
App.ActiveDocument.C804.Angle=360.00 
App.ActiveDocument.C804.Placement=Base.Placement(Base.Vector(27.651328,149.828243,-61.818375),Base.Rotation(-0.148308,0.945938,0.000000,0.288454))
App.ActiveDocument.addObject("Part::Cylinder","C805")
App.ActiveDocument.C805.Radius=0.661516
App.ActiveDocument.C805.Height=20.00
App.ActiveDocument.C805.Angle=360.00 
App.ActiveDocument.C805.Placement=Base.Placement(Base.Vector(27.322282,145.777068,-62.349450),Base.Rotation(-0.080590,0.950346,0.000000,0.300578))
App.ActiveDocument.addObject("Part::Cylinder","C806")
App.ActiveDocument.C806.Radius=0.662059
App.ActiveDocument.C806.Height=20.00
App.ActiveDocument.C806.Angle=360.00 
App.ActiveDocument.C806.Placement=Base.Placement(Base.Vector(26.956945,141.802591,-62.749018),Base.Rotation(-0.021208,0.948330,0.000000,0.316577))
App.ActiveDocument.addObject("Part::Cylinder","C807")
App.ActiveDocument.C807.Radius=0.662757
App.ActiveDocument.C807.Height=20.00
App.ActiveDocument.C807.Angle=360.00 
App.ActiveDocument.C807.Placement=Base.Placement(Base.Vector(26.336882,137.455045,-63.190793),Base.Rotation(0.042644,0.940080,0.000000,0.338277))
App.ActiveDocument.addObject("Part::Cylinder","C808")
App.ActiveDocument.C808.Radius=0.663161
App.ActiveDocument.C808.Height=20.00
App.ActiveDocument.C808.Angle=360.00 
App.ActiveDocument.C808.Placement=Base.Placement(Base.Vector(25.839816,133.380480,-63.375439),Base.Rotation(0.089334,0.931868,0.000000,0.351626))
App.ActiveDocument.addObject("Part::Cylinder","C809")
App.ActiveDocument.C809.Radius=0.662085
App.ActiveDocument.C809.Height=20.00
App.ActiveDocument.C809.Angle=360.00 
App.ActiveDocument.C809.Placement=Base.Placement(Base.Vector(25.553295,129.324218,-63.167032),Base.Rotation(0.164552,0.913337,0.000000,0.372476))
App.ActiveDocument.addObject("Part::Cylinder","C810")
App.ActiveDocument.C810.Radius=0.660805
App.ActiveDocument.C810.Height=20.00
App.ActiveDocument.C810.Angle=360.00 
App.ActiveDocument.C810.Placement=Base.Placement(Base.Vector(25.419678,125.534550,-62.534699),Base.Rotation(0.237342,0.895402,0.000000,0.376729))
App.ActiveDocument.addObject("Part::Cylinder","C811")
App.ActiveDocument.C811.Radius=0.657452
App.ActiveDocument.C811.Height=20.00
App.ActiveDocument.C811.Angle=360.00 
App.ActiveDocument.C811.Placement=Base.Placement(Base.Vector(25.652687,122.528275,-61.349498),Base.Rotation(0.345552,0.852609,0.000000,0.391985))
App.ActiveDocument.addObject("Part::Cylinder","C812")
App.ActiveDocument.C812.Radius=0.654965
App.ActiveDocument.C812.Height=20.00
App.ActiveDocument.C812.Angle=360.00 
App.ActiveDocument.C812.Placement=Base.Placement(Base.Vector(25.407424,119.416847,-60.191747),Base.Rotation(0.395362,0.826152,0.000000,0.401449))
App.ActiveDocument.addObject("Part::Cylinder","C813")
App.ActiveDocument.C813.Radius=0.649996
App.ActiveDocument.C813.Height=20.00
App.ActiveDocument.C813.Angle=360.00 
App.ActiveDocument.C813.Placement=Base.Placement(Base.Vector(25.753980,116.594780,-58.377215),Base.Rotation(0.434639,0.799046,0.000000,0.415468))
App.ActiveDocument.addObject("Part::Cylinder","C814")
App.ActiveDocument.C814.Radius=0.646208
App.ActiveDocument.C814.Height=20.00
App.ActiveDocument.C814.Angle=360.00 
App.ActiveDocument.C814.Placement=Base.Placement(Base.Vector(25.661744,113.122922,-56.465064),Base.Rotation(0.491310,0.764772,0.000000,0.416819))
App.ActiveDocument.addObject("Part::Cylinder","C815")
App.ActiveDocument.C815.Radius=0.641777
App.ActiveDocument.C815.Height=20.00
App.ActiveDocument.C815.Angle=360.00 
App.ActiveDocument.C815.Placement=Base.Placement(Base.Vector(25.647471,109.549489,-54.119527),Base.Rotation(0.534338,0.739738,0.000000,0.408987))
App.ActiveDocument.addObject("Part::Cylinder","C816")
App.ActiveDocument.C816.Radius=0.638953
App.ActiveDocument.C816.Height=20.00
App.ActiveDocument.C816.Angle=360.00 
App.ActiveDocument.C816.Placement=Base.Placement(Base.Vector(27.483695,109.716976,-55.207411),Base.Rotation(0.782837,0.239064,0.000000,0.574469))
App.ActiveDocument.addObject("Part::Cylinder","C817")
App.ActiveDocument.C817.Radius=0.511138
App.ActiveDocument.C817.Height=20.00
App.ActiveDocument.C817.Angle=360.00 
App.ActiveDocument.C817.Placement=Base.Placement(Base.Vector(31.632796,196.606556,-4.423281),Base.Rotation(-0.607449,0.370728,0.000000,0.702543))
App.ActiveDocument.addObject("Part::Cylinder","C818")
App.ActiveDocument.C818.Radius=0.521487
App.ActiveDocument.C818.Height=20.00
App.ActiveDocument.C818.Angle=360.00 
App.ActiveDocument.C818.Placement=Base.Placement(Base.Vector(31.848854,196.337224,-8.972087),Base.Rotation(-0.614969,0.378184,0.000000,0.691947))
App.ActiveDocument.addObject("Part::Cylinder","C819")
App.ActiveDocument.C819.Radius=0.531703
App.ActiveDocument.C819.Height=20.00
App.ActiveDocument.C819.Angle=360.00 
App.ActiveDocument.C819.Placement=Base.Placement(Base.Vector(31.913509,195.988460,-13.308124),Base.Rotation(-0.622910,0.389720,0.000000,0.678307))
App.ActiveDocument.addObject("Part::Cylinder","C820")
App.ActiveDocument.C820.Radius=0.541908
App.ActiveDocument.C820.Height=20.00
App.ActiveDocument.C820.Angle=360.00 
App.ActiveDocument.C820.Placement=Base.Placement(Base.Vector(32.103277,195.343464,-17.700366),Base.Rotation(-0.630345,0.402658,0.000000,0.663726))
App.ActiveDocument.addObject("Part::Cylinder","C821")
App.ActiveDocument.C821.Radius=0.551858
App.ActiveDocument.C821.Height=20.00
App.ActiveDocument.C821.Angle=360.00 
App.ActiveDocument.C821.Placement=Base.Placement(Base.Vector(32.269825,194.500432,-21.904674),Base.Rotation(-0.636164,0.422944,0.000000,0.645301))
App.ActiveDocument.addObject("Part::Cylinder","C822")
App.ActiveDocument.C822.Radius=0.562777
App.ActiveDocument.C822.Height=20.00
App.ActiveDocument.C822.Angle=360.00 
App.ActiveDocument.C822.Placement=Base.Placement(Base.Vector(31.865187,193.793349,-26.105335),Base.Rotation(-0.649325,0.431231,0.000000,0.626432))
App.ActiveDocument.addObject("Part::Cylinder","C823")
App.ActiveDocument.C823.Radius=0.571758
App.ActiveDocument.C823.Height=20.00
App.ActiveDocument.C823.Angle=360.00 
App.ActiveDocument.C823.Placement=Base.Placement(Base.Vector(32.197138,192.412061,-29.988386),Base.Rotation(-0.651029,0.455373,0.000000,0.607287))
App.ActiveDocument.addObject("Part::Cylinder","C824")
App.ActiveDocument.C824.Radius=0.581643
App.ActiveDocument.C824.Height=20.00
App.ActiveDocument.C824.Angle=360.00 
App.ActiveDocument.C824.Placement=Base.Placement(Base.Vector(32.104064,191.024538,-33.905861),Base.Rotation(-0.656416,0.476871,0.000000,0.584561))
App.ActiveDocument.addObject("Part::Cylinder","C825")
App.ActiveDocument.C825.Radius=0.591188
App.ActiveDocument.C825.Height=20.00
App.ActiveDocument.C825.Angle=360.00 
App.ActiveDocument.C825.Placement=Base.Placement(Base.Vector(31.998938,189.402298,-37.569577),Base.Rotation(-0.659689,0.504815,0.000000,0.556751))
App.ActiveDocument.addObject("Part::Cylinder","C826")
App.ActiveDocument.C826.Radius=0.599837
App.ActiveDocument.C826.Height=20.00
App.ActiveDocument.C826.Angle=360.00 
App.ActiveDocument.C826.Placement=Base.Placement(Base.Vector(31.897398,187.629102,-40.742664),Base.Rotation(-0.657968,0.541455,0.000000,0.523359))
App.ActiveDocument.addObject("Part::Cylinder","C827")
App.ActiveDocument.C827.Radius=0.607324
App.ActiveDocument.C827.Height=20.00
App.ActiveDocument.C827.Angle=360.00 
App.ActiveDocument.C827.Placement=Base.Placement(Base.Vector(32.153447,185.303596,-43.637882),Base.Rotation(-0.651265,0.579017,0.000000,0.490503))
App.ActiveDocument.addObject("Part::Cylinder","C828")
App.ActiveDocument.C828.Radius=0.614645
App.ActiveDocument.C828.Height=20.00
App.ActiveDocument.C828.Angle=360.00 
App.ActiveDocument.C828.Placement=Base.Placement(Base.Vector(32.062674,182.989694,-46.304263),Base.Rotation(-0.626411,0.632247,0.000000,0.455931))
App.ActiveDocument.addObject("Part::Cylinder","C829")
App.ActiveDocument.C829.Radius=0.620334
App.ActiveDocument.C829.Height=20.00
App.ActiveDocument.C829.Angle=360.00 
App.ActiveDocument.C829.Placement=Base.Placement(Base.Vector(32.335658,180.151411,-48.591787),Base.Rotation(-0.602033,0.673189,0.000000,0.429387))
App.ActiveDocument.addObject("Part::Cylinder","C830")
App.ActiveDocument.C830.Radius=0.626290
App.ActiveDocument.C830.Height=20.00
App.ActiveDocument.C830.Angle=360.00 
App.ActiveDocument.C830.Placement=Base.Placement(Base.Vector(32.303292,177.237249,-50.726799),Base.Rotation(-0.561468,0.726166,0.000000,0.396784))
App.ActiveDocument.addObject("Part::Cylinder","C831")
App.ActiveDocument.C831.Radius=0.631873
App.ActiveDocument.C831.Height=20.00
App.ActiveDocument.C831.Angle=360.00 
App.ActiveDocument.C831.Placement=Base.Placement(Base.Vector(32.107936,173.926954,-52.767494),Base.Rotation(-0.493939,0.786894,0.000000,0.369895))
App.ActiveDocument.addObject("Part::Cylinder","C832")
App.ActiveDocument.C832.Radius=0.636383
App.ActiveDocument.C832.Height=20.00
App.ActiveDocument.C832.Angle=360.00 
App.ActiveDocument.C832.Placement=Base.Placement(Base.Vector(31.845821,170.623162,-54.451795),Base.Rotation(-0.429920,0.830787,0.000000,0.353500))
App.ActiveDocument.addObject("Part::Cylinder","C833")
App.ActiveDocument.C833.Radius=0.640404
App.ActiveDocument.C833.Height=20.00
App.ActiveDocument.C833.Angle=360.00 
App.ActiveDocument.C833.Placement=Base.Placement(Base.Vector(31.521411,167.337428,-55.880797),Base.Rotation(-0.365691,0.866846,0.000000,0.338892))
App.ActiveDocument.addObject("Part::Cylinder","C834")
App.ActiveDocument.C834.Radius=0.642770
App.ActiveDocument.C834.Height=20.00
App.ActiveDocument.C834.Angle=360.00 
App.ActiveDocument.C834.Placement=Base.Placement(Base.Vector(31.543633,163.764427,-56.876999),Base.Rotation(-0.295892,0.896369,0.000000,0.330108))
App.ActiveDocument.addObject("Part::Cylinder","C835")
App.ActiveDocument.C835.Radius=0.645167
App.ActiveDocument.C835.Height=20.00
App.ActiveDocument.C835.Angle=360.00 
App.ActiveDocument.C835.Placement=Base.Placement(Base.Vector(31.474378,159.752893,-57.812576),Base.Rotation(-0.232426,0.917776,0.000000,0.321972))
App.ActiveDocument.addObject("Part::Cylinder","C836")
App.ActiveDocument.C836.Radius=0.646343
App.ActiveDocument.C836.Height=20.00
App.ActiveDocument.C836.Angle=360.00 
App.ActiveDocument.C836.Placement=Base.Placement(Base.Vector(31.448332,156.008857,-58.444539),Base.Rotation(-0.166905,0.931026,0.000000,0.324552))
App.ActiveDocument.addObject("Part::Cylinder","C837")
App.ActiveDocument.C837.Radius=0.648218
App.ActiveDocument.C837.Height=20.00
App.ActiveDocument.C837.Angle=360.00 
App.ActiveDocument.C837.Placement=Base.Placement(Base.Vector(31.026512,152.097754,-59.200040),Base.Rotation(-0.094943,0.939295,0.000000,0.329713))
App.ActiveDocument.addObject("Part::Cylinder","C838")
App.ActiveDocument.C838.Radius=0.648402
App.ActiveDocument.C838.Height=20.00
App.ActiveDocument.C838.Angle=360.00 
App.ActiveDocument.C838.Placement=Base.Placement(Base.Vector(30.816945,148.102482,-59.589117),Base.Rotation(-0.025904,0.937360,0.000000,0.347399))
App.ActiveDocument.addObject("Part::Cylinder","C839")
App.ActiveDocument.C839.Radius=0.648697
App.ActiveDocument.C839.Height=20.00
App.ActiveDocument.C839.Angle=360.00 
App.ActiveDocument.C839.Placement=Base.Placement(Base.Vector(30.436088,144.345283,-59.887377),Base.Rotation(0.032979,0.930830,0.000000,0.363960))
App.ActiveDocument.addObject("Part::Cylinder","C840")
App.ActiveDocument.C840.Radius=0.649995
App.ActiveDocument.C840.Height=20.00
App.ActiveDocument.C840.Angle=360.00 
App.ActiveDocument.C840.Placement=Base.Placement(Base.Vector(29.705460,140.121574,-60.336332),Base.Rotation(0.074424,0.923309,0.000000,0.376779))
App.ActiveDocument.addObject("Part::Cylinder","C841")
App.ActiveDocument.C841.Radius=0.650517
App.ActiveDocument.C841.Height=20.00
App.ActiveDocument.C841.Angle=360.00 
App.ActiveDocument.C841.Placement=Base.Placement(Base.Vector(29.121981,136.034833,-60.510145),Base.Rotation(0.102801,0.915450,0.000000,0.389080))
App.ActiveDocument.addObject("Part::Cylinder","C842")
App.ActiveDocument.C842.Radius=0.650189
App.ActiveDocument.C842.Height=20.00
App.ActiveDocument.C842.Angle=360.00 
App.ActiveDocument.C842.Placement=Base.Placement(Base.Vector(28.683959,131.678409,-60.382337),Base.Rotation(0.133450,0.906142,0.000000,0.401370))
App.ActiveDocument.addObject("Part::Cylinder","C843")
App.ActiveDocument.C843.Radius=0.648672
App.ActiveDocument.C843.Height=20.00
App.ActiveDocument.C843.Angle=360.00 
App.ActiveDocument.C843.Placement=Base.Placement(Base.Vector(28.520561,127.624660,-59.825431),Base.Rotation(0.179190,0.893302,0.000000,0.412192))
App.ActiveDocument.addObject("Part::Cylinder","C844")
App.ActiveDocument.C844.Radius=0.645904
App.ActiveDocument.C844.Height=20.00
App.ActiveDocument.C844.Angle=360.00 
App.ActiveDocument.C844.Placement=Base.Placement(Base.Vector(28.632556,124.215760,-58.816213),Base.Rotation(0.234293,0.875801,0.000000,0.421995))
App.ActiveDocument.addObject("Part::Cylinder","C845")
App.ActiveDocument.C845.Radius=0.642979
App.ActiveDocument.C845.Height=20.00
App.ActiveDocument.C845.Angle=360.00 
App.ActiveDocument.C845.Placement=Base.Placement(Base.Vector(28.565738,120.813368,-57.487448),Base.Rotation(0.346271,0.833016,0.000000,0.431488))
App.ActiveDocument.addObject("Part::Cylinder","C846")
App.ActiveDocument.C846.Radius=0.636879
App.ActiveDocument.C846.Height=20.00
App.ActiveDocument.C846.Angle=360.00 
App.ActiveDocument.C846.Placement=Base.Placement(Base.Vector(28.946091,117.094982,-55.063922),Base.Rotation(0.375407,0.816315,0.000000,0.438976))
App.ActiveDocument.addObject("Part::Cylinder","C847")
App.ActiveDocument.C847.Radius=0.633476
App.ActiveDocument.C847.Height=20.00
App.ActiveDocument.C847.Angle=360.00 
App.ActiveDocument.C847.Placement=Base.Placement(Base.Vector(28.729577,112.759431,-52.992524),Base.Rotation(0.407878,0.807533,0.000000,0.426059))
App.ActiveDocument.addObject("Part::Cylinder","C848")
App.ActiveDocument.C848.Radius=0.629389
App.ActiveDocument.C848.Height=20.00
App.ActiveDocument.C848.Angle=360.00 
App.ActiveDocument.C848.Placement=Base.Placement(Base.Vector(28.826208,108.707764,-50.659425),Base.Rotation(0.451019,0.793599,0.000000,0.408390))
App.ActiveDocument.addObject("Part::Cylinder","C849")
App.ActiveDocument.C849.Radius=0.626663
App.ActiveDocument.C849.Height=20.00
App.ActiveDocument.C849.Angle=360.00 
App.ActiveDocument.C849.Placement=Base.Placement(Base.Vector(30.371032,108.834555,-51.083800),Base.Rotation(0.773612,0.333386,0.000000,0.538868))
App.ActiveDocument.addObject("Part::Cylinder","C850")
App.ActiveDocument.C850.Radius=0.505473
App.ActiveDocument.C850.Height=20.00
App.ActiveDocument.C850.Angle=360.00 
App.ActiveDocument.C850.Placement=Base.Placement(Base.Vector(34.786249,194.505445,-4.259926),Base.Rotation(-0.569436,0.423908,0.000000,0.704305))
App.ActiveDocument.addObject("Part::Cylinder","C851")
App.ActiveDocument.C851.Radius=0.515451
App.ActiveDocument.C851.Height=20.00
App.ActiveDocument.C851.Angle=360.00 
App.ActiveDocument.C851.Placement=Base.Placement(Base.Vector(35.092420,194.146564,-8.659694),Base.Rotation(-0.575944,0.435509,0.000000,0.691824))
App.ActiveDocument.addObject("Part::Cylinder","C852")
App.ActiveDocument.C852.Radius=0.525665
App.ActiveDocument.C852.Height=20.00
App.ActiveDocument.C852.Angle=360.00 
App.ActiveDocument.C852.Placement=Base.Placement(Base.Vector(35.212296,193.731280,-13.026901),Base.Rotation(-0.584463,0.443898,0.000000,0.679233))
App.ActiveDocument.addObject("Part::Cylinder","C853")
App.ActiveDocument.C853.Radius=0.535675
App.ActiveDocument.C853.Height=20.00
App.ActiveDocument.C853.Angle=360.00 
App.ActiveDocument.C853.Placement=Base.Placement(Base.Vector(35.477906,192.968820,-17.395333),Base.Rotation(-0.586156,0.464887,0.000000,0.663551))
App.ActiveDocument.addObject("Part::Cylinder","C854")
App.ActiveDocument.C854.Radius=0.546077
App.ActiveDocument.C854.Height=20.00
App.ActiveDocument.C854.Angle=360.00 
App.ActiveDocument.C854.Placement=Base.Placement(Base.Vector(35.560854,192.094275,-21.752881),Base.Rotation(-0.593124,0.479192,0.000000,0.646976))
App.ActiveDocument.addObject("Part::Cylinder","C855")
App.ActiveDocument.C855.Radius=0.557128
App.ActiveDocument.C855.Height=20.00
App.ActiveDocument.C855.Angle=360.00 
App.ActiveDocument.C855.Placement=Base.Placement(Base.Vector(35.233039,191.308508,-26.038390),Base.Rotation(-0.605763,0.489275,0.000000,0.627424))
App.ActiveDocument.addObject("Part::Cylinder","C856")
App.ActiveDocument.C856.Radius=0.566183
App.ActiveDocument.C856.Height=20.00
App.ActiveDocument.C856.Angle=360.00 
App.ActiveDocument.C856.Placement=Base.Placement(Base.Vector(35.604612,189.770997,-29.965255),Base.Rotation(-0.605020,0.513890,0.000000,0.608168))
App.ActiveDocument.addObject("Part::Cylinder","C857")
App.ActiveDocument.C857.Radius=0.576172
App.ActiveDocument.C857.Height=20.00
App.ActiveDocument.C857.Angle=360.00 
App.ActiveDocument.C857.Placement=Base.Placement(Base.Vector(35.496001,188.350439,-33.815278),Base.Rotation(-0.613387,0.532670,0.000000,0.583112))
App.ActiveDocument.addObject("Part::Cylinder","C858")
App.ActiveDocument.C858.Radius=0.585480
App.ActiveDocument.C858.Height=20.00
App.ActiveDocument.C858.Angle=360.00 
App.ActiveDocument.C858.Placement=Base.Placement(Base.Vector(35.454750,186.629887,-37.338938),Base.Rotation(-0.613982,0.563410,0.000000,0.552806))
App.ActiveDocument.addObject("Part::Cylinder","C859")
App.ActiveDocument.C859.Radius=0.593586
App.ActiveDocument.C859.Height=20.00
App.ActiveDocument.C859.Angle=360.00 
App.ActiveDocument.C859.Placement=Base.Placement(Base.Vector(35.495459,184.672466,-40.361459),Base.Rotation(-0.604607,0.603605,0.000000,0.519722))
App.ActiveDocument.addObject("Part::Cylinder","C860")
App.ActiveDocument.C860.Radius=0.600743
App.ActiveDocument.C860.Height=20.00
App.ActiveDocument.C860.Angle=360.00 
App.ActiveDocument.C860.Placement=Base.Placement(Base.Vector(35.609700,182.314529,-43.131764),Base.Rotation(-0.580904,0.650157,0.000000,0.489741))
App.ActiveDocument.addObject("Part::Cylinder","C861")
App.ActiveDocument.C861.Radius=0.606844
App.ActiveDocument.C861.Height=20.00
App.ActiveDocument.C861.Angle=360.00 
App.ActiveDocument.C861.Placement=Base.Placement(Base.Vector(35.783061,179.692403,-45.509937),Base.Rotation(-0.559101,0.687405,0.000000,0.463553))
App.ActiveDocument.addObject("Part::Cylinder","C862")
App.ActiveDocument.C862.Radius=0.612888
App.ActiveDocument.C862.Height=20.00
App.ActiveDocument.C862.Angle=360.00 
App.ActiveDocument.C862.Placement=Base.Placement(Base.Vector(35.603792,177.144968,-47.673300),Base.Rotation(-0.504111,0.746872,0.000000,0.433652))
App.ActiveDocument.addObject("Part::Cylinder","C863")
App.ActiveDocument.C863.Radius=0.618426
App.ActiveDocument.C863.Height=20.00
App.ActiveDocument.C863.Angle=360.00 
App.ActiveDocument.C863.Placement=Base.Placement(Base.Vector(35.404547,174.264736,-49.639692),Base.Rotation(-0.450028,0.794334,0.000000,0.408055))
App.ActiveDocument.addObject("Part::Cylinder","C864")
App.ActiveDocument.C864.Radius=0.622680
App.ActiveDocument.C864.Height=20.00
App.ActiveDocument.C864.Angle=360.00 
App.ActiveDocument.C864.Placement=Base.Placement(Base.Vector(35.282924,171.161095,-51.234361),Base.Rotation(-0.381781,0.838097,0.000000,0.389662))
App.ActiveDocument.addObject("Part::Cylinder","C865")
App.ActiveDocument.C865.Radius=0.626551
App.ActiveDocument.C865.Height=20.00
App.ActiveDocument.C865.Angle=360.00 
App.ActiveDocument.C865.Placement=Base.Placement(Base.Vector(35.091051,167.551681,-52.776065),Base.Rotation(-0.307950,0.872406,0.000000,0.379571))
App.ActiveDocument.addObject("Part::Cylinder","C866")
App.ActiveDocument.C866.Radius=0.629860
App.ActiveDocument.C866.Height=20.00
App.ActiveDocument.C866.Angle=360.00 
App.ActiveDocument.C866.Placement=Base.Placement(Base.Vector(34.844404,164.097418,-54.042309),Base.Rotation(-0.253411,0.892740,0.000000,0.372557))
App.ActiveDocument.addObject("Part::Cylinder","C867")
App.ActiveDocument.C867.Radius=0.631788
App.ActiveDocument.C867.Height=20.00
App.ActiveDocument.C867.Angle=360.00 
App.ActiveDocument.C867.Placement=Base.Placement(Base.Vector(34.666831,160.728051,-54.967744),Base.Rotation(-0.176079,0.909883,0.000000,0.375644))
App.ActiveDocument.addObject("Part::Cylinder","C868")
App.ActiveDocument.C868.Radius=0.633032
App.ActiveDocument.C868.Height=20.00
App.ActiveDocument.C868.Angle=360.00 
App.ActiveDocument.C868.Placement=Base.Placement(Base.Vector(34.460618,157.179875,-55.693826),Base.Rotation(-0.093271,0.918159,0.000000,0.385078))
App.ActiveDocument.addObject("Part::Cylinder","C869")
App.ActiveDocument.C869.Radius=0.634847
App.ActiveDocument.C869.Height=20.00
App.ActiveDocument.C869.Angle=360.00 
App.ActiveDocument.C869.Placement=Base.Placement(Base.Vector(34.004577,153.528656,-56.412958),Base.Rotation(-0.039085,0.919457,0.000000,0.391244))
App.ActiveDocument.addObject("Part::Cylinder","C870")
App.ActiveDocument.C870.Radius=0.635685
App.ActiveDocument.C870.Height=20.00
App.ActiveDocument.C870.Angle=360.00 
App.ActiveDocument.C870.Placement=Base.Placement(Base.Vector(33.636796,149.511222,-56.823466),Base.Rotation(0.014797,0.915863,0.000000,0.401219))
App.ActiveDocument.addObject("Part::Cylinder","C871")
App.ActiveDocument.C871.Radius=0.635536
App.ActiveDocument.C871.Height=20.00
App.ActiveDocument.C871.Angle=360.00 
App.ActiveDocument.C871.Placement=Base.Placement(Base.Vector(33.373914,145.605539,-56.907355),Base.Rotation(0.062081,0.908172,0.000000,0.413969))
App.ActiveDocument.addObject("Part::Cylinder","C872")
App.ActiveDocument.C872.Radius=0.636233
App.ActiveDocument.C872.Height=20.00
App.ActiveDocument.C872.Angle=360.00 
App.ActiveDocument.C872.Placement=Base.Placement(Base.Vector(32.859517,141.940425,-57.116631),Base.Rotation(0.097417,0.901068,0.000000,0.422595))
App.ActiveDocument.addObject("Part::Cylinder","C873")
App.ActiveDocument.C873.Radius=0.637736
App.ActiveDocument.C873.Height=20.00
App.ActiveDocument.C873.Angle=360.00 
App.ActiveDocument.C873.Placement=Base.Placement(Base.Vector(32.061937,138.159370,-57.494450),Base.Rotation(0.123405,0.894281,0.000000,0.430154))
App.ActiveDocument.addObject("Part::Cylinder","C874")
App.ActiveDocument.C874.Radius=0.636978
App.ActiveDocument.C874.Height=20.00
App.ActiveDocument.C874.Angle=360.00 
App.ActiveDocument.C874.Placement=Base.Placement(Base.Vector(31.701783,134.212730,-57.212846),Base.Rotation(0.140984,0.886055,0.000000,0.441622))
App.ActiveDocument.addObject("Part::Cylinder","C875")
App.ActiveDocument.C875.Radius=0.636219
App.ActiveDocument.C875.Height=20.00
App.ActiveDocument.C875.Angle=360.00 
App.ActiveDocument.C875.Placement=Base.Placement(Base.Vector(31.249851,129.917526,-56.873849),Base.Rotation(0.153248,0.878334,0.000000,0.452819))
App.ActiveDocument.addObject("Part::Cylinder","C876")
App.ActiveDocument.C876.Radius=0.633318
App.ActiveDocument.C876.Height=20.00
App.ActiveDocument.C876.Angle=360.00 
App.ActiveDocument.C876.Placement=Base.Placement(Base.Vector(31.336882,126.165360,-55.807661),Base.Rotation(0.174635,0.869871,0.000000,0.461332))
App.ActiveDocument.addObject("Part::Cylinder","C877")
App.ActiveDocument.C877.Radius=0.631007
App.ActiveDocument.C877.Height=20.00
App.ActiveDocument.C877.Angle=360.00 
App.ActiveDocument.C877.Placement=Base.Placement(Base.Vector(31.267742,122.555096,-54.761908),Base.Rotation(0.226081,0.855602,0.000000,0.465654))
App.ActiveDocument.addObject("Part::Cylinder","C878")
App.ActiveDocument.C878.Radius=0.628203
App.ActiveDocument.C878.Height=20.00
App.ActiveDocument.C878.Angle=360.00 
App.ActiveDocument.C878.Placement=Base.Placement(Base.Vector(31.377822,119.628698,-53.390567),Base.Rotation(0.281217,0.840647,0.000000,0.462849))
App.ActiveDocument.addObject("Part::Cylinder","C879")
App.ActiveDocument.C879.Radius=0.622911
App.ActiveDocument.C879.Height=20.00
App.ActiveDocument.C879.Angle=360.00 
App.ActiveDocument.C879.Placement=Base.Placement(Base.Vector(31.729680,115.734655,-50.991076),Base.Rotation(0.315630,0.831397,0.000000,0.457336))
App.ActiveDocument.addObject("Part::Cylinder","C880")
App.ActiveDocument.C880.Radius=0.619806
App.ActiveDocument.C880.Height=20.00
App.ActiveDocument.C880.Angle=360.00 
App.ActiveDocument.C880.Placement=Base.Placement(Base.Vector(31.472908,111.642649,-49.197702),Base.Rotation(0.340408,0.825408,0.000000,0.450360))
App.ActiveDocument.addObject("Part::Cylinder","C881")
App.ActiveDocument.C881.Radius=0.616730
App.ActiveDocument.C881.Height=20.00
App.ActiveDocument.C881.Angle=360.00 
App.ActiveDocument.C881.Placement=Base.Placement(Base.Vector(31.180878,107.291969,-47.387843),Base.Rotation(0.342477,0.829582,0.000000,0.441025))
App.ActiveDocument.addObject("Part::Cylinder","C882")
App.ActiveDocument.C882.Radius=0.614166
App.ActiveDocument.C882.Height=20.00
App.ActiveDocument.C882.Angle=360.00 
App.ActiveDocument.C882.Placement=Base.Placement(Base.Vector(33.920516,109.346311,-48.784513),Base.Rotation(0.754738,0.243349,0.000000,0.609222))
App.ActiveDocument.addObject("Part::Cylinder","C883")
App.ActiveDocument.C883.Radius=0.500509
App.ActiveDocument.C883.Height=20.00
App.ActiveDocument.C883.Angle=360.00 
App.ActiveDocument.C883.Placement=Base.Placement(Base.Vector(37.752919,192.009850,-4.379428),Base.Rotation(-0.515101,0.485961,0.000000,0.706054))
App.ActiveDocument.addObject("Part::Cylinder","C884")
App.ActiveDocument.C884.Radius=0.510519
App.ActiveDocument.C884.Height=20.00
App.ActiveDocument.C884.Angle=360.00 
App.ActiveDocument.C884.Placement=Base.Placement(Base.Vector(38.050207,191.617822,-8.783279),Base.Rotation(-0.525071,0.490566,0.000000,0.695447))
App.ActiveDocument.addObject("Part::Cylinder","C885")
App.ActiveDocument.C885.Radius=0.520706
App.ActiveDocument.C885.Height=20.00
App.ActiveDocument.C885.Angle=360.00 
App.ActiveDocument.C885.Placement=Base.Placement(Base.Vector(38.225279,191.132539,-13.078402),Base.Rotation(-0.536547,0.499381,0.000000,0.680246))
App.ActiveDocument.addObject("Part::Cylinder","C886")
App.ActiveDocument.C886.Radius=0.530237
App.ActiveDocument.C886.Height=20.00
App.ActiveDocument.C886.Angle=360.00 
App.ActiveDocument.C886.Placement=Base.Placement(Base.Vector(38.618103,190.215507,-17.309057),Base.Rotation(-0.538527,0.516150,0.000000,0.666017))
App.ActiveDocument.addObject("Part::Cylinder","C887")
App.ActiveDocument.C887.Radius=0.541198
App.ActiveDocument.C887.Height=20.00
App.ActiveDocument.C887.Angle=360.00 
App.ActiveDocument.C887.Placement=Base.Placement(Base.Vector(38.468501,189.522504,-21.741742),Base.Rotation(-0.547177,0.528471,0.000000,0.649088))
App.ActiveDocument.addObject("Part::Cylinder","C888")
App.ActiveDocument.C888.Radius=0.551241
App.ActiveDocument.C888.Height=20.00
App.ActiveDocument.C888.Angle=360.00 
App.ActiveDocument.C888.Placement=Base.Placement(Base.Vector(38.494569,188.454815,-25.871600),Base.Rotation(-0.552288,0.544428,0.000000,0.631329))
App.ActiveDocument.addObject("Part::Cylinder","C889")
App.ActiveDocument.C889.Radius=0.560996
App.ActiveDocument.C889.Height=20.00
App.ActiveDocument.C889.Angle=360.00 
App.ActiveDocument.C889.Placement=Base.Placement(Base.Vector(38.690324,186.931340,-29.945949),Base.Rotation(-0.554041,0.564938,0.000000,0.611460))
App.ActiveDocument.addObject("Part::Cylinder","C890")
App.ActiveDocument.C890.Radius=0.571031
App.ActiveDocument.C890.Height=20.00
App.ActiveDocument.C890.Angle=360.00 
App.ActiveDocument.C890.Placement=Base.Placement(Base.Vector(38.534316,185.521822,-33.720301),Base.Rotation(-0.558712,0.589450,0.000000,0.583429))
App.ActiveDocument.addObject("Part::Cylinder","C891")
App.ActiveDocument.C891.Radius=0.579437
App.ActiveDocument.C891.Height=20.00
App.ActiveDocument.C891.Angle=360.00 
App.ActiveDocument.C891.Placement=Base.Placement(Base.Vector(38.641185,183.616773,-37.026081),Base.Rotation(-0.544921,0.628060,0.000000,0.555519))
App.ActiveDocument.addObject("Part::Cylinder","C892")
App.ActiveDocument.C892.Radius=0.587000
App.ActiveDocument.C892.Height=20.00
App.ActiveDocument.C892.Angle=360.00 
App.ActiveDocument.C892.Placement=Base.Placement(Base.Vector(38.820824,181.383225,-39.877643),Base.Rotation(-0.530650,0.666634,0.000000,0.523459))
App.ActiveDocument.addObject("Part::Cylinder","C893")
App.ActiveDocument.C893.Radius=0.593316
App.ActiveDocument.C893.Height=20.00
App.ActiveDocument.C893.Angle=360.00 
App.ActiveDocument.C893.Placement=Base.Placement(Base.Vector(38.865388,179.132189,-42.263052),Base.Rotation(-0.501285,0.708489,0.000000,0.496746))
App.ActiveDocument.addObject("Part::Cylinder","C894")
App.ActiveDocument.C894.Radius=0.599155
App.ActiveDocument.C894.Height=20.00
App.ActiveDocument.C894.Angle=360.00 
App.ActiveDocument.C894.Placement=Base.Placement(Base.Vector(39.002048,176.359988,-44.401281),Base.Rotation(-0.455569,0.759036,0.000000,0.465104))
App.ActiveDocument.addObject("Part::Cylinder","C895")
App.ActiveDocument.C895.Radius=0.604702
App.ActiveDocument.C895.Height=20.00
App.ActiveDocument.C895.Angle=360.00 
App.ActiveDocument.C895.Placement=Base.Placement(Base.Vector(38.776833,173.662634,-46.412959),Base.Rotation(-0.405894,0.798989,0.000000,0.443695))
App.ActiveDocument.addObject("Part::Cylinder","C896")
App.ActiveDocument.C896.Radius=0.609584
App.ActiveDocument.C896.Height=20.00
App.ActiveDocument.C896.Angle=360.00 
App.ActiveDocument.C896.Placement=Base.Placement(Base.Vector(38.525315,170.756755,-48.136754),Base.Rotation(-0.332194,0.843210,0.000000,0.422662))
App.ActiveDocument.addObject("Part::Cylinder","C897")
App.ActiveDocument.C897.Radius=0.613625
App.ActiveDocument.C897.Height=20.00
App.ActiveDocument.C897.Angle=360.00 
App.ActiveDocument.C897.Placement=Base.Placement(Base.Vector(38.236918,167.585966,-49.652118),Base.Rotation(-0.249984,0.876666,0.000000,0.411053))
App.ActiveDocument.addObject("Part::Cylinder","C898")
App.ActiveDocument.C898.Radius=0.616384
App.ActiveDocument.C898.Height=20.00
App.ActiveDocument.C898.Angle=360.00 
App.ActiveDocument.C898.Placement=Base.Placement(Base.Vector(38.039726,164.067328,-50.825720),Base.Rotation(-0.178905,0.894723,0.000000,0.409224))
App.ActiveDocument.addObject("Part::Cylinder","C899")
App.ActiveDocument.C899.Radius=0.618197
App.ActiveDocument.C899.Height=20.00
App.ActiveDocument.C899.Angle=360.00 
App.ActiveDocument.C899.Placement=Base.Placement(Base.Vector(37.809831,160.867829,-51.640697),Base.Rotation(-0.111028,0.904278,0.000000,0.412255))
App.ActiveDocument.addObject("Part::Cylinder","C900")
App.ActiveDocument.C900.Radius=0.620630
App.ActiveDocument.C900.Height=20.00
App.ActiveDocument.C900.Angle=360.00 
App.ActiveDocument.C900.Placement=Base.Placement(Base.Vector(37.277648,157.365589,-52.561809),Base.Rotation(-0.043395,0.908079,0.000000,0.416546))
App.ActiveDocument.addObject("Part::Cylinder","C901")
App.ActiveDocument.C901.Radius=0.621453
App.ActiveDocument.C901.Height=20.00
App.ActiveDocument.C901.Angle=360.00 
App.ActiveDocument.C901.Placement=Base.Placement(Base.Vector(37.012830,154.227771,-52.944278),Base.Rotation(-0.003523,0.906136,0.000000,0.422972))
App.ActiveDocument.addObject("Part::Cylinder","C902")
App.ActiveDocument.C902.Radius=0.621486
App.ActiveDocument.C902.Height=20.00
App.ActiveDocument.C902.Angle=360.00 
App.ActiveDocument.C902.Placement=Base.Placement(Base.Vector(36.801603,150.635071,-53.093202),Base.Rotation(0.040017,0.900326,0.000000,0.433373))
App.ActiveDocument.addObject("Part::Cylinder","C903")
App.ActiveDocument.C903.Radius=0.622097
App.ActiveDocument.C903.Height=20.00
App.ActiveDocument.C903.Angle=360.00 
App.ActiveDocument.C903.Placement=Base.Placement(Base.Vector(36.397454,147.131572,-53.325414),Base.Rotation(0.071428,0.894425,0.000000,0.441476))
App.ActiveDocument.addObject("Part::Cylinder","C904")
App.ActiveDocument.C904.Radius=0.622657
App.ActiveDocument.C904.Height=20.00
App.ActiveDocument.C904.Angle=360.00 
App.ActiveDocument.C904.Placement=Base.Placement(Base.Vector(35.886107,142.933130,-53.442780),Base.Rotation(0.107904,0.887063,0.000000,0.448861))
App.ActiveDocument.addObject("Part::Cylinder","C905")
App.ActiveDocument.C905.Radius=0.624136
App.ActiveDocument.C905.Height=20.00
App.ActiveDocument.C905.Angle=360.00 
App.ActiveDocument.C905.Placement=Base.Placement(Base.Vector(35.145257,138.958094,-53.699247),Base.Rotation(0.134440,0.882430,0.000000,0.450825))
App.ActiveDocument.addObject("Part::Cylinder","C906")
App.ActiveDocument.C906.Radius=0.624140
App.ActiveDocument.C906.Height=20.00
App.ActiveDocument.C906.Angle=360.00 
App.ActiveDocument.C906.Placement=Base.Placement(Base.Vector(34.688460,135.371257,-53.513712),Base.Rotation(0.151662,0.877580,0.000000,0.454809))
App.ActiveDocument.addObject("Part::Cylinder","C907")
App.ActiveDocument.C907.Radius=0.623434
App.ActiveDocument.C907.Height=20.00
App.ActiveDocument.C907.Angle=360.00 
App.ActiveDocument.C907.Placement=Base.Placement(Base.Vector(34.343077,131.704638,-53.072428),Base.Rotation(0.163076,0.873546,0.000000,0.458609))
App.ActiveDocument.addObject("Part::Cylinder","C908")
App.ActiveDocument.C908.Radius=0.621701
App.ActiveDocument.C908.Height=20.00
App.ActiveDocument.C908.Angle=360.00 
App.ActiveDocument.C908.Placement=Base.Placement(Base.Vector(34.224006,128.279328,-52.315051),Base.Rotation(0.176715,0.868525,0.000000,0.463073))
App.ActiveDocument.addObject("Part::Cylinder","C909")
App.ActiveDocument.C909.Radius=0.618247
App.ActiveDocument.C909.Height=20.00
App.ActiveDocument.C909.Angle=360.00 
App.ActiveDocument.C909.Placement=Base.Placement(Base.Vector(34.352867,124.481115,-50.951300),Base.Rotation(0.200674,0.860052,0.000000,0.469085))
App.ActiveDocument.addObject("Part::Cylinder","C910")
App.ActiveDocument.C910.Radius=0.615623
App.ActiveDocument.C910.Height=20.00
App.ActiveDocument.C910.Angle=360.00 
App.ActiveDocument.C910.Placement=Base.Placement(Base.Vector(34.097324,120.304757,-49.750645),Base.Rotation(0.236508,0.846675,0.000000,0.476660))
App.ActiveDocument.addObject("Part::Cylinder","C911")
App.ActiveDocument.C911.Radius=0.610192
App.ActiveDocument.C911.Height=20.00
App.ActiveDocument.C911.Angle=360.00 
App.ActiveDocument.C911.Placement=Base.Placement(Base.Vector(34.478866,116.316675,-47.490786),Base.Rotation(0.253307,0.841710,0.000000,0.476823))
App.ActiveDocument.addObject("Part::Cylinder","C912")
App.ActiveDocument.C912.Radius=0.607484
App.ActiveDocument.C912.Height=20.00
App.ActiveDocument.C912.Angle=360.00 
App.ActiveDocument.C912.Placement=Base.Placement(Base.Vector(34.236325,112.242974,-45.854346),Base.Rotation(0.304914,0.828027,0.000000,0.470530))
App.ActiveDocument.addObject("Part::Cylinder","C913")
App.ActiveDocument.C913.Radius=0.604256
App.ActiveDocument.C913.Height=20.00
App.ActiveDocument.C913.Angle=360.00 
App.ActiveDocument.C913.Placement=Base.Placement(Base.Vector(33.842548,107.655365,-44.020081),Base.Rotation(0.303868,0.831354,0.000000,0.465312))
App.ActiveDocument.addObject("Part::Cylinder","C914")
App.ActiveDocument.C914.Radius=0.602277
App.ActiveDocument.C914.Height=20.00
App.ActiveDocument.C914.Angle=360.00 
App.ActiveDocument.C914.Placement=Base.Placement(Base.Vector(35.032211,108.080409,-44.330196),Base.Rotation(0.684039,0.463943,0.000000,0.562893))
App.ActiveDocument.addObject("Part::Cylinder","C915")
App.ActiveDocument.C915.Radius=0.495804
App.ActiveDocument.C915.Height=20.00
App.ActiveDocument.C915.Angle=360.00 
App.ActiveDocument.C915.Placement=Base.Placement(Base.Vector(40.525003,189.162975,-4.374724),Base.Rotation(-0.467083,0.528433,0.000000,0.708937))
App.ActiveDocument.addObject("Part::Cylinder","C916")
App.ActiveDocument.C916.Radius=0.506231
App.ActiveDocument.C916.Height=20.00
App.ActiveDocument.C916.Angle=360.00 
App.ActiveDocument.C916.Placement=Base.Placement(Base.Vector(40.899774,188.660701,-9.059366),Base.Rotation(-0.469864,0.540329,0.000000,0.698049))
App.ActiveDocument.addObject("Part::Cylinder","C917")
App.ActiveDocument.C917.Radius=0.516591
App.ActiveDocument.C917.Height=20.00
App.ActiveDocument.C917.Angle=360.00 
App.ActiveDocument.C917.Placement=Base.Placement(Base.Vector(41.046727,188.184114,-13.407018),Base.Rotation(-0.482472,0.548275,0.000000,0.683092))
App.ActiveDocument.addObject("Part::Cylinder","C918")
App.ActiveDocument.C918.Radius=0.526563
App.ActiveDocument.C918.Height=20.00
App.ActiveDocument.C918.Angle=360.00 
App.ActiveDocument.C918.Placement=Base.Placement(Base.Vector(41.409773,187.190015,-17.750377),Base.Rotation(-0.486733,0.563606,0.000000,0.667412))
App.ActiveDocument.addObject("Part::Cylinder","C919")
App.ActiveDocument.C919.Radius=0.536593
App.ActiveDocument.C919.Height=20.00
App.ActiveDocument.C919.Angle=360.00 
App.ActiveDocument.C919.Placement=Base.Placement(Base.Vector(41.331790,186.456436,-21.813140),Base.Rotation(-0.494301,0.575993,0.000000,0.651075))
App.ActiveDocument.addObject("Part::Cylinder","C920")
App.ActiveDocument.C920.Radius=0.546290
App.ActiveDocument.C920.Height=20.00
App.ActiveDocument.C920.Angle=360.00 
App.ActiveDocument.C920.Placement=Base.Placement(Base.Vector(41.328014,185.373887,-25.823990),Base.Rotation(-0.493778,0.594256,0.000000,0.634857))
App.ActiveDocument.addObject("Part::Cylinder","C921")
App.ActiveDocument.C921.Radius=0.556339
App.ActiveDocument.C921.Height=20.00
App.ActiveDocument.C921.Angle=360.00 
App.ActiveDocument.C921.Placement=Base.Placement(Base.Vector(41.279767,183.994536,-29.897564),Base.Rotation(-0.485686,0.622060,0.000000,0.614126))
App.ActiveDocument.addObject("Part::Cylinder","C922")
App.ActiveDocument.C922.Radius=0.565429
App.ActiveDocument.C922.Height=20.00
App.ActiveDocument.C922.Angle=360.00 
App.ActiveDocument.C922.Placement=Base.Placement(Base.Vector(41.245132,182.402009,-33.468743),Base.Rotation(-0.482732,0.645459,0.000000,0.591906))
App.ActiveDocument.addObject("Part::Cylinder","C923")
App.ActiveDocument.C923.Radius=0.573105
App.ActiveDocument.C923.Height=20.00
App.ActiveDocument.C923.Angle=360.00 
App.ActiveDocument.C923.Placement=Base.Placement(Base.Vector(41.485059,180.290303,-36.436480),Base.Rotation(-0.467406,0.682082,0.000000,0.562402))
App.ActiveDocument.addObject("Part::Cylinder","C924")
App.ActiveDocument.C924.Radius=0.579785
App.ActiveDocument.C924.Height=20.00
App.ActiveDocument.C924.Angle=360.00 
App.ActiveDocument.C924.Placement=Base.Placement(Base.Vector(41.630220,178.021171,-38.981878),Base.Rotation(-0.437051,0.723395,0.000000,0.534496))
App.ActiveDocument.addObject("Part::Cylinder","C925")
App.ActiveDocument.C925.Radius=0.586045
App.ActiveDocument.C925.Height=20.00
App.ActiveDocument.C925.Angle=360.00 
App.ActiveDocument.C925.Placement=Base.Placement(Base.Vector(41.603422,175.599554,-41.285288),Base.Rotation(-0.384316,0.771643,0.000000,0.506822))
App.ActiveDocument.addObject("Part::Cylinder","C926")
App.ActiveDocument.C926.Radius=0.591174
App.ActiveDocument.C926.Height=20.00
App.ActiveDocument.C926.Angle=360.00 
App.ActiveDocument.C926.Placement=Base.Placement(Base.Vector(41.588812,172.856377,-43.185900),Base.Rotation(-0.329658,0.810190,0.000000,0.484684))
App.ActiveDocument.addObject("Part::Cylinder","C927")
App.ActiveDocument.C927.Radius=0.596187
App.ActiveDocument.C927.Height=20.00
App.ActiveDocument.C927.Angle=360.00 
App.ActiveDocument.C927.Placement=Base.Placement(Base.Vector(41.280216,170.395660,-44.905596),Base.Rotation(-0.270847,0.842599,0.000000,0.465476))
App.ActiveDocument.addObject("Part::Cylinder","C928")
App.ActiveDocument.C928.Radius=0.600586
App.ActiveDocument.C928.Height=20.00
App.ActiveDocument.C928.Angle=360.00 
App.ActiveDocument.C928.Placement=Base.Placement(Base.Vector(41.004010,167.317666,-46.444854),Base.Rotation(-0.210204,0.867702,0.000000,0.450452))
App.ActiveDocument.addObject("Part::Cylinder","C929")
App.ActiveDocument.C929.Radius=0.602791
App.ActiveDocument.C929.Height=20.00
App.ActiveDocument.C929.Angle=360.00 
App.ActiveDocument.C929.Placement=Base.Placement(Base.Vector(40.970780,164.240309,-47.285789),Base.Rotation(-0.142732,0.885516,0.000000,0.442141))
App.ActiveDocument.addObject("Part::Cylinder","C930")
App.ActiveDocument.C930.Radius=0.604837
App.ActiveDocument.C930.Height=20.00
App.ActiveDocument.C930.Angle=360.00 
App.ActiveDocument.C930.Placement=Base.Placement(Base.Vector(40.737429,160.866545,-48.101380),Base.Rotation(-0.068837,0.894676,0.000000,0.441381))
App.ActiveDocument.addObject("Part::Cylinder","C931")
App.ActiveDocument.C931.Radius=0.606639
App.ActiveDocument.C931.Height=20.00
App.ActiveDocument.C931.Angle=360.00 
App.ActiveDocument.C931.Placement=Base.Placement(Base.Vector(40.331595,157.478743,-48.812933),Base.Rotation(-0.004409,0.894940,0.000000,0.446165))
App.ActiveDocument.addObject("Part::Cylinder","C932")
App.ActiveDocument.C932.Radius=0.608272
App.ActiveDocument.C932.Height=20.00
App.ActiveDocument.C932.Angle=360.00 
App.ActiveDocument.C932.Placement=Base.Placement(Base.Vector(39.843383,153.990116,-49.365518),Base.Rotation(0.035174,0.892164,0.000000,0.450339))
App.ActiveDocument.addObject("Part::Cylinder","C933")
App.ActiveDocument.C933.Radius=0.608407
App.ActiveDocument.C933.Height=20.00
App.ActiveDocument.C933.Angle=360.00 
App.ActiveDocument.C933.Placement=Base.Placement(Base.Vector(39.430073,149.700700,-49.499951),Base.Rotation(0.080292,0.882558,0.000000,0.463297))
App.ActiveDocument.addObject("Part::Cylinder","C934")
App.ActiveDocument.C934.Radius=0.609391
App.ActiveDocument.C934.Height=20.00
App.ActiveDocument.C934.Angle=360.00 
App.ActiveDocument.C934.Placement=Base.Placement(Base.Vector(38.843418,145.728150,-49.753007),Base.Rotation(0.102063,0.876824,0.000000,0.469854))
App.ActiveDocument.addObject("Part::Cylinder","C935")
App.ActiveDocument.C935.Radius=0.609674
App.ActiveDocument.C935.Height=20.00
App.ActiveDocument.C935.Angle=360.00 
App.ActiveDocument.C935.Placement=Base.Placement(Base.Vector(38.313554,141.358510,-49.696970),Base.Rotation(0.122387,0.871146,0.000000,0.475526))
App.ActiveDocument.addObject("Part::Cylinder","C936")
App.ActiveDocument.C936.Radius=0.610679
App.ActiveDocument.C936.Height=20.00
App.ActiveDocument.C936.Angle=360.00 
App.ActiveDocument.C936.Placement=Base.Placement(Base.Vector(37.703468,137.434050,-49.733391),Base.Rotation(0.137551,0.869698,0.000000,0.474031))
App.ActiveDocument.addObject("Part::Cylinder","C937")
App.ActiveDocument.C937.Radius=0.610103
App.ActiveDocument.C937.Height=20.00
App.ActiveDocument.C937.Angle=360.00 
App.ActiveDocument.C937.Placement=Base.Placement(Base.Vector(37.350797,133.128335,-49.195910),Base.Rotation(0.151938,0.868334,0.000000,0.472135))
App.ActiveDocument.addObject("Part::Cylinder","C938")
App.ActiveDocument.C938.Radius=0.608549
App.ActiveDocument.C938.Height=20.00
App.ActiveDocument.C938.Angle=360.00 
App.ActiveDocument.C938.Placement=Base.Placement(Base.Vector(37.227583,129.508436,-48.406815),Base.Rotation(0.170157,0.864732,0.000000,0.472530))
App.ActiveDocument.addObject("Part::Cylinder","C939")
App.ActiveDocument.C939.Radius=0.605702
App.ActiveDocument.C939.Height=20.00
App.ActiveDocument.C939.Angle=360.00 
App.ActiveDocument.C939.Placement=Base.Placement(Base.Vector(37.153942,125.229760,-47.131430),Base.Rotation(0.203110,0.855423,0.000000,0.476443))
App.ActiveDocument.addObject("Part::Cylinder","C940")
App.ActiveDocument.C940.Radius=0.602283
App.ActiveDocument.C940.Height=20.00
App.ActiveDocument.C940.Angle=360.00 
App.ActiveDocument.C940.Placement=Base.Placement(Base.Vector(37.120591,121.072292,-45.544235),Base.Rotation(0.231833,0.847493,0.000000,0.477503))
App.ActiveDocument.addObject("Part::Cylinder","C941")
App.ActiveDocument.C941.Radius=0.597195
App.ActiveDocument.C941.Height=20.00
App.ActiveDocument.C941.Angle=360.00 
App.ActiveDocument.C941.Placement=Base.Placement(Base.Vector(37.580385,116.730894,-43.113827),Base.Rotation(0.238085,0.854020,0.000000,0.462563))
App.ActiveDocument.addObject("Part::Cylinder","C942")
App.ActiveDocument.C942.Radius=0.595210
App.ActiveDocument.C942.Height=20.00
App.ActiveDocument.C942.Angle=360.00 
App.ActiveDocument.C942.Placement=Base.Placement(Base.Vector(37.351605,112.566751,-41.742536),Base.Rotation(0.283184,0.845571,0.000000,0.452567))
App.ActiveDocument.addObject("Part::Cylinder","C943")
App.ActiveDocument.C943.Radius=0.591720
App.ActiveDocument.C943.Height=20.00
App.ActiveDocument.C943.Angle=360.00 
App.ActiveDocument.C943.Placement=Base.Placement(Base.Vector(37.018676,108.609884,-40.245149),Base.Rotation(0.338260,0.816191,0.000000,0.468415))
App.ActiveDocument.addObject("Part::Cylinder","C944")
App.ActiveDocument.C944.Radius=0.590277
App.ActiveDocument.C944.Height=20.00
App.ActiveDocument.C944.Angle=360.00 
App.ActiveDocument.C944.Placement=Base.Placement(Base.Vector(38.224798,108.983364,-41.395704),Base.Rotation(0.685071,0.421769,0.000000,0.593960))
App.ActiveDocument.addObject("Part::Cylinder","C945")
App.ActiveDocument.C945.Radius=0.491659
App.ActiveDocument.C945.Height=20.00
App.ActiveDocument.C945.Angle=360.00 
App.ActiveDocument.C945.Placement=Base.Placement(Base.Vector(42.992225,186.080963,-4.371948),Base.Rotation(-0.419186,0.564002,0.000000,0.711467))
App.ActiveDocument.addObject("Part::Cylinder","C946")
App.ActiveDocument.C946.Radius=0.501884
App.ActiveDocument.C946.Height=20.00
App.ActiveDocument.C946.Angle=360.00 
App.ActiveDocument.C946.Placement=Base.Placement(Base.Vector(43.406352,185.505504,-8.976097),Base.Rotation(-0.423421,0.574089,0.000000,0.700811))
App.ActiveDocument.addObject("Part::Cylinder","C947")
App.ActiveDocument.C947.Radius=0.512143
App.ActiveDocument.C947.Height=20.00
App.ActiveDocument.C947.Angle=360.00 
App.ActiveDocument.C947.Placement=Base.Placement(Base.Vector(43.574849,185.012572,-13.372459),Base.Rotation(-0.427001,0.587948,0.000000,0.687013))
App.ActiveDocument.addObject("Part::Cylinder","C948")
App.ActiveDocument.C948.Radius=0.522198
App.ActiveDocument.C948.Height=20.00
App.ActiveDocument.C948.Angle=360.00 
App.ActiveDocument.C948.Placement=Base.Placement(Base.Vector(43.878568,184.008883,-17.707557),Base.Rotation(-0.426724,0.606977,0.000000,0.670437))
App.ActiveDocument.addObject("Part::Cylinder","C949")
App.ActiveDocument.C949.Radius=0.532352
App.ActiveDocument.C949.Height=20.00
App.ActiveDocument.C949.Angle=360.00 
App.ActiveDocument.C949.Placement=Base.Placement(Base.Vector(43.755438,183.289708,-21.795648),Base.Rotation(-0.428925,0.623990,0.000000,0.653191))
App.ActiveDocument.addObject("Part::Cylinder","C950")
App.ActiveDocument.C950.Radius=0.541839
App.ActiveDocument.C950.Height=20.00
App.ActiveDocument.C950.Angle=360.00 
App.ActiveDocument.C950.Placement=Base.Placement(Base.Vector(43.836621,181.956462,-25.769152),Base.Rotation(-0.421996,0.645304,0.000000,0.636790))
App.ActiveDocument.addObject("Part::Cylinder","C951")
App.ActiveDocument.C951.Radius=0.551068
App.ActiveDocument.C951.Height=20.00
App.ActiveDocument.C951.Angle=360.00 
App.ActiveDocument.C951.Placement=Base.Placement(Base.Vector(43.733089,180.625235,-29.495058),Base.Rotation(-0.415386,0.665694,0.000000,0.619924))
App.ActiveDocument.addObject("Part::Cylinder","C952")
App.ActiveDocument.C952.Radius=0.559361
App.ActiveDocument.C952.Height=20.00
App.ActiveDocument.C952.Angle=360.00 
App.ActiveDocument.C952.Placement=Base.Placement(Base.Vector(43.673562,179.062102,-32.725667),Base.Rotation(-0.399610,0.694731,0.000000,0.598047))
App.ActiveDocument.addObject("Part::Cylinder","C953")
App.ActiveDocument.C953.Radius=0.565877
App.ActiveDocument.C953.Height=20.00
App.ActiveDocument.C953.Angle=360.00 
App.ActiveDocument.C953.Placement=Base.Placement(Base.Vector(43.947315,176.685508,-35.454419),Base.Rotation(-0.364888,0.729939,0.000000,0.577967))
App.ActiveDocument.addObject("Part::Cylinder","C954")
App.ActiveDocument.C954.Radius=0.572791
App.ActiveDocument.C954.Height=20.00
App.ActiveDocument.C954.Angle=360.00 
App.ActiveDocument.C954.Placement=Base.Placement(Base.Vector(43.927999,174.371207,-37.938416),Base.Rotation(-0.320190,0.772456,0.000000,0.548444))
App.ActiveDocument.addObject("Part::Cylinder","C955")
App.ActiveDocument.C955.Radius=0.578309
App.ActiveDocument.C955.Height=20.00
App.ActiveDocument.C955.Angle=360.00 
App.ActiveDocument.C955.Placement=Base.Placement(Base.Vector(43.974769,171.492275,-39.980692),Base.Rotation(-0.259971,0.810674,0.000000,0.524616))
App.ActiveDocument.addObject("Part::Cylinder","C956")
App.ActiveDocument.C956.Radius=0.584768
App.ActiveDocument.C956.Height=20.00
App.ActiveDocument.C956.Angle=360.00 
App.ActiveDocument.C956.Placement=Base.Placement(Base.Vector(43.586694,168.580355,-42.143967),Base.Rotation(-0.206362,0.840497,0.000000,0.500978))
App.ActiveDocument.addObject("Part::Cylinder","C957")
App.ActiveDocument.C957.Radius=0.588174
App.ActiveDocument.C957.Height=20.00
App.ActiveDocument.C957.Angle=360.00 
App.ActiveDocument.C957.Placement=Base.Placement(Base.Vector(43.432147,165.804244,-43.363489),Base.Rotation(-0.150808,0.858833,0.000000,0.489554))
App.ActiveDocument.addObject("Part::Cylinder","C958")
App.ActiveDocument.C958.Radius=0.590517
App.ActiveDocument.C958.Height=20.00
App.ActiveDocument.C958.Angle=360.00 
App.ActiveDocument.C958.Placement=Base.Placement(Base.Vector(43.305463,162.329400,-44.253636),Base.Rotation(-0.068423,0.872616,0.000000,0.483591))
App.ActiveDocument.addObject("Part::Cylinder","C959")
App.ActiveDocument.C959.Radius=0.591986
App.ActiveDocument.C959.Height=20.00
App.ActiveDocument.C959.Angle=360.00 
App.ActiveDocument.C959.Placement=Base.Placement(Base.Vector(43.073572,158.556079,-44.837242),Base.Rotation(0.008316,0.874412,0.000000,0.485113))
App.ActiveDocument.addObject("Part::Cylinder","C960")
App.ActiveDocument.C960.Radius=0.594176
App.ActiveDocument.C960.Height=20.00
App.ActiveDocument.C960.Angle=360.00 
App.ActiveDocument.C960.Placement=Base.Placement(Base.Vector(42.529491,154.948073,-45.480534),Base.Rotation(0.051639,0.873227,0.000000,0.484571))
App.ActiveDocument.addObject("Part::Cylinder","C961")
App.ActiveDocument.C961.Radius=0.594873
App.ActiveDocument.C961.Height=20.00
App.ActiveDocument.C961.Angle=360.00 
App.ActiveDocument.C961.Placement=Base.Placement(Base.Vector(42.104169,151.580968,-45.704499),Base.Rotation(0.087236,0.866592,0.000000,0.491333))
App.ActiveDocument.addObject("Part::Cylinder","C962")
App.ActiveDocument.C962.Radius=0.595324
App.ActiveDocument.C962.Height=20.00
App.ActiveDocument.C962.Angle=360.00 
App.ActiveDocument.C962.Placement=Base.Placement(Base.Vector(41.568890,147.032378,-45.702280),Base.Rotation(0.108758,0.861381,0.000000,0.496180))
App.ActiveDocument.addObject("Part::Cylinder","C963")
App.ActiveDocument.C963.Radius=0.596256
App.ActiveDocument.C963.Height=20.00
App.ActiveDocument.C963.Angle=360.00 
App.ActiveDocument.C963.Placement=Base.Placement(Base.Vector(40.960249,142.761758,-45.773380),Base.Rotation(0.116980,0.859847,0.000000,0.496969))
App.ActiveDocument.addObject("Part::Cylinder","C964")
App.ActiveDocument.C964.Radius=0.596778
App.ActiveDocument.C964.Height=20.00
App.ActiveDocument.C964.Angle=360.00 
App.ActiveDocument.C964.Placement=Base.Placement(Base.Vector(40.355514,137.893995,-45.640339),Base.Rotation(0.123009,0.859014,0.000000,0.496955))
App.ActiveDocument.addObject("Part::Cylinder","C965")
App.ActiveDocument.C965.Radius=0.597160
App.ActiveDocument.C965.Height=20.00
App.ActiveDocument.C965.Angle=360.00 
App.ActiveDocument.C965.Placement=Base.Placement(Base.Vector(39.902840,133.954011,-45.436647),Base.Rotation(0.131698,0.859816,0.000000,0.493328))
App.ActiveDocument.addObject("Part::Cylinder","C966")
App.ActiveDocument.C966.Radius=0.594899
App.ActiveDocument.C966.Height=20.00
App.ActiveDocument.C966.Angle=360.00 
App.ActiveDocument.C966.Placement=Base.Placement(Base.Vector(39.935087,130.432258,-44.456896),Base.Rotation(0.146550,0.856500,0.000000,0.494905))
App.ActiveDocument.addObject("Part::Cylinder","C967")
App.ActiveDocument.C967.Radius=0.593882
App.ActiveDocument.C967.Height=20.00
App.ActiveDocument.C967.Angle=360.00 
App.ActiveDocument.C967.Placement=Base.Placement(Base.Vector(39.591780,126.178933,-43.684764),Base.Rotation(0.174744,0.852764,0.000000,0.492198))
App.ActiveDocument.addObject("Part::Cylinder","C968")
App.ActiveDocument.C968.Radius=0.590107
App.ActiveDocument.C968.Height=20.00
App.ActiveDocument.C968.Angle=360.00 
App.ActiveDocument.C968.Placement=Base.Placement(Base.Vector(39.877582,121.867025,-41.741214),Base.Rotation(0.195319,0.856393,0.000000,0.477955))
App.ActiveDocument.addObject("Part::Cylinder","C969")
App.ActiveDocument.C969.Radius=0.584964
App.ActiveDocument.C969.Height=20.00
App.ActiveDocument.C969.Angle=360.00 
App.ActiveDocument.C969.Placement=Base.Placement(Base.Vector(40.163372,117.470217,-39.833071),Base.Rotation(0.189269,0.852453,0.000000,0.487342))
App.ActiveDocument.addObject("Part::Cylinder","C970")
App.ActiveDocument.C970.Radius=0.583130
App.ActiveDocument.C970.Height=20.00
App.ActiveDocument.C970.Angle=360.00 
App.ActiveDocument.C970.Placement=Base.Placement(Base.Vector(39.606245,113.192328,-39.220529),Base.Rotation(0.207447,0.835241,0.000000,0.509253))
App.ActiveDocument.addObject("Part::Cylinder","C971")
App.ActiveDocument.C971.Radius=0.579232
App.ActiveDocument.C971.Height=20.00
App.ActiveDocument.C971.Angle=360.00 
App.ActiveDocument.C971.Placement=Base.Placement(Base.Vector(39.777690,110.050098,-37.004137),Base.Rotation(0.351817,0.791476,0.000000,0.499791))
App.ActiveDocument.addObject("Part::Cylinder","C972")
App.ActiveDocument.C972.Radius=0.577595
App.ActiveDocument.C972.Height=20.00
App.ActiveDocument.C972.Angle=360.00 
App.ActiveDocument.C972.Placement=Base.Placement(Base.Vector(39.150262,107.623238,-35.872778),Base.Rotation(0.518338,0.676031,0.000000,0.523745))
App.ActiveDocument.addObject("Part::Cylinder","C973")
App.ActiveDocument.C973.Radius=0.488082
App.ActiveDocument.C973.Height=20.00
App.ActiveDocument.C973.Angle=360.00 
App.ActiveDocument.C973.Placement=Base.Placement(Base.Vector(45.363565,182.640931,-4.430916),Base.Rotation(-0.381087,0.589065,0.000000,0.712583))
App.ActiveDocument.addObject("Part::Cylinder","C974")
App.ActiveDocument.C974.Radius=0.498277
App.ActiveDocument.C974.Height=20.00
App.ActiveDocument.C974.Angle=360.00 
App.ActiveDocument.C974.Placement=Base.Placement(Base.Vector(45.697219,182.127982,-8.983248),Base.Rotation(-0.382786,0.600606,0.000000,0.701959))
App.ActiveDocument.addObject("Part::Cylinder","C975")
App.ActiveDocument.C975.Radius=0.508506
App.ActiveDocument.C975.Height=20.00
App.ActiveDocument.C975.Angle=360.00 
App.ActiveDocument.C975.Placement=Base.Placement(Base.Vector(45.884810,181.551368,-13.370700),Base.Rotation(-0.381108,0.618539,0.000000,0.687143))
App.ActiveDocument.addObject("Part::Cylinder","C976")
App.ActiveDocument.C976.Radius=0.518128
App.ActiveDocument.C976.Height=20.00
App.ActiveDocument.C976.Angle=360.00 
App.ActiveDocument.C976.Placement=Base.Placement(Base.Vector(46.175529,180.450680,-17.528288),Base.Rotation(-0.373898,0.640435,0.000000,0.670853))
App.ActiveDocument.addObject("Part::Cylinder","C977")
App.ActiveDocument.C977.Radius=0.527993
App.ActiveDocument.C977.Height=20.00
App.ActiveDocument.C977.Angle=360.00 
App.ActiveDocument.C977.Placement=Base.Placement(Base.Vector(46.006790,179.758186,-21.455685),Base.Rotation(-0.372245,0.659209,0.000000,0.653359))
App.ActiveDocument.addObject("Part::Cylinder","C978")
App.ActiveDocument.C978.Radius=0.537366
App.ActiveDocument.C978.Height=20.00
App.ActiveDocument.C978.Angle=360.00 
App.ActiveDocument.C978.Placement=Base.Placement(Base.Vector(46.033959,178.323736,-25.367992),Base.Rotation(-0.355696,0.683804,0.000000,0.637096))
App.ActiveDocument.addObject("Part::Cylinder","C979")
App.ActiveDocument.C979.Radius=0.546894
App.ActiveDocument.C979.Height=20.00
App.ActiveDocument.C979.Angle=360.00 
App.ActiveDocument.C979.Placement=Base.Placement(Base.Vector(45.917674,176.705423,-29.221850),Base.Rotation(-0.334711,0.710435,0.000000,0.619073))
App.ActiveDocument.addObject("Part::Cylinder","C980")
App.ActiveDocument.C980.Radius=0.553672
App.ActiveDocument.C980.Height=20.00
App.ActiveDocument.C980.Angle=360.00 
App.ActiveDocument.C980.Placement=Base.Placement(Base.Vector(46.001188,174.736841,-32.021850),Base.Rotation(-0.305465,0.736643,0.000000,0.603364))
App.ActiveDocument.addObject("Part::Cylinder","C981")
App.ActiveDocument.C981.Radius=0.560235
App.ActiveDocument.C981.Height=20.00
App.ActiveDocument.C981.Angle=360.00 
App.ActiveDocument.C981.Placement=Base.Placement(Base.Vector(45.980890,172.580692,-34.539434),Base.Rotation(-0.264822,0.768304,0.000000,0.582733))
App.ActiveDocument.addObject("Part::Cylinder","C982")
App.ActiveDocument.C982.Radius=0.566430
App.ActiveDocument.C982.Height=20.00
App.ActiveDocument.C982.Angle=360.00 
App.ActiveDocument.C982.Placement=Base.Placement(Base.Vector(45.947954,169.801932,-36.823255),Base.Rotation(-0.207037,0.802419,0.000000,0.559696))
App.ActiveDocument.addObject("Part::Cylinder","C983")
App.ActiveDocument.C983.Radius=0.572005
App.ActiveDocument.C983.Height=20.00
App.ActiveDocument.C983.Angle=360.00 
App.ActiveDocument.C983.Placement=Base.Placement(Base.Vector(45.725846,167.067060,-38.714323),Base.Rotation(-0.156198,0.828077,0.000000,0.538415))
App.ActiveDocument.addObject("Part::Cylinder","C984")
App.ActiveDocument.C984.Radius=0.576546
App.ActiveDocument.C984.Height=20.00
App.ActiveDocument.C984.Angle=360.00 
App.ActiveDocument.C984.Placement=Base.Placement(Base.Vector(45.399574,163.794473,-40.291811),Base.Rotation(-0.082653,0.846827,0.000000,0.525407))
App.ActiveDocument.addObject("Part::Cylinder","C985")
App.ActiveDocument.C985.Radius=0.578106
App.ActiveDocument.C985.Height=20.00
App.ActiveDocument.C985.Angle=360.00 
App.ActiveDocument.C985.Placement=Base.Placement(Base.Vector(45.248867,160.254677,-40.937491),Base.Rotation(-0.007645,0.850756,0.000000,0.525506))
App.ActiveDocument.addObject("Part::Cylinder","C986")
App.ActiveDocument.C986.Radius=0.580470
App.ActiveDocument.C986.Height=20.00
App.ActiveDocument.C986.Angle=360.00 
App.ActiveDocument.C986.Placement=Base.Placement(Base.Vector(44.785342,156.350277,-41.613690),Base.Rotation(0.048099,0.851892,0.000000,0.521505))
App.ActiveDocument.addObject("Part::Cylinder","C987")
App.ActiveDocument.C987.Radius=0.580295
App.ActiveDocument.C987.Height=20.00
App.ActiveDocument.C987.Angle=360.00 
App.ActiveDocument.C987.Placement=Base.Placement(Base.Vector(44.554491,152.344306,-41.437597),Base.Rotation(0.081539,0.848028,0.000000,0.523641))
App.ActiveDocument.addObject("Part::Cylinder","C988")
App.ActiveDocument.C988.Radius=0.581951
App.ActiveDocument.C988.Height=20.00
App.ActiveDocument.C988.Angle=360.00 
App.ActiveDocument.C988.Placement=Base.Placement(Base.Vector(43.983052,148.437494,-41.699791),Base.Rotation(0.102889,0.848658,0.000000,0.518838))
App.ActiveDocument.addObject("Part::Cylinder","C989")
App.ActiveDocument.C989.Radius=0.582553
App.ActiveDocument.C989.Height=20.00
App.ActiveDocument.C989.Angle=360.00 
App.ActiveDocument.C989.Placement=Base.Placement(Base.Vector(43.452231,144.115103,-41.620709),Base.Rotation(0.116525,0.847382,0.000000,0.518040))
App.ActiveDocument.addObject("Part::Cylinder","C990")
App.ActiveDocument.C990.Radius=0.583512
App.ActiveDocument.C990.Height=20.00
App.ActiveDocument.C990.Angle=360.00 
App.ActiveDocument.C990.Placement=Base.Placement(Base.Vector(42.802080,139.807222,-41.717029),Base.Rotation(0.115838,0.846299,0.000000,0.519960))
App.ActiveDocument.addObject("Part::Cylinder","C991")
App.ActiveDocument.C991.Radius=0.583937
App.ActiveDocument.C991.Height=20.00
App.ActiveDocument.C991.Angle=360.00 
App.ActiveDocument.C991.Placement=Base.Placement(Base.Vector(42.258090,135.176186,-41.575081),Base.Rotation(0.112937,0.846910,0.000000,0.519604))
App.ActiveDocument.addObject("Part::Cylinder","C992")
App.ActiveDocument.C992.Radius=0.582071
App.ActiveDocument.C992.Height=20.00
App.ActiveDocument.C992.Angle=360.00 
App.ActiveDocument.C992.Placement=Base.Placement(Base.Vector(42.198878,131.338857,-40.704028),Base.Rotation(0.119794,0.845566,0.000000,0.520258))
App.ActiveDocument.addObject("Part::Cylinder","C993")
App.ActiveDocument.C993.Radius=0.581358
App.ActiveDocument.C993.Height=20.00
App.ActiveDocument.C993.Angle=360.00 
App.ActiveDocument.C993.Placement=Base.Placement(Base.Vector(41.984906,127.581033,-40.033664),Base.Rotation(0.135653,0.847740,0.000000,0.512772))
App.ActiveDocument.addObject("Part::Cylinder","C994")
App.ActiveDocument.C994.Radius=0.578908
App.ActiveDocument.C994.Height=20.00
App.ActiveDocument.C994.Angle=360.00 
App.ActiveDocument.C994.Placement=Base.Placement(Base.Vector(42.064351,124.168649,-38.904262),Base.Rotation(0.140113,0.848367,0.000000,0.510531))
App.ActiveDocument.addObject("Part::Cylinder","C995")
App.ActiveDocument.C995.Radius=0.574477
App.ActiveDocument.C995.Height=20.00
App.ActiveDocument.C995.Angle=360.00 
App.ActiveDocument.C995.Placement=Base.Placement(Base.Vector(42.122117,121.355249,-37.890965),Base.Rotation(0.198703,0.811934,0.000000,0.548890))
App.ActiveDocument.addObject("Part::Cylinder","C996")
App.ActiveDocument.C996.Radius=0.571242
App.ActiveDocument.C996.Height=20.00
App.ActiveDocument.C996.Angle=360.00 
App.ActiveDocument.C996.Placement=Base.Placement(Base.Vector(42.492265,115.793207,-34.763938),Base.Rotation(0.102215,0.874038,0.000000,0.474984))
App.ActiveDocument.addObject("Part::Cylinder","C997")
App.ActiveDocument.C997.Radius=0.568959
App.ActiveDocument.C997.Height=20.00
App.ActiveDocument.C997.Angle=360.00 
App.ActiveDocument.C997.Placement=Base.Placement(Base.Vector(43.541175,111.718115,-32.727917),Base.Rotation(0.166157,0.895151,0.000000,0.413637))
App.ActiveDocument.addObject("Part::Cylinder","C998")
App.ActiveDocument.C998.Radius=0.566024
App.ActiveDocument.C998.Height=20.00
App.ActiveDocument.C998.Angle=360.00 
App.ActiveDocument.C998.Placement=Base.Placement(Base.Vector(44.575489,108.734181,-30.710406),Base.Rotation(0.379988,0.846669,0.000000,0.372505))
App.ActiveDocument.addObject("Part::Cylinder","C999")
App.ActiveDocument.C999.Radius=0.564992
App.ActiveDocument.C999.Height=20.00
App.ActiveDocument.C999.Angle=360.00 
App.ActiveDocument.C999.Placement=Base.Placement(Base.Vector(44.514641,107.806427,-30.380899),Base.Rotation(0.719454,0.536130,0.000000,0.441532))
App.ActiveDocument.addObject("Part::Cylinder","C1000")
App.ActiveDocument.C1000.Radius=0.484184
App.ActiveDocument.C1000.Height=20.00
App.ActiveDocument.C1000.Angle=360.00 
App.ActiveDocument.C1000.Placement=Base.Placement(Base.Vector(47.596543,178.945220,-4.241445),Base.Rotation(-0.338433,0.613860,0.000000,0.713189))
App.ActiveDocument.addObject("Part::Cylinder","C1001")
App.ActiveDocument.C1001.Radius=0.494726
App.ActiveDocument.C1001.Height=20.00
App.ActiveDocument.C1001.Angle=360.00 
App.ActiveDocument.C1001.Placement=Base.Placement(Base.Vector(47.792320,178.595810,-8.844117),Base.Rotation(-0.333511,0.630643,0.000000,0.700757))
App.ActiveDocument.addObject("Part::Cylinder","C1002")
App.ActiveDocument.C1002.Radius=0.504460
App.ActiveDocument.C1002.Height=20.00
App.ActiveDocument.C1002.Angle=360.00 
App.ActiveDocument.C1002.Placement=Base.Placement(Base.Vector(47.991144,177.906677,-13.049490),Base.Rotation(-0.327876,0.648330,0.000000,0.687143))
App.ActiveDocument.addObject("Part::Cylinder","C1003")
App.ActiveDocument.C1003.Radius=0.513884
App.ActiveDocument.C1003.Height=20.00
App.ActiveDocument.C1003.Angle=360.00 
App.ActiveDocument.C1003.Placement=Base.Placement(Base.Vector(48.173274,176.829941,-17.069024),Base.Rotation(-0.311163,0.673163,0.000000,0.670842))
App.ActiveDocument.addObject("Part::Cylinder","C1004")
App.ActiveDocument.C1004.Radius=0.524074
App.ActiveDocument.C1004.Height=20.00
App.ActiveDocument.C1004.Angle=360.00 
App.ActiveDocument.C1004.Placement=Base.Placement(Base.Vector(47.964470,176.045233,-21.106617),Base.Rotation(-0.304707,0.693544,0.000000,0.652802))
App.ActiveDocument.addObject("Part::Cylinder","C1005")
App.ActiveDocument.C1005.Radius=0.533546
App.ActiveDocument.C1005.Height=20.00
App.ActiveDocument.C1005.Angle=360.00 
App.ActiveDocument.C1005.Placement=Base.Placement(Base.Vector(47.848366,174.610430,-24.946753),Base.Rotation(-0.281538,0.718789,0.000000,0.635672))
App.ActiveDocument.addObject("Part::Cylinder","C1006")
App.ActiveDocument.C1006.Radius=0.541595
App.ActiveDocument.C1006.Height=20.00
App.ActiveDocument.C1006.Angle=360.00 
App.ActiveDocument.C1006.Placement=Base.Placement(Base.Vector(47.800176,172.652748,-28.318081),Base.Rotation(-0.247193,0.742172,0.000000,0.622958))
App.ActiveDocument.addObject("Part::Cylinder","C1007")
App.ActiveDocument.C1007.Radius=0.549420
App.ActiveDocument.C1007.Height=20.00
App.ActiveDocument.C1007.Angle=360.00 
App.ActiveDocument.C1007.Placement=Base.Placement(Base.Vector(47.673250,170.353736,-31.417011),Base.Rotation(-0.194626,0.771900,0.000000,0.605220))
App.ActiveDocument.addObject("Part::Cylinder","C1008")
App.ActiveDocument.C1008.Radius=0.554697
App.ActiveDocument.C1008.Height=20.00
App.ActiveDocument.C1008.Angle=360.00 
App.ActiveDocument.C1008.Placement=Base.Placement(Base.Vector(47.612817,167.785644,-33.524875),Base.Rotation(-0.149348,0.790789,0.000000,0.593589))
App.ActiveDocument.addObject("Part::Cylinder","C1009")
App.ActiveDocument.C1009.Radius=0.560391
App.ActiveDocument.C1009.Height=20.00
App.ActiveDocument.C1009.Angle=360.00 
App.ActiveDocument.C1009.Placement=Base.Placement(Base.Vector(47.316027,165.326433,-35.475424),Base.Rotation(-0.093164,0.812769,0.000000,0.575088))
App.ActiveDocument.addObject("Part::Cylinder","C1010")
App.ActiveDocument.C1010.Radius=0.564428
App.ActiveDocument.C1010.Height=20.00
App.ActiveDocument.C1010.Angle=360.00 
App.ActiveDocument.C1010.Placement=Base.Placement(Base.Vector(47.013998,161.844707,-36.892157),Base.Rotation(-0.021823,0.824495,0.000000,0.565448))
App.ActiveDocument.addObject("Part::Cylinder","C1011")
App.ActiveDocument.C1011.Radius=0.566464
App.ActiveDocument.C1011.Height=20.00
App.ActiveDocument.C1011.Angle=360.00 
App.ActiveDocument.C1011.Placement=Base.Placement(Base.Vector(46.739200,158.162115,-37.521065),Base.Rotation(0.029179,0.827414,0.000000,0.560834))
App.ActiveDocument.addObject("Part::Cylinder","C1012")
App.ActiveDocument.C1012.Radius=0.567296
App.ActiveDocument.C1012.Height=20.00
App.ActiveDocument.C1012.Angle=360.00 
App.ActiveDocument.C1012.Placement=Base.Placement(Base.Vector(46.457721,154.067145,-37.664586),Base.Rotation(0.057894,0.827223,0.000000,0.558883))
App.ActiveDocument.addObject("Part::Cylinder","C1013")
App.ActiveDocument.C1013.Radius=0.567076
App.ActiveDocument.C1013.Height=20.00
App.ActiveDocument.C1013.Angle=360.00 
App.ActiveDocument.C1013.Placement=Base.Placement(Base.Vector(46.233565,149.677468,-37.341473),Base.Rotation(0.073936,0.827877,0.000000,0.556015))
App.ActiveDocument.addObject("Part::Cylinder","C1014")
App.ActiveDocument.C1014.Radius=0.570455
App.ActiveDocument.C1014.Height=20.00
App.ActiveDocument.C1014.Angle=360.00 
App.ActiveDocument.C1014.Placement=Base.Placement(Base.Vector(45.572349,146.233141,-37.983417),Base.Rotation(0.101487,0.836302,0.000000,0.538794))
App.ActiveDocument.addObject("Part::Cylinder","C1015")
App.ActiveDocument.C1015.Radius=0.569561
App.ActiveDocument.C1015.Height=20.00
App.ActiveDocument.C1015.Angle=360.00 
App.ActiveDocument.C1015.Placement=Base.Placement(Base.Vector(45.250014,141.849400,-37.377169),Base.Rotation(0.123246,0.833062,0.000000,0.539275))
App.ActiveDocument.addObject("Part::Cylinder","C1016")
App.ActiveDocument.C1016.Radius=0.570854
App.ActiveDocument.C1016.Height=20.00
App.ActiveDocument.C1016.Angle=360.00 
App.ActiveDocument.C1016.Placement=Base.Placement(Base.Vector(44.499573,137.533512,-37.595389),Base.Rotation(0.116108,0.832274,0.000000,0.542069))
App.ActiveDocument.addObject("Part::Cylinder","C1017")
App.ActiveDocument.C1017.Radius=0.569254
App.ActiveDocument.C1017.Height=20.00
App.ActiveDocument.C1017.Angle=360.00 
App.ActiveDocument.C1017.Placement=Base.Placement(Base.Vector(44.274405,133.159250,-36.838594),Base.Rotation(0.101006,0.832055,0.000000,0.545419))
App.ActiveDocument.addObject("Part::Cylinder","C1018")
App.ActiveDocument.C1018.Radius=0.568002
App.ActiveDocument.C1018.Height=20.00
App.ActiveDocument.C1018.Angle=360.00 
App.ActiveDocument.C1018.Placement=Base.Placement(Base.Vector(44.131886,129.361160,-36.156834),Base.Rotation(0.098606,0.833033,0.000000,0.544365))
App.ActiveDocument.addObject("Part::Cylinder","C1019")
App.ActiveDocument.C1019.Radius=0.566475
App.ActiveDocument.C1019.Height=20.00
App.ActiveDocument.C1019.Angle=360.00 
App.ActiveDocument.C1019.Placement=Base.Placement(Base.Vector(44.068769,125.634761,-35.331612),Base.Rotation(0.116036,0.832659,0.000000,0.541493))
App.ActiveDocument.addObject("Part::Cylinder","C1020")
App.ActiveDocument.C1020.Radius=0.561677
App.ActiveDocument.C1020.Height=20.00
App.ActiveDocument.C1020.Angle=360.00 
App.ActiveDocument.C1020.Placement=Base.Placement(Base.Vector(44.646083,120.661243,-32.234883),Base.Rotation(0.071530,0.866670,0.000000,0.493728))
App.ActiveDocument.addObject("Part::Cylinder","C1021")
App.ActiveDocument.C1021.Radius=0.558543
App.ActiveDocument.C1021.Height=20.00
App.ActiveDocument.C1021.Angle=360.00 
App.ActiveDocument.C1021.Placement=Base.Placement(Base.Vector(45.093257,116.061340,-31.229543),Base.Rotation(0.073118,0.863350,0.000000,0.499281))
App.ActiveDocument.addObject("Part::Cylinder","C1022")
App.ActiveDocument.C1022.Radius=0.556098
App.ActiveDocument.C1022.Height=20.00
App.ActiveDocument.C1022.Angle=360.00 
App.ActiveDocument.C1022.Placement=Base.Placement(Base.Vector(45.193931,111.200151,-30.448538),Base.Rotation(0.045419,0.859689,0.000000,0.508795))
App.ActiveDocument.addObject("Part::Cylinder","C1023")
App.ActiveDocument.C1023.Radius=0.554411
App.ActiveDocument.C1023.Height=20.00
App.ActiveDocument.C1023.Angle=360.00 
App.ActiveDocument.C1023.Placement=Base.Placement(Base.Vector(46.430899,107.879627,-28.416950),Base.Rotation(0.238847,0.866139,0.000000,0.439039))
App.ActiveDocument.addObject("Part::Cylinder","C1024")
App.ActiveDocument.C1024.Radius=0.553552
App.ActiveDocument.C1024.Height=20.00
App.ActiveDocument.C1024.Angle=360.00 
App.ActiveDocument.C1024.Placement=Base.Placement(Base.Vector(47.408953,107.056085,-27.406889),Base.Rotation(0.649988,0.617224,0.000000,0.443340))
App.ActiveDocument.addObject("Part::Cylinder","C1025")
App.ActiveDocument.C1025.Radius=0.481674
App.ActiveDocument.C1025.Height=20.00
App.ActiveDocument.C1025.Angle=360.00 
App.ActiveDocument.C1025.Placement=Base.Placement(Base.Vector(49.146884,175.713950,-4.363185),Base.Rotation(-0.261547,0.649777,0.000000,0.713710))
App.ActiveDocument.addObject("Part::Cylinder","C1026")
App.ActiveDocument.C1026.Radius=0.491968
App.ActiveDocument.C1026.Height=20.00
App.ActiveDocument.C1026.Angle=360.00 
App.ActiveDocument.C1026.Placement=Base.Placement(Base.Vector(49.391296,175.132706,-8.924809),Base.Rotation(-0.243197,0.669453,0.000000,0.701917))
App.ActiveDocument.addObject("Part::Cylinder","C1027")
App.ActiveDocument.C1027.Radius=0.501991
App.ActiveDocument.C1027.Height=20.00
App.ActiveDocument.C1027.Angle=360.00 
App.ActiveDocument.C1027.Placement=Base.Placement(Base.Vector(49.473501,174.483045,-13.147429),Base.Rotation(-0.235249,0.687284,0.000000,0.687240))
App.ActiveDocument.addObject("Part::Cylinder","C1028")
App.ActiveDocument.C1028.Radius=0.511424
App.ActiveDocument.C1028.Height=20.00
App.ActiveDocument.C1028.Angle=360.00 
App.ActiveDocument.C1028.Placement=Base.Placement(Base.Vector(49.529630,173.354496,-17.129421),Base.Rotation(-0.212587,0.708474,0.000000,0.672957))
App.ActiveDocument.addObject("Part::Cylinder","C1029")
App.ActiveDocument.C1029.Radius=0.521431
App.ActiveDocument.C1029.Height=20.00
App.ActiveDocument.C1029.Angle=360.00 
App.ActiveDocument.C1029.Placement=Base.Placement(Base.Vector(49.304715,172.409329,-21.091270),Base.Rotation(-0.203096,0.726824,0.000000,0.656109))
App.ActiveDocument.addObject("Part::Cylinder","C1030")
App.ActiveDocument.C1030.Radius=0.529484
App.ActiveDocument.C1030.Height=20.00
App.ActiveDocument.C1030.Angle=360.00 
App.ActiveDocument.C1030.Placement=Base.Placement(Base.Vector(49.205561,170.664483,-24.388222),Base.Rotation(-0.169243,0.746946,0.000000,0.642984))
App.ActiveDocument.addObject("Part::Cylinder","C1031")
App.ActiveDocument.C1031.Radius=0.537012
App.ActiveDocument.C1031.Height=20.00
App.ActiveDocument.C1031.Angle=360.00 
App.ActiveDocument.C1031.Placement=Base.Placement(Base.Vector(49.023099,168.515558,-27.497719),Base.Rotation(-0.122643,0.763998,0.000000,0.633455))
App.ActiveDocument.addObject("Part::Cylinder","C1032")
App.ActiveDocument.C1032.Radius=0.542709
App.ActiveDocument.C1032.Height=20.00
App.ActiveDocument.C1032.Angle=360.00 
App.ActiveDocument.C1032.Placement=Base.Placement(Base.Vector(48.850997,166.023818,-29.828284),Base.Rotation(-0.081637,0.775066,0.000000,0.626585))
App.ActiveDocument.addObject("Part::Cylinder","C1033")
App.ActiveDocument.C1033.Radius=0.548901
App.ActiveDocument.C1033.Height=20.00
App.ActiveDocument.C1033.Angle=360.00 
App.ActiveDocument.C1033.Placement=Base.Placement(Base.Vector(48.493135,163.647702,-32.064632),Base.Rotation(-0.037293,0.789219,0.000000,0.612978))
App.ActiveDocument.addObject("Part::Cylinder","C1034")
App.ActiveDocument.C1034.Radius=0.552619
App.ActiveDocument.C1034.Height=20.00
App.ActiveDocument.C1034.Angle=360.00 
App.ActiveDocument.C1034.Placement=Base.Placement(Base.Vector(48.206636,159.642649,-33.339577),Base.Rotation(0.013186,0.796674,0.000000,0.604265))
App.ActiveDocument.addObject("Part::Cylinder","C1035")
App.ActiveDocument.C1035.Radius=0.554242
App.ActiveDocument.C1035.Height=20.00
App.ActiveDocument.C1035.Angle=360.00 
App.ActiveDocument.C1035.Placement=Base.Placement(Base.Vector(47.958276,155.483186,-33.706227),Base.Rotation(0.038095,0.801601,0.000000,0.596644))
App.ActiveDocument.addObject("Part::Cylinder","C1036")
App.ActiveDocument.C1036.Radius=0.554056
App.ActiveDocument.C1036.Height=20.00
App.ActiveDocument.C1036.Angle=360.00 
App.ActiveDocument.C1036.Placement=Base.Placement(Base.Vector(47.817533,151.318463,-33.422688),Base.Rotation(0.048850,0.803906,0.000000,0.592747))
App.ActiveDocument.addObject("Part::Cylinder","C1037")
App.ActiveDocument.C1037.Radius=0.555207
App.ActiveDocument.C1037.Height=20.00
App.ActiveDocument.C1037.Angle=360.00 
App.ActiveDocument.C1037.Placement=Base.Placement(Base.Vector(47.509332,147.017575,-33.443820),Base.Rotation(0.065998,0.810654,0.000000,0.581794))
App.ActiveDocument.addObject("Part::Cylinder","C1038")
App.ActiveDocument.C1038.Radius=0.556565
App.ActiveDocument.C1038.Height=20.00
App.ActiveDocument.C1038.Angle=360.00 
App.ActiveDocument.C1038.Placement=Base.Placement(Base.Vector(47.129330,143.225770,-33.483220),Base.Rotation(0.098400,0.815630,0.000000,0.570144))
App.ActiveDocument.addObject("Part::Cylinder","C1039")
App.ActiveDocument.C1039.Radius=0.556844
App.ActiveDocument.C1039.Height=20.00
App.ActiveDocument.C1039.Angle=360.00 
App.ActiveDocument.C1039.Placement=Base.Placement(Base.Vector(46.649306,139.072116,-33.195912),Base.Rotation(0.123202,0.814812,0.000000,0.566482))
App.ActiveDocument.addObject("Part::Cylinder","C1040")
App.ActiveDocument.C1040.Radius=0.556778
App.ActiveDocument.C1040.Height=20.00
App.ActiveDocument.C1040.Angle=360.00 
App.ActiveDocument.C1040.Placement=Base.Placement(Base.Vector(46.104993,134.734238,-32.915484),Base.Rotation(0.113101,0.814584,0.000000,0.568912))
App.ActiveDocument.addObject("Part::Cylinder","C1041")
App.ActiveDocument.C1041.Radius=0.554610
App.ActiveDocument.C1041.Height=20.00
App.ActiveDocument.C1041.Angle=360.00 
App.ActiveDocument.C1041.Placement=Base.Placement(Base.Vector(45.904718,130.674721,-32.119469),Base.Rotation(0.088510,0.810333,0.000000,0.579247))
App.ActiveDocument.addObject("Part::Cylinder","C1042")
App.ActiveDocument.C1042.Radius=0.553017
App.ActiveDocument.C1042.Height=20.00
App.ActiveDocument.C1042.Angle=360.00 
App.ActiveDocument.C1042.Placement=Base.Placement(Base.Vector(45.753546,127.323782,-31.650767),Base.Rotation(0.089135,0.801287,0.000000,0.591603))
App.ActiveDocument.addObject("Part::Cylinder","C1043")
App.ActiveDocument.C1043.Radius=0.550960
App.ActiveDocument.C1043.Height=20.00
App.ActiveDocument.C1043.Angle=360.00 
App.ActiveDocument.C1043.Placement=Base.Placement(Base.Vector(46.354631,121.600037,-28.863158),Base.Rotation(-0.111536,0.851732,0.000000,0.511968))
App.ActiveDocument.addObject("Part::Cylinder","C1044")
App.ActiveDocument.C1044.Radius=0.547024
App.ActiveDocument.C1044.Height=20.00
App.ActiveDocument.C1044.Angle=360.00 
App.ActiveDocument.C1044.Placement=Base.Placement(Base.Vector(46.826136,119.467200,-28.449920),Base.Rotation(0.076305,0.831080,0.000000,0.550893))
App.ActiveDocument.addObject("Part::Cylinder","C1045")
App.ActiveDocument.C1045.Radius=0.544469
App.ActiveDocument.C1045.Height=20.00
App.ActiveDocument.C1045.Angle=360.00 
App.ActiveDocument.C1045.Placement=Base.Placement(Base.Vector(46.652569,115.425034,-27.751230),Base.Rotation(0.101173,0.814037,0.000000,0.571933))
App.ActiveDocument.addObject("Part::Cylinder","C1046")
App.ActiveDocument.C1046.Radius=0.542984
App.ActiveDocument.C1046.Height=20.00
App.ActiveDocument.C1046.Angle=360.00 
App.ActiveDocument.C1046.Placement=Base.Placement(Base.Vector(46.343930,110.475335,-27.319869),Base.Rotation(0.056539,0.808186,0.000000,0.586208))
App.ActiveDocument.addObject("Part::Cylinder","C1047")
App.ActiveDocument.C1047.Radius=0.541553
App.ActiveDocument.C1047.Height=20.00
App.ActiveDocument.C1047.Angle=360.00 
App.ActiveDocument.C1047.Placement=Base.Placement(Base.Vector(46.356744,104.956795,-27.421015),Base.Rotation(-0.019267,0.790531,0.000000,0.612119))
App.ActiveDocument.addObject("Part::Cylinder","C1048")
App.ActiveDocument.C1048.Radius=0.541444
App.ActiveDocument.C1048.Height=20.00
App.ActiveDocument.C1048.Angle=360.00 
App.ActiveDocument.C1048.Placement=Base.Placement(Base.Vector(51.181150,109.491260,-27.236728),Base.Rotation(0.718258,0.275864,0.000000,0.638753))
App.ActiveDocument.addObject("Part::Cylinder","C1049")
App.ActiveDocument.C1049.Radius=0.479844
App.ActiveDocument.C1049.Height=20.00
App.ActiveDocument.C1049.Angle=360.00 
App.ActiveDocument.C1049.Placement=Base.Placement(Base.Vector(50.189666,172.342343,-4.408677),Base.Rotation(-0.161951,0.682373,0.000000,0.712838))
App.ActiveDocument.addObject("Part::Cylinder","C1050")
App.ActiveDocument.C1050.Radius=0.489917
App.ActiveDocument.C1050.Height=20.00
App.ActiveDocument.C1050.Angle=360.00 
App.ActiveDocument.C1050.Placement=Base.Placement(Base.Vector(50.385057,171.570283,-8.846939),Base.Rotation(-0.145252,0.696599,0.000000,0.702604))
App.ActiveDocument.addObject("Part::Cylinder","C1051")
App.ActiveDocument.C1051.Radius=0.499820
App.ActiveDocument.C1051.Height=20.00
App.ActiveDocument.C1051.Angle=360.00 
App.ActiveDocument.C1051.Placement=Base.Placement(Base.Vector(50.418528,170.754963,-13.030341),Base.Rotation(-0.126989,0.712922,0.000000,0.689649))
App.ActiveDocument.addObject("Part::Cylinder","C1052")
App.ActiveDocument.C1052.Radius=0.509494
App.ActiveDocument.C1052.Height=20.00
App.ActiveDocument.C1052.Angle=360.00 
App.ActiveDocument.C1052.Placement=Base.Placement(Base.Vector(50.317648,169.718042,-17.020722),Base.Rotation(-0.109453,0.728081,0.000000,0.676696))
App.ActiveDocument.addObject("Part::Cylinder","C1053")
App.ActiveDocument.C1053.Radius=0.518692
App.ActiveDocument.C1053.Height=20.00
App.ActiveDocument.C1053.Angle=360.00 
App.ActiveDocument.C1053.Placement=Base.Placement(Base.Vector(50.127501,168.256134,-20.751754),Base.Rotation(-0.082678,0.743147,0.000000,0.664000))
App.ActiveDocument.addObject("Part::Cylinder","C1054")
App.ActiveDocument.C1054.Radius=0.526099
App.ActiveDocument.C1054.Height=20.00
App.ActiveDocument.C1054.Angle=360.00 
App.ActiveDocument.C1054.Placement=Base.Placement(Base.Vector(49.911394,166.361033,-23.759124),Base.Rotation(-0.053466,0.753467,0.000000,0.655309))
App.ActiveDocument.addObject("Part::Cylinder","C1055")
App.ActiveDocument.C1055.Radius=0.532956
App.ActiveDocument.C1055.Height=20.00
App.ActiveDocument.C1055.Angle=360.00 
App.ActiveDocument.C1055.Placement=Base.Placement(Base.Vector(49.638674,163.585815,-26.492548),Base.Rotation(-0.026689,0.761742,0.000000,0.647330))
App.ActiveDocument.addObject("Part::Cylinder","C1056")
App.ActiveDocument.C1056.Radius=0.538523
App.ActiveDocument.C1056.Height=20.00
App.ActiveDocument.C1056.Angle=360.00 
App.ActiveDocument.C1056.Placement=Base.Placement(Base.Vector(49.305963,161.002988,-28.633182),Base.Rotation(-0.003095,0.767838,0.000000,0.640637))
App.ActiveDocument.addObject("Part::Cylinder","C1057")
App.ActiveDocument.C1057.Radius=0.541226
App.ActiveDocument.C1057.Height=20.00
App.ActiveDocument.C1057.Angle=360.00 
App.ActiveDocument.C1057.Placement=Base.Placement(Base.Vector(49.082221,157.104414,-29.464982),Base.Rotation(0.021018,0.775060,0.000000,0.631538))
App.ActiveDocument.addObject("Part::Cylinder","C1058")
App.ActiveDocument.C1058.Radius=0.541109
App.ActiveDocument.C1058.Height=20.00
App.ActiveDocument.C1058.Angle=360.00 
App.ActiveDocument.C1058.Placement=Base.Placement(Base.Vector(48.990768,152.981019,-29.247549),Base.Rotation(0.027807,0.777919,0.000000,0.627749))
App.ActiveDocument.addObject("Part::Cylinder","C1059")
App.ActiveDocument.C1059.Radius=0.541919
App.ActiveDocument.C1059.Height=20.00
App.ActiveDocument.C1059.Angle=360.00 
App.ActiveDocument.C1059.Placement=Base.Placement(Base.Vector(48.814635,148.549079,-29.229247),Base.Rotation(0.035068,0.785441,0.000000,0.617943))
App.ActiveDocument.addObject("Part::Cylinder","C1060")
App.ActiveDocument.C1060.Radius=0.543013
App.ActiveDocument.C1060.Height=20.00
App.ActiveDocument.C1060.Angle=360.00 
App.ActiveDocument.C1060.Placement=Base.Placement(Base.Vector(48.583438,144.546336,-29.283122),Base.Rotation(0.055032,0.792401,0.000000,0.607513))
App.ActiveDocument.addObject("Part::Cylinder","C1061")
App.ActiveDocument.C1061.Radius=0.543591
App.ActiveDocument.C1061.Height=20.00
App.ActiveDocument.C1061.Angle=360.00 
App.ActiveDocument.C1061.Placement=Base.Placement(Base.Vector(48.289438,140.933940,-29.139711),Base.Rotation(0.098303,0.793575,0.000000,0.600480))
App.ActiveDocument.addObject("Part::Cylinder","C1062")
App.ActiveDocument.C1062.Radius=0.543829
App.ActiveDocument.C1062.Height=20.00
App.ActiveDocument.C1062.Angle=360.00 
App.ActiveDocument.C1062.Placement=Base.Placement(Base.Vector(47.778167,137.057621,-29.010070),Base.Rotation(0.124206,0.787310,0.000000,0.603917))
App.ActiveDocument.addObject("Part::Cylinder","C1063")
App.ActiveDocument.C1063.Radius=0.542398
App.ActiveDocument.C1063.Height=20.00
App.ActiveDocument.C1063.Angle=360.00 
App.ActiveDocument.C1063.Placement=Base.Placement(Base.Vector(47.185138,132.717453,-28.633197),Base.Rotation(0.119074,0.770591,0.000000,0.626108))
App.ActiveDocument.addObject("Part::Cylinder","C1064")
App.ActiveDocument.C1064.Radius=0.540710
App.ActiveDocument.C1064.Height=20.00
App.ActiveDocument.C1064.Angle=360.00 
App.ActiveDocument.C1064.Placement=Base.Placement(Base.Vector(46.731457,128.741602,-28.036782),Base.Rotation(0.103600,0.760346,0.000000,0.641203))
App.ActiveDocument.addObject("Part::Cylinder","C1065")
App.ActiveDocument.C1065.Radius=0.538501
App.ActiveDocument.C1065.Height=20.00
App.ActiveDocument.C1065.Angle=360.00 
App.ActiveDocument.C1065.Placement=Base.Placement(Base.Vector(48.232259,122.652452,-25.519606),Base.Rotation(-0.100804,0.825809,0.000000,0.554868))
App.ActiveDocument.addObject("Part::Cylinder","C1066")
App.ActiveDocument.C1066.Radius=0.534348
App.ActiveDocument.C1066.Height=20.00
App.ActiveDocument.C1066.Angle=360.00 
App.ActiveDocument.C1066.Placement=Base.Placement(Base.Vector(48.192424,120.149057,-24.824530),Base.Rotation(0.087556,0.796678,0.000000,0.598029))
App.ActiveDocument.addObject("Part::Cylinder","C1067")
App.ActiveDocument.C1067.Radius=0.532351
App.ActiveDocument.C1067.Height=20.00
App.ActiveDocument.C1067.Angle=360.00 
App.ActiveDocument.C1067.Placement=Base.Placement(Base.Vector(47.788684,115.894239,-24.108276),Base.Rotation(0.112586,0.781019,0.000000,0.614275))
App.ActiveDocument.addObject("Part::Cylinder","C1068")
App.ActiveDocument.C1068.Radius=0.530801
App.ActiveDocument.C1068.Height=20.00
App.ActiveDocument.C1068.Angle=360.00 
App.ActiveDocument.C1068.Placement=Base.Placement(Base.Vector(47.337926,110.707559,-23.544957),Base.Rotation(0.061252,0.776328,0.000000,0.627346))
App.ActiveDocument.addObject("Part::Cylinder","C1069")
App.ActiveDocument.C1069.Radius=0.529822
App.ActiveDocument.C1069.Height=20.00
App.ActiveDocument.C1069.Angle=360.00 
App.ActiveDocument.C1069.Placement=Base.Placement(Base.Vector(47.160867,104.837054,-23.496508),Base.Rotation(-0.019721,0.764388,0.000000,0.644455))
App.ActiveDocument.addObject("Part::Cylinder","C1070")
App.ActiveDocument.C1070.Radius=0.530086
App.ActiveDocument.C1070.Height=20.00
App.ActiveDocument.C1070.Angle=360.00 
App.ActiveDocument.C1070.Placement=Base.Placement(Base.Vector(50.996423,109.154106,-23.847633),Base.Rotation(0.643348,0.347556,0.000000,0.682135))
App.ActiveDocument.addObject("Part::Cylinder","C1071")
App.ActiveDocument.C1071.Radius=0.478817
App.ActiveDocument.C1071.Height=20.00
App.ActiveDocument.C1071.Angle=360.00 
App.ActiveDocument.C1071.Placement=Base.Placement(Base.Vector(50.969635,168.185761,-4.392551),Base.Rotation(-0.101347,0.698318,0.000000,0.708577))
App.ActiveDocument.addObject("Part::Cylinder","C1072")
App.ActiveDocument.C1072.Radius=0.488930
App.ActiveDocument.C1072.Height=20.00
App.ActiveDocument.C1072.Angle=360.00 
App.ActiveDocument.C1072.Placement=Base.Placement(Base.Vector(51.030755,167.420553,-8.739606),Base.Rotation(-0.084177,0.711247,0.000000,0.697884))
App.ActiveDocument.addObject("Part::Cylinder","C1073")
App.ActiveDocument.C1073.Radius=0.498835
App.ActiveDocument.C1073.Height=20.00
App.ActiveDocument.C1073.Angle=360.00 
App.ActiveDocument.C1073.Placement=Base.Placement(Base.Vector(50.965807,166.395904,-12.895658),Base.Rotation(-0.062991,0.724341,0.000000,0.686558))
App.ActiveDocument.addObject("Part::Cylinder","C1074")
App.ActiveDocument.C1074.Radius=0.508162
App.ActiveDocument.C1074.Height=20.00
App.ActiveDocument.C1074.Angle=360.00 
App.ActiveDocument.C1074.Placement=Base.Placement(Base.Vector(50.762046,165.383380,-16.709355),Base.Rotation(-0.044107,0.735914,0.000000,0.675637))
App.ActiveDocument.addObject("Part::Cylinder","C1075")
App.ActiveDocument.C1075.Radius=0.516628
App.ActiveDocument.C1075.Height=20.00
App.ActiveDocument.C1075.Angle=360.00 
App.ActiveDocument.C1075.Placement=Base.Placement(Base.Vector(50.510204,163.331595,-20.131560),Base.Rotation(-0.023432,0.745708,0.000000,0.665861))
App.ActiveDocument.addObject("Part::Cylinder","C1076")
App.ActiveDocument.C1076.Radius=0.522599
App.ActiveDocument.C1076.Height=20.00
App.ActiveDocument.C1076.Angle=360.00 
App.ActiveDocument.C1076.Placement=Base.Placement(Base.Vector(50.259734,160.907501,-22.499146),Base.Rotation(-0.005185,0.752132,0.000000,0.658992))
App.ActiveDocument.addObject("Part::Cylinder","C1077")
App.ActiveDocument.C1077.Radius=0.528542
App.ActiveDocument.C1077.Height=20.00
App.ActiveDocument.C1077.Angle=360.00 
App.ActiveDocument.C1077.Placement=Base.Placement(Base.Vector(49.922343,158.168133,-24.776876),Base.Rotation(0.009459,0.758711,0.000000,0.651359))
App.ActiveDocument.addObject("Part::Cylinder","C1078")
App.ActiveDocument.C1078.Radius=0.527921
App.ActiveDocument.C1078.Height=20.00
App.ActiveDocument.C1078.Angle=360.00 
App.ActiveDocument.C1078.Placement=Base.Placement(Base.Vector(49.905766,154.223969,-24.431789),Base.Rotation(0.013238,0.760245,0.000000,0.649501))
App.ActiveDocument.addObject("Part::Cylinder","C1079")
App.ActiveDocument.C1079.Radius=0.528504
App.ActiveDocument.C1079.Height=20.00
App.ActiveDocument.C1079.Angle=360.00 
App.ActiveDocument.C1079.Placement=Base.Placement(Base.Vector(49.845797,150.106426,-24.440937),Base.Rotation(0.011711,0.766797,0.000000,0.641783))
App.ActiveDocument.addObject("Part::Cylinder","C1080")
App.ActiveDocument.C1080.Radius=0.530211
App.ActiveDocument.C1080.Height=20.00
App.ActiveDocument.C1080.Angle=360.00 
App.ActiveDocument.C1080.Placement=Base.Placement(Base.Vector(49.689265,145.805894,-24.858982),Base.Rotation(0.026603,0.773996,0.000000,0.632632))
App.ActiveDocument.addObject("Part::Cylinder","C1081")
App.ActiveDocument.C1081.Radius=0.530367
App.ActiveDocument.C1081.Height=20.00
App.ActiveDocument.C1081.Angle=360.00 
App.ActiveDocument.C1081.Placement=Base.Placement(Base.Vector(49.511536,142.263292,-24.733134),Base.Rotation(0.075049,0.772692,0.000000,0.630329))
App.ActiveDocument.addObject("Part::Cylinder","C1082")
App.ActiveDocument.C1082.Radius=0.531430
App.ActiveDocument.C1082.Height=20.00
App.ActiveDocument.C1082.Angle=360.00 
App.ActiveDocument.C1082.Placement=Base.Placement(Base.Vector(48.999851,138.765178,-25.025769),Base.Rotation(0.129048,0.760436,0.000000,0.636462))
App.ActiveDocument.addObject("Part::Cylinder","C1083")
App.ActiveDocument.C1083.Radius=0.530965
App.ActiveDocument.C1083.Height=20.00
App.ActiveDocument.C1083.Angle=360.00 
App.ActiveDocument.C1083.Placement=Base.Placement(Base.Vector(48.372022,135.582619,-24.959745),Base.Rotation(0.158547,0.737383,0.000000,0.656604))
App.ActiveDocument.addObject("Part::Cylinder","C1084")
App.ActiveDocument.C1084.Radius=0.528961
App.ActiveDocument.C1084.Height=20.00
App.ActiveDocument.C1084.Angle=360.00 
App.ActiveDocument.C1084.Placement=Base.Placement(Base.Vector(49.059617,134.729694,-26.163880),Base.Rotation(0.375630,0.545182,0.000000,0.749452))
App.ActiveDocument.addObject("Part::Cylinder","C1085")
App.ActiveDocument.C1085.Radius=0.525435
App.ActiveDocument.C1085.Height=20.00
App.ActiveDocument.C1085.Angle=360.00 
App.ActiveDocument.C1085.Placement=Base.Placement(Base.Vector(51.362030,132.224859,-25.729967),Base.Rotation(0.419537,0.507136,0.000000,0.752863))
App.ActiveDocument.addObject("Part::Cylinder","C1086")
App.ActiveDocument.C1086.Radius=0.523634
App.ActiveDocument.C1086.Height=20.00
App.ActiveDocument.C1086.Angle=360.00 
App.ActiveDocument.C1086.Placement=Base.Placement(Base.Vector(49.249056,122.681413,-21.635999),Base.Rotation(0.050565,0.771704,0.000000,0.633969))
App.ActiveDocument.addObject("Part::Cylinder","C1087")
App.ActiveDocument.C1087.Radius=0.520872
App.ActiveDocument.C1087.Height=20.00
App.ActiveDocument.C1087.Angle=360.00 
App.ActiveDocument.C1087.Placement=Base.Placement(Base.Vector(49.097641,119.311341,-20.672917),Base.Rotation(0.108678,0.752881,0.000000,0.649122))
App.ActiveDocument.addObject("Part::Cylinder","C1088")
App.ActiveDocument.C1088.Radius=0.520180
App.ActiveDocument.C1088.Height=20.00
App.ActiveDocument.C1088.Angle=360.00 
App.ActiveDocument.C1088.Placement=Base.Placement(Base.Vector(48.526115,115.537152,-19.883351),Base.Rotation(0.141904,0.750027,0.000000,0.646005))
App.ActiveDocument.addObject("Part::Cylinder","C1089")
App.ActiveDocument.C1089.Radius=0.519130
App.ActiveDocument.C1089.Height=20.00
App.ActiveDocument.C1089.Angle=360.00 
App.ActiveDocument.C1089.Placement=Base.Placement(Base.Vector(47.643032,110.455490,-19.981665),Base.Rotation(0.090967,0.724803,0.000000,0.682924))
App.ActiveDocument.addObject("Part::Cylinder","C1090")
App.ActiveDocument.C1090.Radius=0.518159
App.ActiveDocument.C1090.Height=20.00
App.ActiveDocument.C1090.Angle=360.00 
App.ActiveDocument.C1090.Placement=Base.Placement(Base.Vector(47.510846,104.126293,-20.350322),Base.Rotation(-0.026344,0.700879,0.000000,0.712793))
App.ActiveDocument.addObject("Part::Cylinder","C1091")
App.ActiveDocument.C1091.Radius=0.519792
App.ActiveDocument.C1091.Height=20.00
App.ActiveDocument.C1091.Angle=360.00 
App.ActiveDocument.C1091.Placement=Base.Placement(Base.Vector(46.531909,103.700562,-20.430381),Base.Rotation(0.247822,0.643314,0.000000,0.724383))
App.ActiveDocument.addObject("Part::Cylinder","C1092")
App.ActiveDocument.C1092.Radius=0.477537
App.ActiveDocument.C1092.Height=20.00
App.ActiveDocument.C1092.Angle=360.00 
App.ActiveDocument.C1092.Placement=Base.Placement(Base.Vector(51.484997,163.829822,-4.004440),Base.Rotation(-0.065054,0.708091,0.000000,0.703118))
App.ActiveDocument.addObject("Part::Cylinder","C1093")
App.ActiveDocument.C1093.Radius=0.487715
App.ActiveDocument.C1093.Height=20.00
App.ActiveDocument.C1093.Angle=360.00 
App.ActiveDocument.C1093.Placement=Base.Placement(Base.Vector(51.444357,162.856950,-8.300237),Base.Rotation(-0.043935,0.720573,0.000000,0.691986))
App.ActiveDocument.addObject("Part::Cylinder","C1094")
App.ActiveDocument.C1094.Radius=0.497806
App.ActiveDocument.C1094.Height=20.00
App.ActiveDocument.C1094.Angle=360.00 
App.ActiveDocument.C1094.Placement=Base.Placement(Base.Vector(51.266099,161.612094,-12.505573),Base.Rotation(-0.028571,0.730535,0.000000,0.682277))
App.ActiveDocument.addObject("Part::Cylinder","C1095")
App.ActiveDocument.C1095.Radius=0.506248
App.ActiveDocument.C1095.Height=20.00
App.ActiveDocument.C1095.Angle=360.00 
App.ActiveDocument.C1095.Placement=Base.Placement(Base.Vector(51.007949,160.477745,-15.894889),Base.Rotation(-0.012366,0.740449,0.000000,0.671999))
App.ActiveDocument.addObject("Part::Cylinder","C1096")
App.ActiveDocument.C1096.Radius=0.512342
App.ActiveDocument.C1096.Height=20.00
App.ActiveDocument.C1096.Angle=360.00 
App.ActiveDocument.C1096.Placement=Base.Placement(Base.Vector(50.768754,158.004122,-18.323728),Base.Rotation(0.001658,0.746719,0.000000,0.665138))
App.ActiveDocument.addObject("Part::Cylinder","C1097")
App.ActiveDocument.C1097.Radius=0.517911
App.ActiveDocument.C1097.Height=20.00
App.ActiveDocument.C1097.Angle=360.00 
App.ActiveDocument.C1097.Placement=Base.Placement(Base.Vector(50.476344,155.086484,-20.514219),Base.Rotation(0.007039,0.751706,0.000000,0.659461))
App.ActiveDocument.addObject("Part::Cylinder","C1098")
App.ActiveDocument.C1098.Radius=0.516907
App.ActiveDocument.C1098.Height=20.00
App.ActiveDocument.C1098.Angle=360.00 
App.ActiveDocument.C1098.Placement=Base.Placement(Base.Vector(50.522620,150.178445,-20.014692),Base.Rotation(0.000096,0.753952,0.000000,0.656929))
App.ActiveDocument.addObject("Part::Cylinder","C1099")
App.ActiveDocument.C1099.Radius=0.518690
App.ActiveDocument.C1099.Height=20.00
App.ActiveDocument.C1099.Angle=360.00 
App.ActiveDocument.C1099.Placement=Base.Placement(Base.Vector(50.426465,145.889793,-20.670470),Base.Rotation(0.013972,0.756715,0.000000,0.653596))
App.ActiveDocument.addObject("Part::Cylinder","C1100")
App.ActiveDocument.C1100.Radius=0.518319
App.ActiveDocument.C1100.Height=20.00
App.ActiveDocument.C1100.Angle=360.00 
App.ActiveDocument.C1100.Placement=Base.Placement(Base.Vector(50.278682,142.034438,-20.415912),Base.Rotation(0.087488,0.750480,0.000000,0.655077))
App.ActiveDocument.addObject("Part::Cylinder","C1101")
App.ActiveDocument.C1101.Radius=0.519020
App.ActiveDocument.C1101.Height=20.00
App.ActiveDocument.C1101.Angle=360.00 
App.ActiveDocument.C1101.Placement=Base.Placement(Base.Vector(49.688713,138.910011,-20.606138),Base.Rotation(0.174524,0.723850,0.000000,0.667519))
App.ActiveDocument.addObject("Part::Cylinder","C1102")
App.ActiveDocument.C1102.Radius=0.518913
App.ActiveDocument.C1102.Height=20.00
App.ActiveDocument.C1102.Angle=360.00 
App.ActiveDocument.C1102.Placement=Base.Placement(Base.Vector(48.626302,132.316067,-18.601316),Base.Rotation(-0.027643,0.787675,0.000000,0.615471))
App.ActiveDocument.addObject("Part::Cylinder","C1103")
App.ActiveDocument.C1103.Radius=0.514321
App.ActiveDocument.C1103.Height=20.00
App.ActiveDocument.C1103.Angle=360.00 
App.ActiveDocument.C1103.Placement=Base.Placement(Base.Vector(51.095214,124.980267,-16.277431),Base.Rotation(-0.346506,0.742791,0.000000,0.572883))
App.ActiveDocument.addObject("Part::Cylinder","C1104")
App.ActiveDocument.C1104.Radius=0.511762
App.ActiveDocument.C1104.Height=20.00
App.ActiveDocument.C1104.Angle=360.00 
App.ActiveDocument.C1104.Placement=Base.Placement(Base.Vector(50.017914,125.432341,-17.678638),Base.Rotation(0.072862,0.740005,0.000000,0.668643))
App.ActiveDocument.addObject("Part::Cylinder","C1105")
App.ActiveDocument.C1105.Radius=0.510083
App.ActiveDocument.C1105.Height=20.00
App.ActiveDocument.C1105.Angle=360.00 
App.ActiveDocument.C1105.Placement=Base.Placement(Base.Vector(49.601891,121.568531,-17.299696),Base.Rotation(0.088845,0.716861,0.000000,0.691532))
App.ActiveDocument.addObject("Part::Cylinder","C1106")
App.ActiveDocument.C1106.Radius=0.508251
App.ActiveDocument.C1106.Height=20.00
App.ActiveDocument.C1106.Angle=360.00 
App.ActiveDocument.C1106.Placement=Base.Placement(Base.Vector(49.089263,117.365986,-16.660472),Base.Rotation(0.087161,0.699538,0.000000,0.709260))
App.ActiveDocument.addObject("Part::Cylinder","C1107")
App.ActiveDocument.C1107.Radius=0.507678
App.ActiveDocument.C1107.Height=20.00
App.ActiveDocument.C1107.Angle=360.00 
App.ActiveDocument.C1107.Placement=Base.Placement(Base.Vector(48.634229,113.968368,-15.947195),Base.Rotation(0.130916,0.697061,0.000000,0.704959))
App.ActiveDocument.addObject("Part::Cylinder","C1108")
App.ActiveDocument.C1108.Radius=0.507860
App.ActiveDocument.C1108.Height=20.00
App.ActiveDocument.C1108.Angle=360.00 
App.ActiveDocument.C1108.Placement=Base.Placement(Base.Vector(47.538223,109.405519,-16.134977),Base.Rotation(0.125353,0.669556,0.000000,0.732108))
App.ActiveDocument.addObject("Part::Cylinder","C1109")
App.ActiveDocument.C1109.Radius=0.507741
App.ActiveDocument.C1109.Height=20.00
App.ActiveDocument.C1109.Angle=360.00 
App.ActiveDocument.C1109.Placement=Base.Placement(Base.Vector(47.146594,103.163474,-17.295572),Base.Rotation(0.007844,0.624460,0.000000,0.781017))
App.ActiveDocument.addObject("Part::Cylinder","C1110")
App.ActiveDocument.C1110.Radius=0.513198
App.ActiveDocument.C1110.Height=20.00
App.ActiveDocument.C1110.Angle=360.00 
App.ActiveDocument.C1110.Placement=Base.Placement(Base.Vector(53.752131,110.004171,-15.676439),Base.Rotation(0.707107,0.000000,0.000000,0.707107))
App.ActiveDocument.addObject("Part::Cylinder","C1111")
App.ActiveDocument.C1111.Radius=0.477144
App.ActiveDocument.C1111.Height=20.00
App.ActiveDocument.C1111.Angle=360.00 
App.ActiveDocument.C1111.Placement=Base.Placement(Base.Vector(51.783830,159.411447,-3.849152),Base.Rotation(-0.029791,0.716573,0.000000,0.696876))
App.ActiveDocument.addObject("Part::Cylinder","C1112")
App.ActiveDocument.C1112.Radius=0.488620
App.ActiveDocument.C1112.Height=20.00
App.ActiveDocument.C1112.Angle=360.00 
App.ActiveDocument.C1112.Placement=Base.Placement(Base.Vector(51.598995,158.661758,-8.673528),Base.Rotation(-0.018138,0.726382,0.000000,0.687051))
App.ActiveDocument.addObject("Part::Cylinder","C1113")
App.ActiveDocument.C1113.Radius=0.498535
App.ActiveDocument.C1113.Height=20.00
App.ActiveDocument.C1113.Angle=360.00 
App.ActiveDocument.C1113.Placement=Base.Placement(Base.Vector(51.332441,156.800003,-12.719482),Base.Rotation(-0.004543,0.736338,0.000000,0.676598))
App.ActiveDocument.addObject("Part::Cylinder","C1114")
App.ActiveDocument.C1114.Radius=0.504989
App.ActiveDocument.C1114.Height=20.00
App.ActiveDocument.C1114.Angle=360.00 
App.ActiveDocument.C1114.Placement=Base.Placement(Base.Vector(51.086778,153.593619,-15.302814),Base.Rotation(0.001543,0.742735,0.000000,0.669583))
App.ActiveDocument.addObject("Part::Cylinder","C1115")
App.ActiveDocument.C1115.Radius=0.505737
App.ActiveDocument.C1115.Height=20.00
App.ActiveDocument.C1115.Angle=360.00 
App.ActiveDocument.C1115.Placement=Base.Placement(Base.Vector(51.040823,148.606420,-15.661253),Base.Rotation(0.003420,0.741248,0.000000,0.671222))
App.ActiveDocument.addObject("Part::Cylinder","C1116")
App.ActiveDocument.C1116.Radius=0.506980
App.ActiveDocument.C1116.Height=20.00
App.ActiveDocument.C1116.Angle=360.00 
App.ActiveDocument.C1116.Placement=Base.Placement(Base.Vector(50.925569,144.426124,-16.261630),Base.Rotation(0.035606,0.736800,0.000000,0.675173))
App.ActiveDocument.addObject("Part::Cylinder","C1117")
App.ActiveDocument.C1117.Radius=0.506501
App.ActiveDocument.C1117.Height=20.00
App.ActiveDocument.C1117.Angle=360.00 
App.ActiveDocument.C1117.Placement=Base.Placement(Base.Vector(50.699274,141.174771,-15.793906),Base.Rotation(0.121892,0.728791,0.000000,0.673800))
App.ActiveDocument.addObject("Part::Cylinder","C1118")
App.ActiveDocument.C1118.Radius=0.506945
App.ActiveDocument.C1118.Height=20.00
App.ActiveDocument.C1118.Angle=360.00 
App.ActiveDocument.C1118.Placement=Base.Placement(Base.Vector(50.396165,133.779793,-12.359224),Base.Rotation(-0.131211,0.824127,0.000000,0.550997))
App.ActiveDocument.addObject("Part::Cylinder","C1119")
App.ActiveDocument.C1119.Radius=0.503881
App.ActiveDocument.C1119.Height=20.00
App.ActiveDocument.C1119.Angle=360.00 
App.ActiveDocument.C1119.Placement=Base.Placement(Base.Vector(50.327256,130.815108,-13.323548),Base.Rotation(-0.036492,0.772456,0.000000,0.634019))
App.ActiveDocument.addObject("Part::Cylinder","C1120")
App.ActiveDocument.C1120.Radius=0.500112
App.ActiveDocument.C1120.Height=20.00
App.ActiveDocument.C1120.Angle=360.00 
App.ActiveDocument.C1120.Placement=Base.Placement(Base.Vector(50.843741,128.146681,-12.810694),Base.Rotation(0.067077,0.743079,0.000000,0.665833))
App.ActiveDocument.addObject("Part::Cylinder","C1121")
App.ActiveDocument.C1121.Radius=0.498778
App.ActiveDocument.C1121.Height=20.00
App.ActiveDocument.C1121.Angle=360.00 
App.ActiveDocument.C1121.Placement=Base.Placement(Base.Vector(50.317664,124.936433,-12.449715),Base.Rotation(0.138360,0.711807,0.000000,0.688613))
App.ActiveDocument.addObject("Part::Cylinder","C1122")
App.ActiveDocument.C1122.Radius=0.497770
App.ActiveDocument.C1122.Height=20.00
App.ActiveDocument.C1122.Angle=360.00 
App.ActiveDocument.C1122.Placement=Base.Placement(Base.Vector(49.533714,120.985428,-11.988386),Base.Rotation(0.132075,0.696836,0.000000,0.704966))
App.ActiveDocument.addObject("Part::Cylinder","C1123")
App.ActiveDocument.C1123.Radius=0.496725
App.ActiveDocument.C1123.Height=20.00
App.ActiveDocument.C1123.Angle=360.00 
App.ActiveDocument.C1123.Placement=Base.Placement(Base.Vector(48.704704,116.314696,-11.591045),Base.Rotation(0.110495,0.680440,0.000000,0.724425))
App.ActiveDocument.addObject("Part::Cylinder","C1124")
App.ActiveDocument.C1124.Radius=0.496830
App.ActiveDocument.C1124.Height=20.00
App.ActiveDocument.C1124.Angle=360.00 
App.ActiveDocument.C1124.Placement=Base.Placement(Base.Vector(48.064917,112.544187,-11.438224),Base.Rotation(0.148868,0.663238,0.000000,0.733454))
App.ActiveDocument.addObject("Part::Cylinder","C1125")
App.ActiveDocument.C1125.Radius=0.497626
App.ActiveDocument.C1125.Height=20.00
App.ActiveDocument.C1125.Angle=360.00 
App.ActiveDocument.C1125.Placement=Base.Placement(Base.Vector(47.400397,109.592202,-12.354778),Base.Rotation(0.224767,0.588204,0.000000,0.776850))
App.ActiveDocument.addObject("Part::Cylinder","C1126")
App.ActiveDocument.C1126.Radius=0.499389
App.ActiveDocument.C1126.Height=20.00
App.ActiveDocument.C1126.Angle=360.00 
App.ActiveDocument.C1126.Placement=Base.Placement(Base.Vector(46.280544,103.715288,-14.066518),Base.Rotation(0.136856,0.542216,0.000000,0.829019))
App.ActiveDocument.addObject("Part::Cylinder","C1127")
App.ActiveDocument.C1127.Radius=0.477195
App.ActiveDocument.C1127.Height=20.00
App.ActiveDocument.C1127.Angle=360.00 
App.ActiveDocument.C1127.Placement=Base.Placement(Base.Vector(51.857650,155.122166,-3.892522),Base.Rotation(0.005824,0.718170,0.000000,0.695844))
App.ActiveDocument.addObject("Part::Cylinder","C1128")
App.ActiveDocument.C1128.Radius=0.487027
App.ActiveDocument.C1128.Height=20.00
App.ActiveDocument.C1128.Angle=360.00 
App.ActiveDocument.C1128.Placement=Base.Placement(Base.Vector(51.667368,154.101402,-8.040103),Base.Rotation(0.007439,0.725000,0.000000,0.688708))
App.ActiveDocument.addObject("Part::Cylinder","C1129")
App.ActiveDocument.C1129.Radius=0.493887
App.ActiveDocument.C1129.Height=20.00
App.ActiveDocument.C1129.Angle=360.00 
App.ActiveDocument.C1129.Placement=Base.Placement(Base.Vector(51.461257,151.539399,-10.890484),Base.Rotation(0.012034,0.729577,0.000000,0.683793))
App.ActiveDocument.addObject("Part::Cylinder","C1130")
App.ActiveDocument.C1130.Radius=0.496130
App.ActiveDocument.C1130.Height=20.00
App.ActiveDocument.C1130.Angle=360.00 
App.ActiveDocument.C1130.Placement=Base.Placement(Base.Vector(51.267408,146.563728,-12.033821),Base.Rotation(0.031639,0.720751,0.000000,0.692471))
App.ActiveDocument.addObject("Part::Cylinder","C1131")
App.ActiveDocument.C1131.Radius=0.495955
App.ActiveDocument.C1131.Height=20.00
App.ActiveDocument.C1131.Angle=360.00 
App.ActiveDocument.C1131.Placement=Base.Placement(Base.Vector(51.003699,141.921814,-11.858132),Base.Rotation(0.053331,0.716969,0.000000,0.695062))
App.ActiveDocument.addObject("Part::Cylinder","C1132")
App.ActiveDocument.C1132.Radius=0.494519
App.ActiveDocument.C1132.Height=20.00
App.ActiveDocument.C1132.Angle=360.00 
App.ActiveDocument.C1132.Placement=Base.Placement(Base.Vector(50.696506,135.370403,-9.931379),Base.Rotation(-0.060155,0.751632,0.000000,0.656834))
App.ActiveDocument.addObject("Part::Cylinder","C1133")
App.ActiveDocument.C1133.Radius=0.490994
App.ActiveDocument.C1133.Height=20.00
App.ActiveDocument.C1133.Angle=360.00 
App.ActiveDocument.C1133.Placement=Base.Placement(Base.Vector(51.527782,131.183369,-8.946805),Base.Rotation(-0.038864,0.749830,0.000000,0.660488))
App.ActiveDocument.addObject("Part::Cylinder","C1134")
App.ActiveDocument.C1134.Radius=0.488377
App.ActiveDocument.C1134.Height=20.00
App.ActiveDocument.C1134.Angle=360.00 
App.ActiveDocument.C1134.Placement=Base.Placement(Base.Vector(51.365129,128.735942,-7.956582),Base.Rotation(0.101917,0.732942,0.000000,0.672613))
App.ActiveDocument.addObject("Part::Cylinder","C1135")
App.ActiveDocument.C1135.Radius=0.487005
App.ActiveDocument.C1135.Height=20.00
App.ActiveDocument.C1135.Angle=360.00 
App.ActiveDocument.C1135.Placement=Base.Placement(Base.Vector(50.701211,125.311431,-7.125508),Base.Rotation(0.161157,0.712838,0.000000,0.682561))
App.ActiveDocument.addObject("Part::Cylinder","C1136")
App.ActiveDocument.C1136.Radius=0.485605
App.ActiveDocument.C1136.Height=20.00
App.ActiveDocument.C1136.Angle=360.00 
App.ActiveDocument.C1136.Placement=Base.Placement(Base.Vector(49.701997,121.050718,-6.117872),Base.Rotation(0.176840,0.699989,0.000000,0.691913))
App.ActiveDocument.addObject("Part::Cylinder","C1137")
App.ActiveDocument.C1137.Radius=0.485639
App.ActiveDocument.C1137.Height=20.00
App.ActiveDocument.C1137.Angle=360.00 
App.ActiveDocument.C1137.Placement=Base.Placement(Base.Vector(48.520567,116.136932,-5.881741),Base.Rotation(0.148645,0.692012,0.000000,0.706416))
App.ActiveDocument.addObject("Part::Cylinder","C1138")
App.ActiveDocument.C1138.Radius=0.485846
App.ActiveDocument.C1138.Height=20.00
App.ActiveDocument.C1138.Angle=360.00 
App.ActiveDocument.C1138.Placement=Base.Placement(Base.Vector(48.049500,113.193048,-5.712057),Base.Rotation(0.257226,0.647381,0.000000,0.717448))
App.ActiveDocument.addObject("Part::Cylinder","C1139")
App.ActiveDocument.C1139.Radius=0.490302
App.ActiveDocument.C1139.Height=20.00
App.ActiveDocument.C1139.Angle=360.00 
App.ActiveDocument.C1139.Placement=Base.Placement(Base.Vector(49.968221,113.786438,-9.599963),Base.Rotation(0.482009,0.273710,0.000000,0.832316))
App.ActiveDocument.addObject("Part::Cylinder","C1140")
App.ActiveDocument.C1140.Radius=0.498453
App.ActiveDocument.C1140.Height=20.00
App.ActiveDocument.C1140.Angle=360.00 
App.ActiveDocument.C1140.Placement=Base.Placement(Base.Vector(49.094359,97.213544,0.649060),Base.Rotation(-0.872501,0.386681,0.000000,0.298696))
App.ActiveDocument.addObject("Part::Cylinder","C1141")
App.ActiveDocument.C1141.Radius=0.477186
App.ActiveDocument.C1141.Height=20.00
App.ActiveDocument.C1141.Angle=360.00 
App.ActiveDocument.C1141.Placement=Base.Placement(Base.Vector(51.693850,150.614416,-4.015723),Base.Rotation(0.050863,0.708022,0.000000,0.704356))
App.ActiveDocument.addObject("Part::Cylinder","C1142")
App.ActiveDocument.C1142.Radius=0.477927
App.ActiveDocument.C1142.Height=20.00
App.ActiveDocument.C1142.Angle=360.00 
App.ActiveDocument.C1142.Placement=Base.Placement(Base.Vector(51.282176,146.050230,-4.405142),Base.Rotation(0.070738,0.694960,0.000000,0.715560))
App.ActiveDocument.addObject("Part::Cylinder","C1143")
App.ActiveDocument.C1143.Radius=0.478512
App.ActiveDocument.C1143.Height=20.00
App.ActiveDocument.C1143.Angle=360.00 
App.ActiveDocument.C1143.Placement=Base.Placement(Base.Vector(50.802702,139.704456,-4.163253),Base.Rotation(-0.021705,0.707070,0.000000,0.706811))
App.ActiveDocument.addObject("Part::Cylinder","C1144")
App.ActiveDocument.C1144.Radius=0.477552
App.ActiveDocument.C1144.Height=20.00
App.ActiveDocument.C1144.Angle=360.00 
App.ActiveDocument.C1144.Placement=Base.Placement(Base.Vector(51.829118,133.166522,-3.297627),Base.Rotation(-0.134776,0.726955,0.000000,0.673329))
App.ActiveDocument.addObject("Part::Cylinder","C1145")
App.ActiveDocument.C1145.Radius=0.476804
App.ActiveDocument.C1145.Height=20.00
App.ActiveDocument.C1145.Angle=360.00 
App.ActiveDocument.C1145.Placement=Base.Placement(Base.Vector(51.966117,130.715382,-3.503014),Base.Rotation(0.051070,0.725255,0.000000,0.686583))
App.ActiveDocument.addObject("Part::Cylinder","C1146")
App.ActiveDocument.C1146.Radius=0.477552
App.ActiveDocument.C1146.Height=20.00
App.ActiveDocument.C1146.Angle=360.00 
App.ActiveDocument.C1146.Placement=Base.Placement(Base.Vector(51.413053,127.377506,-3.467001),Base.Rotation(0.144933,0.710275,0.000000,0.688843))
App.ActiveDocument.addObject("Part::Cylinder","C1147")
App.ActiveDocument.C1147.Radius=0.477790
App.ActiveDocument.C1147.Height=20.00
App.ActiveDocument.C1147.Angle=360.00 
App.ActiveDocument.C1147.Placement=Base.Placement(Base.Vector(50.472552,123.465833,-3.101289),Base.Rotation(0.178238,0.697122,0.000000,0.694443))
App.ActiveDocument.addObject("Part::Cylinder","C1148")
App.ActiveDocument.C1148.Radius=0.478415
App.ActiveDocument.C1148.Height=20.00
App.ActiveDocument.C1148.Angle=360.00 
App.ActiveDocument.C1148.Placement=Base.Placement(Base.Vector(49.275160,118.922978,-2.787818),Base.Rotation(0.181836,0.691421,0.000000,0.699194))
App.ActiveDocument.addObject("Part::Cylinder","C1149")
App.ActiveDocument.C1149.Radius=0.479153
App.ActiveDocument.C1149.Height=20.00
App.ActiveDocument.C1149.Angle=360.00 
App.ActiveDocument.C1149.Placement=Base.Placement(Base.Vector(48.149743,114.037386,-2.601617),Base.Rotation(0.154454,0.694401,0.000000,0.702816))
App.ActiveDocument.addObject("Part::Cylinder","C1150")
App.ActiveDocument.C1150.Radius=0.543293
App.ActiveDocument.C1150.Height=20.00
App.ActiveDocument.C1150.Angle=360.00 
App.ActiveDocument.C1150.Placement=Base.Placement(Base.Vector(-4.477365,206.602606,0.555626),Base.Rotation(-0.714105,-0.071713,0.000000,0.696356))
App.ActiveDocument.addObject("Part::Cylinder","C1151")
App.ActiveDocument.C1151.Radius=0.536836
App.ActiveDocument.C1151.Height=20.00
App.ActiveDocument.C1151.Angle=360.00 
App.ActiveDocument.C1151.Placement=Base.Placement(Base.Vector(-8.539595,206.017806,0.464406),Base.Rotation(-0.702804,-0.128819,0.000000,0.699623))
App.ActiveDocument.addObject("Part::Cylinder","C1152")
App.ActiveDocument.C1152.Radius=0.530308
App.ActiveDocument.C1152.Height=20.00
App.ActiveDocument.C1152.Angle=360.00 
App.ActiveDocument.C1152.Placement=Base.Placement(Base.Vector(-12.658533,205.083599,0.357359),Base.Rotation(-0.686259,-0.184999,0.000000,0.703438))
App.ActiveDocument.addObject("Part::Cylinder","C1153")
App.ActiveDocument.C1153.Radius=0.523963
App.ActiveDocument.C1153.Height=20.00
App.ActiveDocument.C1153.Angle=360.00 
App.ActiveDocument.C1153.Placement=Base.Placement(Base.Vector(-16.838303,203.822828,0.258089),Base.Rotation(-0.669951,-0.226667,0.000000,0.706957))
App.ActiveDocument.addObject("Part::Cylinder","C1154")
App.ActiveDocument.C1154.Radius=0.517783
App.ActiveDocument.C1154.Height=20.00
App.ActiveDocument.C1154.Angle=360.00 
App.ActiveDocument.C1154.Placement=Base.Placement(Base.Vector(-20.754241,202.310549,0.195668),Base.Rotation(-0.647822,-0.278241,0.000000,0.709161))
App.ActiveDocument.addObject("Part::Cylinder","C1155")
App.ActiveDocument.C1155.Radius=0.511878
App.ActiveDocument.C1155.Height=20.00
App.ActiveDocument.C1155.Angle=360.00 
App.ActiveDocument.C1155.Placement=Base.Placement(Base.Vector(-24.644754,200.484742,0.171380),Base.Rotation(-0.628641,-0.317312,0.000000,0.710016))
App.ActiveDocument.addObject("Part::Cylinder","C1156")
App.ActiveDocument.C1156.Radius=0.505905
App.ActiveDocument.C1156.Height=20.00
App.ActiveDocument.C1156.Angle=360.00 
App.ActiveDocument.C1156.Placement=Base.Placement(Base.Vector(-28.743531,198.293556,0.149592),Base.Rotation(-0.612838,-0.345277,0.000000,0.710783))
App.ActiveDocument.addObject("Part::Cylinder","C1157")
App.ActiveDocument.C1157.Radius=0.500255
App.ActiveDocument.C1157.Height=20.00
App.ActiveDocument.C1157.Angle=360.00 
App.ActiveDocument.C1157.Placement=Base.Placement(Base.Vector(-32.504947,196.051631,0.081752),Base.Rotation(-0.589728,-0.378966,0.000000,0.713165))
App.ActiveDocument.addObject("Part::Cylinder","C1158")
App.ActiveDocument.C1158.Radius=0.494750
App.ActiveDocument.C1158.Height=20.00
App.ActiveDocument.C1158.Angle=360.00 
App.ActiveDocument.C1158.Placement=Base.Placement(Base.Vector(-35.722282,193.755514,0.035212),Base.Rotation(-0.540927,-0.443246,0.000000,0.714795))
App.ActiveDocument.addObject("Part::Cylinder","C1159")
App.ActiveDocument.C1159.Radius=0.489891
App.ActiveDocument.C1159.Height=20.00
App.ActiveDocument.C1159.Angle=360.00 
App.ActiveDocument.C1159.Placement=Base.Placement(Base.Vector(-38.558674,191.175823,0.000556),Base.Rotation(-0.487015,-0.500152,0.000000,0.716006))
App.ActiveDocument.addObject("Part::Cylinder","C1160")
App.ActiveDocument.C1160.Radius=0.485535
App.ActiveDocument.C1160.Height=20.00
App.ActiveDocument.C1160.Angle=360.00 
App.ActiveDocument.C1160.Placement=Base.Placement(Base.Vector(-41.293844,188.165979,-0.029888),Base.Rotation(-0.443673,-0.537557,0.000000,0.717068))
App.ActiveDocument.addObject("Part::Cylinder","C1161")
App.ActiveDocument.C1161.Radius=0.481501
App.ActiveDocument.C1161.Height=20.00
App.ActiveDocument.C1161.Angle=360.00 
App.ActiveDocument.C1161.Placement=Base.Placement(Base.Vector(-43.842706,184.734273,-0.081007),Base.Rotation(-0.397324,-0.570430,0.000000,0.718848))
App.ActiveDocument.addObject("Part::Cylinder","C1162")
App.ActiveDocument.C1162.Radius=0.477954
App.ActiveDocument.C1162.Height=20.00
App.ActiveDocument.C1162.Angle=360.00 
App.ActiveDocument.C1162.Placement=Base.Placement(Base.Vector(-46.206008,181.124000,-0.111069),Base.Rotation(-0.363785,-0.591113,0.000000,0.719893))
App.ActiveDocument.addObject("Part::Cylinder","C1163")
App.ActiveDocument.C1163.Radius=0.474759
App.ActiveDocument.C1163.Height=20.00
App.ActiveDocument.C1163.Angle=360.00 
App.ActiveDocument.C1163.Placement=Base.Placement(Base.Vector(-48.094825,177.784789,-0.158588),Base.Rotation(-0.296399,-0.625720,0.000000,0.721541))
App.ActiveDocument.addObject("Part::Cylinder","C1164")
App.ActiveDocument.C1164.Radius=0.472260
App.ActiveDocument.C1164.Height=20.00
App.ActiveDocument.C1164.Angle=360.00 
App.ActiveDocument.C1164.Placement=Base.Placement(Base.Vector(-49.496121,174.385039,-0.187602),Base.Rotation(-0.211338,-0.658228,0.000000,0.722546))
App.ActiveDocument.addObject("Part::Cylinder","C1165")
App.ActiveDocument.C1165.Radius=0.470620
App.ActiveDocument.C1165.Height=20.00
App.ActiveDocument.C1165.Angle=360.00 
App.ActiveDocument.C1165.Placement=Base.Placement(Base.Vector(-50.464544,170.550335,-0.175293),Base.Rotation(-0.141634,-0.677114,0.000000,0.722120))
App.ActiveDocument.addObject("Part::Cylinder","C1166")
App.ActiveDocument.C1166.Radius=0.469478
App.ActiveDocument.C1166.Height=20.00
App.ActiveDocument.C1166.Angle=360.00 
App.ActiveDocument.C1166.Placement=Base.Placement(Base.Vector(-51.210470,166.097717,-0.037291),Base.Rotation(-0.099152,-0.689646,0.000000,0.717326))
App.ActiveDocument.addObject("Part::Cylinder","C1167")
App.ActiveDocument.C1167.Radius=0.468739
App.ActiveDocument.C1167.Height=20.00
App.ActiveDocument.C1167.Angle=360.00 
App.ActiveDocument.C1167.Placement=Base.Placement(Base.Vector(-51.696859,161.680264,0.200169),Base.Rotation(-0.059510,-0.702691,0.000000,0.709002))
App.ActiveDocument.addObject("Part::Cylinder","C1168")
App.ActiveDocument.C1168.Radius=0.468368
App.ActiveDocument.C1168.Height=20.00
App.ActiveDocument.C1168.Angle=360.00 
App.ActiveDocument.C1168.Placement=Base.Placement(Base.Vector(-51.942630,157.323364,0.354730),Base.Rotation(-0.011549,-0.710571,0.000000,0.703531))
App.ActiveDocument.addObject("Part::Cylinder","C1169")
App.ActiveDocument.C1169.Radius=0.468454
App.ActiveDocument.C1169.Height=20.00
App.ActiveDocument.C1169.Angle=360.00 
App.ActiveDocument.C1169.Placement=Base.Placement(Base.Vector(-51.892062,153.210804,0.271426),Base.Rotation(0.039713,-0.706613,0.000000,0.706485))
App.ActiveDocument.addObject("Part::Cylinder","C1170")
App.ActiveDocument.C1170.Radius=0.469055
App.ActiveDocument.C1170.Height=20.00
App.ActiveDocument.C1170.Angle=360.00 
App.ActiveDocument.C1170.Placement=Base.Placement(Base.Vector(-51.505760,148.859721,-0.032983),Base.Rotation(0.087247,-0.691409,0.000000,0.717176))
App.ActiveDocument.addObject("Part::Cylinder","C1171")
App.ActiveDocument.C1171.Radius=0.469902
App.ActiveDocument.C1171.Height=20.00
App.ActiveDocument.C1171.Angle=360.00 
App.ActiveDocument.C1171.Placement=Base.Placement(Base.Vector(-50.804606,143.265089,-0.080527),Base.Rotation(0.036534,-0.694224,0.000000,0.718831))
App.ActiveDocument.addObject("Part::Cylinder","C1172")
App.ActiveDocument.C1172.Radius=0.469247
App.ActiveDocument.C1172.Height=20.00
App.ActiveDocument.C1172.Angle=360.00 
App.ActiveDocument.C1172.Placement=Base.Placement(Base.Vector(-51.518989,135.681116,0.729207),Base.Rotation(-0.154256,-0.707088,0.000000,0.690096))
App.ActiveDocument.addObject("Part::Cylinder","C1173")
App.ActiveDocument.C1173.Radius=0.468059
App.ActiveDocument.C1173.Height=20.00
App.ActiveDocument.C1173.Angle=360.00 
App.ActiveDocument.C1173.Placement=Base.Placement(Base.Vector(-52.183401,132.501093,0.415996),Base.Rotation(-0.029111,-0.712222,0.000000,0.701350))
App.ActiveDocument.addObject("Part::Cylinder","C1174")
App.ActiveDocument.C1174.Radius=0.468618
App.ActiveDocument.C1174.Height=20.00
App.ActiveDocument.C1174.Angle=360.00 
App.ActiveDocument.C1174.Placement=Base.Placement(Base.Vector(-51.874497,129.300566,0.166886),Base.Rotation(0.109378,-0.695477,0.000000,0.710175))
App.ActiveDocument.addObject("Part::Cylinder","C1175")
App.ActiveDocument.C1175.Radius=0.469990
App.ActiveDocument.C1175.Height=20.00
App.ActiveDocument.C1175.Angle=360.00 
App.ActiveDocument.C1175.Placement=Base.Placement(Base.Vector(-51.004008,125.289927,0.200496),Base.Rotation(0.167335,-0.685078,0.000000,0.708990))
App.ActiveDocument.addObject("Part::Cylinder","C1176")
App.ActiveDocument.C1176.Radius=0.471668
App.ActiveDocument.C1176.Height=20.00
App.ActiveDocument.C1176.Angle=360.00 
App.ActiveDocument.C1176.Placement=Base.Placement(Base.Vector(-49.814427,120.821194,0.123562),Base.Rotation(0.186730,-0.677213,0.000000,0.711698))
App.ActiveDocument.addObject("Part::Cylinder","C1177")
App.ActiveDocument.C1177.Radius=0.473328
App.ActiveDocument.C1177.Height=20.00
App.ActiveDocument.C1177.Angle=360.00 
App.ActiveDocument.C1177.Placement=Base.Placement(Base.Vector(-48.449151,115.464548,0.026139),Base.Rotation(0.153488,-0.681950,0.000000,0.715112))
App.ActiveDocument.addObject("Part::Cylinder","C1178")
App.ActiveDocument.C1178.Radius=0.474828
App.ActiveDocument.C1178.Height=20.00
App.ActiveDocument.C1178.Angle=360.00 
App.ActiveDocument.C1178.Placement=Base.Placement(Base.Vector(-49.296828,114.736159,0.558053),Base.Rotation(0.451019,-0.558384,0.000000,0.696268))
App.ActiveDocument.addObject("Part::Cylinder","C1179")
App.ActiveDocument.C1179.Radius=0.553968
App.ActiveDocument.C1179.Height=20.00
App.ActiveDocument.C1179.Angle=360.00 
App.ActiveDocument.C1179.Placement=Base.Placement(Base.Vector(-4.411225,206.685098,5.151446),Base.Rotation(-0.704809,-0.075578,0.000000,0.705360))
App.ActiveDocument.addObject("Part::Cylinder","C1180")
App.ActiveDocument.C1180.Radius=0.547872
App.ActiveDocument.C1180.Height=20.00
App.ActiveDocument.C1180.Angle=360.00 
App.ActiveDocument.C1180.Placement=Base.Placement(Base.Vector(-8.670562,206.023976,5.364230),Base.Rotation(-0.691370,-0.136991,0.000000,0.709395))
App.ActiveDocument.addObject("Part::Cylinder","C1181")
App.ActiveDocument.C1181.Radius=0.541029
App.ActiveDocument.C1181.Height=20.00
App.ActiveDocument.C1181.Angle=360.00 
App.ActiveDocument.C1181.Placement=Base.Placement(Base.Vector(-12.753103,205.037640,5.100959),Base.Rotation(-0.674524,-0.192273,0.000000,0.712775))
App.ActiveDocument.addObject("Part::Cylinder","C1182")
App.ActiveDocument.C1182.Radius=0.534549
App.ActiveDocument.C1182.Height=20.00
App.ActiveDocument.C1182.Angle=360.00 
App.ActiveDocument.C1182.Placement=Base.Placement(Base.Vector(-16.994046,203.695481,4.952445),Base.Rotation(-0.659878,-0.228794,0.000000,0.715691))
App.ActiveDocument.addObject("Part::Cylinder","C1183")
App.ActiveDocument.C1183.Radius=0.528679
App.ActiveDocument.C1183.Height=20.00
App.ActiveDocument.C1183.Angle=360.00 
App.ActiveDocument.C1183.Placement=Base.Placement(Base.Vector(-20.988679,202.098902,5.078981),Base.Rotation(-0.638053,-0.279117,0.000000,0.717622))
App.ActiveDocument.addObject("Part::Cylinder","C1184")
App.ActiveDocument.C1184.Radius=0.522228
App.ActiveDocument.C1184.Height=20.00
App.ActiveDocument.C1184.Angle=360.00 
App.ActiveDocument.C1184.Placement=Base.Placement(Base.Vector(-25.070055,200.157807,4.948658),Base.Rotation(-0.619230,-0.318581,0.000000,0.717677))
App.ActiveDocument.addObject("Part::Cylinder","C1185")
App.ActiveDocument.C1185.Radius=0.516602
App.ActiveDocument.C1185.Height=20.00
App.ActiveDocument.C1185.Angle=360.00 
App.ActiveDocument.C1185.Placement=Base.Placement(Base.Vector(-29.092302,197.953413,5.043886),Base.Rotation(-0.601306,-0.348499,0.000000,0.719013))
App.ActiveDocument.addObject("Part::Cylinder","C1186")
App.ActiveDocument.C1186.Radius=0.510796
App.ActiveDocument.C1186.Height=20.00
App.ActiveDocument.C1186.Angle=360.00 
App.ActiveDocument.C1186.Placement=Base.Placement(Base.Vector(-32.768370,195.698188,4.892703),Base.Rotation(-0.574176,-0.386861,0.000000,0.721568))
App.ActiveDocument.addObject("Part::Cylinder","C1187")
App.ActiveDocument.C1187.Radius=0.505357
App.ActiveDocument.C1187.Height=20.00
App.ActiveDocument.C1187.Angle=360.00 
App.ActiveDocument.C1187.Placement=Base.Placement(Base.Vector(-35.974458,193.323163,4.830934),Base.Rotation(-0.529205,-0.444618,0.000000,0.722674))
App.ActiveDocument.addObject("Part::Cylinder","C1188")
App.ActiveDocument.C1188.Radius=0.500488
App.ActiveDocument.C1188.Height=20.00
App.ActiveDocument.C1188.Angle=360.00 
App.ActiveDocument.C1188.Placement=Base.Placement(Base.Vector(-38.818987,190.651907,4.814773),Base.Rotation(-0.477112,-0.500001,0.000000,0.722747))
App.ActiveDocument.addObject("Part::Cylinder","C1189")
App.ActiveDocument.C1189.Radius=0.496568
App.ActiveDocument.C1189.Height=20.00
App.ActiveDocument.C1189.Angle=360.00 
App.ActiveDocument.C1189.Placement=Base.Placement(Base.Vector(-41.518187,187.542438,4.994327),Base.Rotation(-0.430262,-0.539961,0.000000,0.723406))
App.ActiveDocument.addObject("Part::Cylinder","C1190")
App.ActiveDocument.C1190.Radius=0.492316
App.ActiveDocument.C1190.Height=20.00
App.ActiveDocument.C1190.Angle=360.00 
App.ActiveDocument.C1190.Placement=Base.Placement(Base.Vector(-44.116598,183.937326,4.870361),Base.Rotation(-0.388127,-0.569863,0.000000,0.724302))
App.ActiveDocument.addObject("Part::Cylinder","C1191")
App.ActiveDocument.C1191.Radius=0.488514
App.ActiveDocument.C1191.Height=20.00
App.ActiveDocument.C1191.Angle=360.00 
App.ActiveDocument.C1191.Placement=Base.Placement(Base.Vector(-46.456903,180.257808,4.704691),Base.Rotation(-0.343509,-0.594323,0.000000,0.727174))
App.ActiveDocument.addObject("Part::Cylinder","C1192")
App.ActiveDocument.C1192.Radius=0.485742
App.ActiveDocument.C1192.Height=20.00
App.ActiveDocument.C1192.Angle=360.00 
App.ActiveDocument.C1192.Placement=Base.Placement(Base.Vector(-48.170397,176.952121,4.693432),Base.Rotation(-0.270877,-0.626949,0.000000,0.730453))
App.ActiveDocument.addObject("Part::Cylinder","C1193")
App.ActiveDocument.C1193.Radius=0.483145
App.ActiveDocument.C1193.Height=20.00
App.ActiveDocument.C1193.Angle=360.00 
App.ActiveDocument.C1193.Placement=Base.Placement(Base.Vector(-49.382111,173.671246,4.422820),Base.Rotation(-0.191340,-0.652979,0.000000,0.732808))
App.ActiveDocument.addObject("Part::Cylinder","C1194")
App.ActiveDocument.C1194.Radius=0.481454
App.ActiveDocument.C1194.Height=20.00
App.ActiveDocument.C1194.Angle=360.00 
App.ActiveDocument.C1194.Placement=Base.Placement(Base.Vector(-50.394712,169.464759,4.465083),Base.Rotation(-0.136931,-0.669361,0.000000,0.730209))
App.ActiveDocument.addObject("Part::Cylinder","C1195")
App.ActiveDocument.C1195.Radius=0.480367
App.ActiveDocument.C1195.Height=20.00
App.ActiveDocument.C1195.Angle=360.00 
App.ActiveDocument.C1195.Placement=Base.Placement(Base.Vector(-51.165406,164.958166,4.655905),Base.Rotation(-0.100583,-0.681563,0.000000,0.724814))
App.ActiveDocument.addObject("Part::Cylinder","C1196")
App.ActiveDocument.C1196.Radius=0.479533
App.ActiveDocument.C1196.Height=20.00
App.ActiveDocument.C1196.Angle=360.00 
App.ActiveDocument.C1196.Placement=Base.Placement(Base.Vector(-51.705037,160.505226,4.836664),Base.Rotation(-0.065441,-0.692782,0.000000,0.718171))
App.ActiveDocument.addObject("Part::Cylinder","C1197")
App.ActiveDocument.C1197.Radius=0.479725
App.ActiveDocument.C1197.Height=20.00
App.ActiveDocument.C1197.Angle=360.00 
App.ActiveDocument.C1197.Placement=Base.Placement(Base.Vector(-51.938802,156.448472,5.233509),Base.Rotation(-0.005068,-0.700874,0.000000,0.713267))
App.ActiveDocument.addObject("Part::Cylinder","C1198")
App.ActiveDocument.C1198.Radius=0.479812
App.ActiveDocument.C1198.Height=20.00
App.ActiveDocument.C1198.Angle=360.00 
App.ActiveDocument.C1198.Placement=Base.Placement(Base.Vector(-51.791158,152.463050,5.086961),Base.Rotation(0.068891,-0.695083,0.000000,0.715621))
App.ActiveDocument.addObject("Part::Cylinder","C1199")
App.ActiveDocument.C1199.Radius=0.480843
App.ActiveDocument.C1199.Height=20.00
App.ActiveDocument.C1199.Angle=360.00 
App.ActiveDocument.C1199.Placement=Base.Placement(Base.Vector(-51.189597,147.991977,4.991784),Base.Rotation(0.105361,-0.684796,0.000000,0.721078))
App.ActiveDocument.addObject("Part::Cylinder","C1200")
App.ActiveDocument.C1200.Radius=0.481203
App.ActiveDocument.C1200.Height=20.00
App.ActiveDocument.C1200.Angle=360.00 
App.ActiveDocument.C1200.Placement=Base.Placement(Base.Vector(-50.721475,140.745815,5.229690),Base.Rotation(-0.060169,-0.701148,0.000000,0.710473))
App.ActiveDocument.addObject("Part::Cylinder","C1201")
App.ActiveDocument.C1201.Radius=0.479747
App.ActiveDocument.C1201.Height=20.00
App.ActiveDocument.C1201.Angle=360.00 
App.ActiveDocument.C1201.Placement=Base.Placement(Base.Vector(-51.905466,134.850487,5.287925),Base.Rotation(-0.129255,-0.694838,0.000000,0.707455))
App.ActiveDocument.addObject("Part::Cylinder","C1202")
App.ActiveDocument.C1202.Radius=0.479656
App.ActiveDocument.C1202.Height=20.00
App.ActiveDocument.C1202.Angle=360.00 
App.ActiveDocument.C1202.Placement=Base.Placement(Base.Vector(-52.019279,132.469348,4.681164),Base.Rotation(0.049926,-0.679565,0.000000,0.731915))
App.ActiveDocument.addObject("Part::Cylinder","C1203")
App.ActiveDocument.C1203.Radius=0.480707
App.ActiveDocument.C1203.Height=20.00
App.ActiveDocument.C1203.Angle=360.00 
App.ActiveDocument.C1203.Placement=Base.Placement(Base.Vector(-51.531743,128.574397,4.708789),Base.Rotation(0.120834,-0.667868,0.000000,0.734406))
App.ActiveDocument.addObject("Part::Cylinder","C1204")
App.ActiveDocument.C1204.Radius=0.481882
App.ActiveDocument.C1204.Height=20.00
App.ActiveDocument.C1204.Angle=360.00 
App.ActiveDocument.C1204.Placement=Base.Placement(Base.Vector(-50.640936,124.552047,4.569886),Base.Rotation(0.168460,-0.655917,0.000000,0.735795))
App.ActiveDocument.addObject("Part::Cylinder","C1205")
App.ActiveDocument.C1205.Radius=0.483519
App.ActiveDocument.C1205.Height=20.00
App.ActiveDocument.C1205.Angle=360.00 
App.ActiveDocument.C1205.Placement=Base.Placement(Base.Vector(-49.387620,120.181479,4.333056),Base.Rotation(0.194444,-0.642934,0.000000,0.740829))
App.ActiveDocument.addObject("Part::Cylinder","C1206")
App.ActiveDocument.C1206.Radius=0.485211
App.ActiveDocument.C1206.Height=20.00
App.ActiveDocument.C1206.Angle=360.00 
App.ActiveDocument.C1206.Placement=Base.Placement(Base.Vector(-48.022293,114.909660,3.808520),Base.Rotation(0.159982,-0.632621,0.000000,0.757758))
App.ActiveDocument.addObject("Part::Cylinder","C1207")
App.ActiveDocument.C1207.Radius=0.487347
App.ActiveDocument.C1207.Height=20.00
App.ActiveDocument.C1207.Angle=360.00 
App.ActiveDocument.C1207.Placement=Base.Placement(Base.Vector(-51.135291,116.290971,2.667556),Base.Rotation(0.555815,-0.275804,0.000000,0.784221))
App.ActiveDocument.addObject("Part::Cylinder","C1208")
App.ActiveDocument.C1208.Radius=0.565179
App.ActiveDocument.C1208.Height=20.00
App.ActiveDocument.C1208.Angle=360.00 
App.ActiveDocument.C1208.Placement=Base.Placement(Base.Vector(-4.310926,206.655818,9.985131),Base.Rotation(-0.694668,-0.082262,0.000000,0.714611))
App.ActiveDocument.addObject("Part::Cylinder","C1209")
App.ActiveDocument.C1209.Radius=0.558878
App.ActiveDocument.C1209.Height=20.00
App.ActiveDocument.C1209.Angle=360.00 
App.ActiveDocument.C1209.Placement=Base.Placement(Base.Vector(-8.411960,205.986148,9.998903),Base.Rotation(-0.682864,-0.137941,0.000000,0.717405))
App.ActiveDocument.addObject("Part::Cylinder","C1210")
App.ActiveDocument.C1210.Radius=0.552134
App.ActiveDocument.C1210.Height=20.00
App.ActiveDocument.C1210.Angle=360.00 
App.ActiveDocument.C1210.Placement=Base.Placement(Base.Vector(-12.457011,204.987833,9.800457),Base.Rotation(-0.665041,-0.196615,0.000000,0.720460))
App.ActiveDocument.addObject("Part::Cylinder","C1211")
App.ActiveDocument.C1211.Radius=0.546084
App.ActiveDocument.C1211.Height=20.00
App.ActiveDocument.C1211.Angle=360.00 
App.ActiveDocument.C1211.Placement=Base.Placement(Base.Vector(-16.778758,203.575217,9.869245),Base.Rotation(-0.650468,-0.230652,0.000000,0.723665))
App.ActiveDocument.addObject("Part::Cylinder","C1212")
App.ActiveDocument.C1212.Radius=0.540358
App.ActiveDocument.C1212.Height=20.00
App.ActiveDocument.C1212.Angle=360.00 
App.ActiveDocument.C1212.Placement=Base.Placement(Base.Vector(-20.703552,202.006383,9.989295),Base.Rotation(-0.632032,-0.274459,0.000000,0.724712))
App.ActiveDocument.addObject("Part::Cylinder","C1213")
App.ActiveDocument.C1213.Radius=0.533717
App.ActiveDocument.C1213.Height=20.00
App.ActiveDocument.C1213.Angle=360.00 
App.ActiveDocument.C1213.Placement=Base.Placement(Base.Vector(-24.649534,200.163084,9.710223),Base.Rotation(-0.615445,-0.312414,0.000000,0.723620))
App.ActiveDocument.addObject("Part::Cylinder","C1214")
App.ActiveDocument.C1214.Radius=0.528462
App.ActiveDocument.C1214.Height=20.00
App.ActiveDocument.C1214.Angle=360.00 
App.ActiveDocument.C1214.Placement=Base.Placement(Base.Vector(-28.564809,198.022386,9.947919),Base.Rotation(-0.595989,-0.345857,0.000000,0.724693))
App.ActiveDocument.addObject("Part::Cylinder","C1215")
App.ActiveDocument.C1215.Radius=0.522315
App.ActiveDocument.C1215.Height=20.00
App.ActiveDocument.C1215.Angle=360.00 
App.ActiveDocument.C1215.Placement=Base.Placement(Base.Vector(-32.296064,195.729072,9.667266),Base.Rotation(-0.569874,-0.382749,0.000000,0.727150))
App.ActiveDocument.addObject("Part::Cylinder","C1216")
App.ActiveDocument.C1216.Radius=0.517115
App.ActiveDocument.C1216.Height=20.00
App.ActiveDocument.C1216.Angle=360.00 
App.ActiveDocument.C1216.Placement=Base.Placement(Base.Vector(-35.538114,193.353108,9.711936),Base.Rotation(-0.527979,-0.437090,0.000000,0.728142))
App.ActiveDocument.addObject("Part::Cylinder","C1217")
App.ActiveDocument.C1217.Radius=0.511951
App.ActiveDocument.C1217.Height=20.00
App.ActiveDocument.C1217.Angle=360.00 
App.ActiveDocument.C1217.Placement=Base.Placement(Base.Vector(-38.415234,190.707847,9.556323),Base.Rotation(-0.481315,-0.488373,0.000000,0.727893))
App.ActiveDocument.addObject("Part::Cylinder","C1218")
App.ActiveDocument.C1218.Radius=0.508088
App.ActiveDocument.C1218.Height=20.00
App.ActiveDocument.C1218.Angle=360.00 
App.ActiveDocument.C1218.Placement=Base.Placement(Base.Vector(-41.020864,187.757930,9.740490),Base.Rotation(-0.432685,-0.531396,0.000000,0.728287))
App.ActiveDocument.addObject("Part::Cylinder","C1219")
App.ActiveDocument.C1219.Radius=0.503794
App.ActiveDocument.C1219.Height=20.00
App.ActiveDocument.C1219.Angle=360.00 
App.ActiveDocument.C1219.Placement=Base.Placement(Base.Vector(-43.473261,184.398578,9.521374),Base.Rotation(-0.386062,-0.564162,0.000000,0.729847))
App.ActiveDocument.addObject("Part::Cylinder","C1220")
App.ActiveDocument.C1220.Radius=0.500111
App.ActiveDocument.C1220.Height=20.00
App.ActiveDocument.C1220.Angle=360.00 
App.ActiveDocument.C1220.Placement=Base.Placement(Base.Vector(-45.787146,180.784443,9.377894),Base.Rotation(-0.343280,-0.587313,0.000000,0.732954))
App.ActiveDocument.addObject("Part::Cylinder","C1221")
App.ActiveDocument.C1221.Radius=0.497230
App.ActiveDocument.C1221.Height=20.00
App.ActiveDocument.C1221.Angle=360.00 
App.ActiveDocument.C1221.Placement=Base.Placement(Base.Vector(-47.568708,177.414073,9.312636),Base.Rotation(-0.277919,-0.616269,0.000000,0.736867))
App.ActiveDocument.addObject("Part::Cylinder","C1222")
App.ActiveDocument.C1222.Radius=0.494555
App.ActiveDocument.C1222.Height=20.00
App.ActiveDocument.C1222.Angle=360.00 
App.ActiveDocument.C1222.Placement=Base.Placement(Base.Vector(-48.861360,174.022095,9.079646),Base.Rotation(-0.196994,-0.644273,0.000000,0.738990))
App.ActiveDocument.addObject("Part::Cylinder","C1223")
App.ActiveDocument.C1223.Radius=0.492934
App.ActiveDocument.C1223.Height=20.00
App.ActiveDocument.C1223.Angle=360.00 
App.ActiveDocument.C1223.Placement=Base.Placement(Base.Vector(-49.928879,169.871552,9.132706),Base.Rotation(-0.146785,-0.658536,0.000000,0.738096))
App.ActiveDocument.addObject("Part::Cylinder","C1224")
App.ActiveDocument.C1224.Radius=0.491323
App.ActiveDocument.C1224.Height=20.00
App.ActiveDocument.C1224.Angle=360.00 
App.ActiveDocument.C1224.Placement=Base.Placement(Base.Vector(-50.794292,165.421738,9.122100),Base.Rotation(-0.114899,-0.669905,0.000000,0.733503))
App.ActiveDocument.addObject("Part::Cylinder","C1225")
App.ActiveDocument.C1225.Radius=0.490833
App.ActiveDocument.C1225.Height=20.00
App.ActiveDocument.C1225.Angle=360.00 
App.ActiveDocument.C1225.Placement=Base.Placement(Base.Vector(-51.450287,160.850348,9.519062),Base.Rotation(-0.082486,-0.681100,0.000000,0.727529))
App.ActiveDocument.addObject("Part::Cylinder","C1226")
App.ActiveDocument.C1226.Radius=0.490520
App.ActiveDocument.C1226.Height=20.00
App.ActiveDocument.C1226.Angle=360.00 
App.ActiveDocument.C1226.Placement=Base.Placement(Base.Vector(-51.788343,156.926238,9.777157),Base.Rotation(-0.020724,-0.691245,0.000000,0.722324))
App.ActiveDocument.addObject("Part::Cylinder","C1227")
App.ActiveDocument.C1227.Radius=0.490443
App.ActiveDocument.C1227.Height=20.00
App.ActiveDocument.C1227.Angle=360.00 
App.ActiveDocument.C1227.Placement=Base.Placement(Base.Vector(-51.711801,153.149654,9.680816),Base.Rotation(0.068782,-0.688536,0.000000,0.721933))
App.ActiveDocument.addObject("Part::Cylinder","C1228")
App.ActiveDocument.C1228.Radius=0.491924
App.ActiveDocument.C1228.Height=20.00
App.ActiveDocument.C1228.Angle=360.00 
App.ActiveDocument.C1228.Placement=Base.Placement(Base.Vector(-51.074405,148.576594,9.929105),Base.Rotation(0.100914,-0.684361,0.000000,0.722126))
App.ActiveDocument.addObject("Part::Cylinder","C1229")
App.ActiveDocument.C1229.Radius=0.492480
App.ActiveDocument.C1229.Height=20.00
App.ActiveDocument.C1229.Angle=360.00 
App.ActiveDocument.C1229.Placement=Base.Placement(Base.Vector(-50.552611,141.702235,10.018132),Base.Rotation(-0.036049,-0.694164,0.000000,0.718914))
App.ActiveDocument.addObject("Part::Cylinder","C1230")
App.ActiveDocument.C1230.Radius=0.490952
App.ActiveDocument.C1230.Height=20.00
App.ActiveDocument.C1230.Angle=360.00 
App.ActiveDocument.C1230.Placement=Base.Placement(Base.Vector(-51.635482,135.780829,9.837363),Base.Rotation(-0.104012,-0.684463,0.000000,0.721590))
App.ActiveDocument.addObject("Part::Cylinder","C1231")
App.ActiveDocument.C1231.Radius=0.492089
App.ActiveDocument.C1231.Height=20.00
App.ActiveDocument.C1231.Angle=360.00 
App.ActiveDocument.C1231.Placement=Base.Placement(Base.Vector(-51.598708,133.207536,10.296710),Base.Rotation(0.051609,-0.687337,0.000000,0.724503))
App.ActiveDocument.addObject("Part::Cylinder","C1232")
App.ActiveDocument.C1232.Radius=0.492587
App.ActiveDocument.C1232.Height=20.00
App.ActiveDocument.C1232.Angle=360.00 
App.ActiveDocument.C1232.Placement=Base.Placement(Base.Vector(-51.180677,129.362284,9.712291),Base.Rotation(0.112334,-0.662549,0.000000,0.740547))
App.ActiveDocument.addObject("Part::Cylinder","C1233")
App.ActiveDocument.C1233.Radius=0.493296
App.ActiveDocument.C1233.Height=20.00
App.ActiveDocument.C1233.Angle=360.00 
App.ActiveDocument.C1233.Placement=Base.Placement(Base.Vector(-50.377857,125.468313,9.245117),Base.Rotation(0.166772,-0.643781,0.000000,0.746815))
App.ActiveDocument.addObject("Part::Cylinder","C1234")
App.ActiveDocument.C1234.Radius=0.494801
App.ActiveDocument.C1234.Height=20.00
App.ActiveDocument.C1234.Angle=360.00 
App.ActiveDocument.C1234.Placement=Base.Placement(Base.Vector(-49.130613,121.240788,8.789340),Base.Rotation(0.205946,-0.622107,0.000000,0.755361))
App.ActiveDocument.addObject("Part::Cylinder","C1235")
App.ActiveDocument.C1235.Radius=0.496900
App.ActiveDocument.C1235.Height=20.00
App.ActiveDocument.C1235.Angle=360.00 
App.ActiveDocument.C1235.Placement=Base.Placement(Base.Vector(-47.585218,116.316764,8.546285),Base.Rotation(0.180679,-0.617889,0.000000,0.765224))
App.ActiveDocument.addObject("Part::Cylinder","C1236")
App.ActiveDocument.C1236.Radius=0.499324
App.ActiveDocument.C1236.Height=20.00
App.ActiveDocument.C1236.Angle=360.00 
App.ActiveDocument.C1236.Placement=Base.Placement(Base.Vector(-47.057467,114.169817,7.183806),Base.Rotation(0.325838,-0.495485,0.000000,0.805186))
App.ActiveDocument.addObject("Part::Cylinder","C1237")
App.ActiveDocument.C1237.Radius=0.576323
App.ActiveDocument.C1237.Height=20.00
App.ActiveDocument.C1237.Angle=360.00 
App.ActiveDocument.C1237.Placement=Base.Placement(Base.Vector(-4.183429,206.510683,14.765742),Base.Rotation(-0.686020,-0.084571,0.000000,0.722651))
App.ActiveDocument.addObject("Part::Cylinder","C1238")
App.ActiveDocument.C1238.Radius=0.569999
App.ActiveDocument.C1238.Height=20.00
App.ActiveDocument.C1238.Angle=360.00 
App.ActiveDocument.C1238.Placement=Base.Placement(Base.Vector(-8.307889,205.809494,14.820723),Base.Rotation(-0.673758,-0.142752,0.000000,0.725033))
App.ActiveDocument.addObject("Part::Cylinder","C1239")
App.ActiveDocument.C1239.Radius=0.563361
App.ActiveDocument.C1239.Height=20.00
App.ActiveDocument.C1239.Angle=360.00 
App.ActiveDocument.C1239.Placement=Base.Placement(Base.Vector(-12.260671,204.801015,14.629469),Base.Rotation(-0.655985,-0.200906,0.000000,0.727544))
App.ActiveDocument.addObject("Part::Cylinder","C1240")
App.ActiveDocument.C1240.Radius=0.557308
App.ActiveDocument.C1240.Height=20.00
App.ActiveDocument.C1240.Angle=360.00 
App.ActiveDocument.C1240.Placement=Base.Placement(Base.Vector(-16.534445,203.370730,14.644142),Base.Rotation(-0.643391,-0.230143,0.000000,0.730125))
App.ActiveDocument.addObject("Part::Cylinder","C1241")
App.ActiveDocument.C1241.Radius=0.551480
App.ActiveDocument.C1241.Height=20.00
App.ActiveDocument.C1241.Angle=360.00 
App.ActiveDocument.C1241.Placement=Base.Placement(Base.Vector(-20.582445,201.748921,14.816143),Base.Rotation(-0.626135,-0.273440,0.000000,0.730196))
App.ActiveDocument.addObject("Part::Cylinder","C1242")
App.ActiveDocument.C1242.Radius=0.544173
App.ActiveDocument.C1242.Height=20.00
App.ActiveDocument.C1242.Angle=360.00 
App.ActiveDocument.C1242.Placement=Base.Placement(Base.Vector(-24.667782,199.867375,14.320727),Base.Rotation(-0.610338,-0.310405,0.000000,0.728791))
App.ActiveDocument.addObject("Part::Cylinder","C1243")
App.ActiveDocument.C1243.Radius=0.539646
App.ActiveDocument.C1243.Height=20.00
App.ActiveDocument.C1243.Angle=360.00 
App.ActiveDocument.C1243.Placement=Base.Placement(Base.Vector(-28.623661,197.649833,14.959636),Base.Rotation(-0.587487,-0.349241,0.000000,0.729993))
App.ActiveDocument.addObject("Part::Cylinder","C1244")
App.ActiveDocument.C1244.Radius=0.533611
App.ActiveDocument.C1244.Height=20.00
App.ActiveDocument.C1244.Angle=360.00 
App.ActiveDocument.C1244.Placement=Base.Placement(Base.Vector(-32.267398,195.361249,14.692799),Base.Rotation(-0.561231,-0.386347,0.000000,0.731953))
App.ActiveDocument.addObject("Part::Cylinder","C1245")
App.ActiveDocument.C1245.Radius=0.528445
App.ActiveDocument.C1245.Height=20.00
App.ActiveDocument.C1245.Angle=360.00 
App.ActiveDocument.C1245.Placement=Base.Placement(Base.Vector(-35.510656,192.938711,14.716801),Base.Rotation(-0.522650,-0.435722,0.000000,0.732791))
App.ActiveDocument.addObject("Part::Cylinder","C1246")
App.ActiveDocument.C1246.Radius=0.522674
App.ActiveDocument.C1246.Height=20.00
App.ActiveDocument.C1246.Angle=360.00 
App.ActiveDocument.C1246.Placement=Base.Placement(Base.Vector(-38.420587,190.252370,14.337320),Base.Rotation(-0.474971,-0.488594,0.000000,0.731901))
App.ActiveDocument.addObject("Part::Cylinder","C1247")
App.ActiveDocument.C1247.Radius=0.518892
App.ActiveDocument.C1247.Height=20.00
App.ActiveDocument.C1247.Angle=360.00 
App.ActiveDocument.C1247.Placement=Base.Placement(Base.Vector(-40.956273,187.313177,14.546190),Base.Rotation(-0.420963,-0.535109,0.000000,0.732426))
App.ActiveDocument.addObject("Part::Cylinder","C1248")
App.ActiveDocument.C1248.Radius=0.515033
App.ActiveDocument.C1248.Height=20.00
App.ActiveDocument.C1248.Angle=360.00 
App.ActiveDocument.C1248.Placement=Base.Placement(Base.Vector(-43.500344,183.702990,14.557091),Base.Rotation(-0.371724,-0.567330,0.000000,0.734818))
App.ActiveDocument.addObject("Part::Cylinder","C1249")
App.ActiveDocument.C1249.Radius=0.511211
App.ActiveDocument.C1249.Height=20.00
App.ActiveDocument.C1249.Angle=360.00 
App.ActiveDocument.C1249.Placement=Base.Placement(Base.Vector(-45.711598,180.104747,14.257364),Base.Rotation(-0.326652,-0.589324,0.000000,0.738915))
App.ActiveDocument.addObject("Part::Cylinder","C1250")
App.ActiveDocument.C1250.Radius=0.508159
App.ActiveDocument.C1250.Height=20.00
App.ActiveDocument.C1250.Angle=360.00 
App.ActiveDocument.C1250.Placement=Base.Placement(Base.Vector(-47.437584,176.554771,14.082966),Base.Rotation(-0.249930,-0.620193,0.000000,0.743569))
App.ActiveDocument.addObject("Part::Cylinder","C1251")
App.ActiveDocument.C1251.Radius=0.505795
App.ActiveDocument.C1251.Height=20.00
App.ActiveDocument.C1251.Angle=360.00 
App.ActiveDocument.C1251.Placement=Base.Placement(Base.Vector(-48.669088,172.928938,13.935667),Base.Rotation(-0.181033,-0.642740,0.000000,0.744388))
App.ActiveDocument.addObject("Part::Cylinder","C1252")
App.ActiveDocument.C1252.Radius=0.504308
App.ActiveDocument.C1252.Height=20.00
App.ActiveDocument.C1252.Angle=360.00 
App.ActiveDocument.C1252.Placement=Base.Placement(Base.Vector(-49.716143,168.637057,14.050161),Base.Rotation(-0.144830,-0.654592,0.000000,0.741980))
App.ActiveDocument.addObject("Part::Cylinder","C1253")
App.ActiveDocument.C1253.Radius=0.503064
App.ActiveDocument.C1253.Height=20.00
App.ActiveDocument.C1253.Angle=360.00 
App.ActiveDocument.C1253.Placement=Base.Placement(Base.Vector(-50.582876,164.192670,14.179884),Base.Rotation(-0.118869,-0.664248,0.000000,0.738000))
App.ActiveDocument.addObject("Part::Cylinder","C1254")
App.ActiveDocument.C1254.Radius=0.502134
App.ActiveDocument.C1254.Height=20.00
App.ActiveDocument.C1254.Angle=360.00 
App.ActiveDocument.C1254.Placement=Base.Placement(Base.Vector(-51.273872,159.589302,14.322598),Base.Rotation(-0.074104,-0.673930,0.000000,0.735069))
App.ActiveDocument.addObject("Part::Cylinder","C1255")
App.ActiveDocument.C1255.Radius=0.501622
App.ActiveDocument.C1255.Height=20.00
App.ActiveDocument.C1255.Angle=360.00 
App.ActiveDocument.C1255.Placement=Base.Placement(Base.Vector(-51.550814,155.797842,14.249814),Base.Rotation(0.006864,-0.676462,0.000000,0.736446))
App.ActiveDocument.addObject("Part::Cylinder","C1256")
App.ActiveDocument.C1256.Radius=0.502165
App.ActiveDocument.C1256.Height=20.00
App.ActiveDocument.C1256.Angle=360.00 
App.ActiveDocument.C1256.Placement=Base.Placement(Base.Vector(-51.306957,151.999327,14.301151),Base.Rotation(0.083830,-0.671197,0.000000,0.736524))
App.ActiveDocument.addObject("Part::Cylinder","C1257")
App.ActiveDocument.C1257.Radius=0.503790
App.ActiveDocument.C1257.Height=20.00
App.ActiveDocument.C1257.Angle=360.00 
App.ActiveDocument.C1257.Placement=Base.Placement(Base.Vector(-50.572519,147.021497,14.438273),Base.Rotation(0.085568,-0.665468,0.000000,0.741505))
App.ActiveDocument.addObject("Part::Cylinder","C1258")
App.ActiveDocument.C1258.Radius=0.503536
App.ActiveDocument.C1258.Height=20.00
App.ActiveDocument.C1258.Angle=360.00 
App.ActiveDocument.C1258.Placement=Base.Placement(Base.Vector(-50.638527,139.125478,14.255337),Base.Rotation(-0.113520,-0.658802,0.000000,0.743702))
App.ActiveDocument.addObject("Part::Cylinder","C1259")
App.ActiveDocument.C1259.Radius=0.502609
App.ActiveDocument.C1259.Height=20.00
App.ActiveDocument.C1259.Angle=360.00 
App.ActiveDocument.C1259.Placement=Base.Placement(Base.Vector(-51.409150,136.080425,14.332630),Base.Rotation(0.011692,-0.666568,0.000000,0.745352))
App.ActiveDocument.addObject("Part::Cylinder","C1260")
App.ActiveDocument.C1260.Radius=0.504286
App.ActiveDocument.C1260.Height=20.00
App.ActiveDocument.C1260.Angle=360.00 
App.ActiveDocument.C1260.Placement=Base.Placement(Base.Vector(-51.069061,132.125353,14.898662),Base.Rotation(0.075024,-0.664083,0.000000,0.743885))
App.ActiveDocument.addObject("Part::Cylinder","C1261")
App.ActiveDocument.C1261.Radius=0.504459
App.ActiveDocument.C1261.Height=20.00
App.ActiveDocument.C1261.Angle=360.00 
App.ActiveDocument.C1261.Placement=Base.Placement(Base.Vector(-50.509279,128.363224,14.421788),Base.Rotation(0.141301,-0.648912,0.000000,0.747628))
App.ActiveDocument.addObject("Part::Cylinder","C1262")
App.ActiveDocument.C1262.Radius=0.505287
App.ActiveDocument.C1262.Height=20.00
App.ActiveDocument.C1262.Angle=360.00 
App.ActiveDocument.C1262.Placement=Base.Placement(Base.Vector(-49.527041,124.532505,13.967906),Base.Rotation(0.184458,-0.633004,0.000000,0.751851))
App.ActiveDocument.addObject("Part::Cylinder","C1263")
App.ActiveDocument.C1263.Radius=0.506660
App.ActiveDocument.C1263.Height=20.00
App.ActiveDocument.C1263.Angle=360.00 
App.ActiveDocument.C1263.Placement=Base.Placement(Base.Vector(-48.107788,120.187372,13.472090),Base.Rotation(0.208138,-0.618515,0.000000,0.757705))
App.ActiveDocument.addObject("Part::Cylinder","C1264")
App.ActiveDocument.C1264.Radius=0.509731
App.ActiveDocument.C1264.Height=20.00
App.ActiveDocument.C1264.Angle=360.00 
App.ActiveDocument.C1264.Placement=Base.Placement(Base.Vector(-46.496044,115.493587,13.945951),Base.Rotation(0.201727,-0.621761,0.000000,0.756782))
App.ActiveDocument.addObject("Part::Cylinder","C1265")
App.ActiveDocument.C1265.Radius=0.511409
App.ActiveDocument.C1265.Height=20.00
App.ActiveDocument.C1265.Angle=360.00 
App.ActiveDocument.C1265.Placement=Base.Placement(Base.Vector(-51.872385,119.051488,10.041195),Base.Rotation(0.561666,-0.000037,0.000000,0.827364))
App.ActiveDocument.addObject("Part::Cylinder","C1266")
App.ActiveDocument.C1266.Radius=0.587168
App.ActiveDocument.C1266.Height=20.00
App.ActiveDocument.C1266.Angle=360.00 
App.ActiveDocument.C1266.Placement=Base.Placement(Base.Vector(-4.012342,206.271261,19.372172),Base.Rotation(-0.676973,-0.086468,0.000000,0.730911))
App.ActiveDocument.addObject("Part::Cylinder","C1267")
App.ActiveDocument.C1267.Radius=0.581530
App.ActiveDocument.C1267.Height=20.00
App.ActiveDocument.C1267.Angle=360.00 
App.ActiveDocument.C1267.Placement=Base.Placement(Base.Vector(-8.060319,205.554665,19.674564),Base.Rotation(-0.665664,-0.140709,0.000000,0.732866))
App.ActiveDocument.addObject("Part::Cylinder","C1268")
App.ActiveDocument.C1268.Radius=0.574520
App.ActiveDocument.C1268.Height=20.00
App.ActiveDocument.C1268.Angle=360.00 
App.ActiveDocument.C1268.Placement=Base.Placement(Base.Vector(-12.125075,204.495075,19.461089),Base.Rotation(-0.646789,-0.204960,0.000000,0.734613))
App.ActiveDocument.addObject("Part::Cylinder","C1269")
App.ActiveDocument.C1269.Radius=0.568190
App.ActiveDocument.C1269.Height=20.00
App.ActiveDocument.C1269.Angle=360.00 
App.ActiveDocument.C1269.Placement=Base.Placement(Base.Vector(-16.581168,202.972917,19.453252),Base.Rotation(-0.636042,-0.230705,0.000000,0.736360))
App.ActiveDocument.addObject("Part::Cylinder","C1270")
App.ActiveDocument.C1270.Radius=0.562563
App.ActiveDocument.C1270.Height=20.00
App.ActiveDocument.C1270.Angle=360.00 
App.ActiveDocument.C1270.Placement=Base.Placement(Base.Vector(-20.857971,201.213985,19.839895),Base.Rotation(-0.619207,-0.272284,0.000000,0.736508))
App.ActiveDocument.addObject("Part::Cylinder","C1271")
App.ActiveDocument.C1271.Radius=0.554899
App.ActiveDocument.C1271.Height=20.00
App.ActiveDocument.C1271.Angle=360.00 
App.ActiveDocument.C1271.Placement=Base.Placement(Base.Vector(-24.887198,199.376360,19.171079),Base.Rotation(-0.603865,-0.309630,0.000000,0.734491))
App.ActiveDocument.addObject("Part::Cylinder","C1272")
App.ActiveDocument.C1272.Radius=0.550550
App.ActiveDocument.C1272.Height=20.00
App.ActiveDocument.C1272.Angle=360.00 
App.ActiveDocument.C1272.Placement=Base.Placement(Base.Vector(-28.667931,197.210200,19.822450),Base.Rotation(-0.579599,-0.351280,0.000000,0.735301))
App.ActiveDocument.addObject("Part::Cylinder","C1273")
App.ActiveDocument.C1273.Radius=0.544714
App.ActiveDocument.C1273.Height=20.00
App.ActiveDocument.C1273.Angle=360.00 
App.ActiveDocument.C1273.Placement=Base.Placement(Base.Vector(-32.345894,194.837742,19.659801),Base.Rotation(-0.554494,-0.386550,0.000000,0.736963))
App.ActiveDocument.addObject("Part::Cylinder","C1274")
App.ActiveDocument.C1274.Radius=0.539235
App.ActiveDocument.C1274.Height=20.00
App.ActiveDocument.C1274.Angle=360.00 
App.ActiveDocument.C1274.Placement=Base.Placement(Base.Vector(-35.530298,192.406227,19.565813),Base.Rotation(-0.512003,-0.440817,0.000000,0.737247))
App.ActiveDocument.addObject("Part::Cylinder","C1275")
App.ActiveDocument.C1275.Radius=0.533779
App.ActiveDocument.C1275.Height=20.00
App.ActiveDocument.C1275.Angle=360.00 
App.ActiveDocument.C1275.Placement=Base.Placement(Base.Vector(-38.402778,189.716301,19.252932),Base.Rotation(-0.466904,-0.488804,0.000000,0.736934))
App.ActiveDocument.addObject("Part::Cylinder","C1276")
App.ActiveDocument.C1276.Radius=0.530064
App.ActiveDocument.C1276.Height=20.00
App.ActiveDocument.C1276.Angle=360.00 
App.ActiveDocument.C1276.Placement=Base.Placement(Base.Vector(-40.824653,186.835266,19.426321),Base.Rotation(-0.408247,-0.537104,0.000000,0.738142))
App.ActiveDocument.addObject("Part::Cylinder","C1277")
App.ActiveDocument.C1277.Radius=0.526140
App.ActiveDocument.C1277.Height=20.00
App.ActiveDocument.C1277.Angle=360.00 
App.ActiveDocument.C1277.Placement=Base.Placement(Base.Vector(-43.219750,183.359638,19.290315),Base.Rotation(-0.359202,-0.567306,0.000000,0.741039))
App.ActiveDocument.addObject("Part::Cylinder","C1278")
App.ActiveDocument.C1278.Radius=0.522911
App.ActiveDocument.C1278.Height=20.00
App.ActiveDocument.C1278.Angle=360.00 
App.ActiveDocument.C1278.Placement=Base.Placement(Base.Vector(-45.250397,179.911136,19.132960),Base.Rotation(-0.309895,-0.589447,0.000000,0.746001))
App.ActiveDocument.addObject("Part::Cylinder","C1279")
App.ActiveDocument.C1279.Radius=0.519536
App.ActiveDocument.C1279.Height=20.00
App.ActiveDocument.C1279.Angle=360.00 
App.ActiveDocument.C1279.Placement=Base.Placement(Base.Vector(-46.895376,176.447535,18.742042),Base.Rotation(-0.241693,-0.615861,0.000000,0.749866))
App.ActiveDocument.addObject("Part::Cylinder","C1280")
App.ActiveDocument.C1280.Radius=0.517306
App.ActiveDocument.C1280.Height=20.00
App.ActiveDocument.C1280.Angle=360.00 
App.ActiveDocument.C1280.Placement=Base.Placement(Base.Vector(-48.154887,172.721532,18.649918),Base.Rotation(-0.183736,-0.634967,0.000000,0.750371))
App.ActiveDocument.addObject("Part::Cylinder","C1281")
App.ActiveDocument.C1281.Radius=0.516152
App.ActiveDocument.C1281.Height=20.00
App.ActiveDocument.C1281.Angle=360.00 
App.ActiveDocument.C1281.Placement=Base.Placement(Base.Vector(-49.179783,168.596448,18.927664),Base.Rotation(-0.150949,-0.647341,0.000000,0.747103))
App.ActiveDocument.addObject("Part::Cylinder","C1282")
App.ActiveDocument.C1282.Radius=0.514569
App.ActiveDocument.C1282.Height=20.00
App.ActiveDocument.C1282.Angle=360.00 
App.ActiveDocument.C1282.Placement=Base.Placement(Base.Vector(-50.133417,164.089188,19.005058),Base.Rotation(-0.124553,-0.658992,0.000000,0.741766))
App.ActiveDocument.addObject("Part::Cylinder","C1283")
App.ActiveDocument.C1283.Radius=0.513875
App.ActiveDocument.C1283.Height=20.00
App.ActiveDocument.C1283.Angle=360.00 
App.ActiveDocument.C1283.Placement=Base.Placement(Base.Vector(-50.795171,159.961546,19.151032),Base.Rotation(-0.075946,-0.666233,0.000000,0.741866))
App.ActiveDocument.addObject("Part::Cylinder","C1284")
App.ActiveDocument.C1284.Radius=0.512927
App.ActiveDocument.C1284.Height=20.00
App.ActiveDocument.C1284.Angle=360.00 
App.ActiveDocument.C1284.Placement=Base.Placement(Base.Vector(-51.083800,156.207355,18.610786),Base.Rotation(0.009846,-0.659182,0.000000,0.751919))
App.ActiveDocument.addObject("Part::Cylinder","C1285")
App.ActiveDocument.C1285.Radius=0.513566
App.ActiveDocument.C1285.Height=20.00
App.ActiveDocument.C1285.Angle=360.00 
App.ActiveDocument.C1285.Placement=Base.Placement(Base.Vector(-50.861365,152.433312,18.117812),Base.Rotation(0.091869,-0.631939,0.000000,0.769554))
App.ActiveDocument.addObject("Part::Cylinder","C1286")
App.ActiveDocument.C1286.Radius=0.515593
App.ActiveDocument.C1286.Height=20.00
App.ActiveDocument.C1286.Angle=360.00 
App.ActiveDocument.C1286.Placement=Base.Placement(Base.Vector(-50.071105,147.686346,18.281550),Base.Rotation(0.100698,-0.621110,0.000000,0.777227))
App.ActiveDocument.addObject("Part::Cylinder","C1287")
App.ActiveDocument.C1287.Radius=0.515473
App.ActiveDocument.C1287.Height=20.00
App.ActiveDocument.C1287.Angle=360.00 
App.ActiveDocument.C1287.Placement=Base.Placement(Base.Vector(-49.871198,139.951641,17.602823),Base.Rotation(-0.079112,-0.605355,0.000000,0.792014))
App.ActiveDocument.addObject("Part::Cylinder","C1288")
App.ActiveDocument.C1288.Radius=0.514226
App.ActiveDocument.C1288.Height=20.00
App.ActiveDocument.C1288.Angle=360.00 
App.ActiveDocument.C1288.Placement=Base.Placement(Base.Vector(-50.771422,135.400701,17.486666),Base.Rotation(-0.071253,-0.602712,0.000000,0.794771))
App.ActiveDocument.addObject("Part::Cylinder","C1289")
App.ActiveDocument.C1289.Radius=0.516734
App.ActiveDocument.C1289.Height=20.00
App.ActiveDocument.C1289.Angle=360.00 
App.ActiveDocument.C1289.Placement=Base.Placement(Base.Vector(-50.431936,132.784661,17.816862),Base.Rotation(0.072397,-0.581113,0.000000,0.810596))
App.ActiveDocument.addObject("Part::Cylinder","C1290")
App.ActiveDocument.C1290.Radius=0.516422
App.ActiveDocument.C1290.Height=20.00
App.ActiveDocument.C1290.Angle=360.00 
App.ActiveDocument.C1290.Placement=Base.Placement(Base.Vector(-49.865443,128.892960,17.544862),Base.Rotation(0.134380,-0.581483,0.000000,0.802383))
App.ActiveDocument.addObject("Part::Cylinder","C1291")
App.ActiveDocument.C1291.Radius=0.517249
App.ActiveDocument.C1291.Height=20.00
App.ActiveDocument.C1291.Angle=360.00 
App.ActiveDocument.C1291.Placement=Base.Placement(Base.Vector(-48.923333,125.205952,17.234518),Base.Rotation(0.185067,-0.568045,0.000000,0.801920))
App.ActiveDocument.addObject("Part::Cylinder","C1292")
App.ActiveDocument.C1292.Radius=0.518196
App.ActiveDocument.C1292.Height=20.00
App.ActiveDocument.C1292.Angle=360.00 
App.ActiveDocument.C1292.Placement=Base.Placement(Base.Vector(-47.508172,120.832795,16.794934),Base.Rotation(0.199174,-0.564325,0.000000,0.801166))
App.ActiveDocument.addObject("Part::Cylinder","C1293")
App.ActiveDocument.C1293.Radius=0.521591
App.ActiveDocument.C1293.Height=20.00
App.ActiveDocument.C1293.Angle=360.00 
App.ActiveDocument.C1293.Placement=Base.Placement(Base.Vector(-46.546983,117.553447,16.430492),Base.Rotation(0.291740,-0.487291,0.000000,0.823065))
App.ActiveDocument.addObject("Part::Cylinder","C1294")
App.ActiveDocument.C1294.Radius=0.598175
App.ActiveDocument.C1294.Height=20.00
App.ActiveDocument.C1294.Angle=360.00 
App.ActiveDocument.C1294.Placement=Base.Placement(Base.Vector(-4.150649,205.853479,24.176333),Base.Rotation(-0.665089,-0.088962,0.000000,0.741446))
App.ActiveDocument.addObject("Part::Cylinder","C1295")
App.ActiveDocument.C1295.Radius=0.592301
App.ActiveDocument.C1295.Height=20.00
App.ActiveDocument.C1295.Angle=360.00 
App.ActiveDocument.C1295.Placement=Base.Placement(Base.Vector(-8.063208,205.137245,24.344206),Base.Rotation(-0.653983,-0.145397,0.000000,0.742405))
App.ActiveDocument.addObject("Part::Cylinder","C1296")
App.ActiveDocument.C1296.Radius=0.585313
App.ActiveDocument.C1296.Height=20.00
App.ActiveDocument.C1296.Angle=360.00 
App.ActiveDocument.C1296.Placement=Base.Placement(Base.Vector(-11.954878,204.114671,24.033641),Base.Rotation(-0.637619,-0.204338,0.000000,0.742757))
App.ActiveDocument.addObject("Part::Cylinder","C1297")
App.ActiveDocument.C1297.Radius=0.579581
App.ActiveDocument.C1297.Height=20.00
App.ActiveDocument.C1297.Angle=360.00 
App.ActiveDocument.C1297.Placement=Base.Placement(Base.Vector(-16.258264,202.604648,24.211562),Base.Rotation(-0.628100,-0.228538,0.000000,0.743815))
App.ActiveDocument.addObject("Part::Cylinder","C1298")
App.ActiveDocument.C1298.Radius=0.574174
App.ActiveDocument.C1298.Height=20.00
App.ActiveDocument.C1298.Angle=360.00 
App.ActiveDocument.C1298.Placement=Base.Placement(Base.Vector(-20.467213,200.885990,24.610526),Base.Rotation(-0.612821,-0.265462,0.000000,0.744299))
App.ActiveDocument.addObject("Part::Cylinder","C1299")
App.ActiveDocument.C1299.Radius=0.566334
App.ActiveDocument.C1299.Height=20.00
App.ActiveDocument.C1299.Angle=360.00 
App.ActiveDocument.C1299.Placement=Base.Placement(Base.Vector(-24.538602,199.078313,23.911418),Base.Rotation(-0.597594,-0.304004,0.000000,0.741932))
App.ActiveDocument.addObject("Part::Cylinder","C1300")
App.ActiveDocument.C1300.Radius=0.561702
App.ActiveDocument.C1300.Height=20.00
App.ActiveDocument.C1300.Angle=360.00 
App.ActiveDocument.C1300.Placement=Base.Placement(Base.Vector(-28.295535,196.945728,24.423097),Base.Rotation(-0.571341,-0.347646,0.000000,0.743446))
App.ActiveDocument.addObject("Part::Cylinder","C1301")
App.ActiveDocument.C1301.Radius=0.555887
App.ActiveDocument.C1301.Height=20.00
App.ActiveDocument.C1301.Angle=360.00 
App.ActiveDocument.C1301.Placement=Base.Placement(Base.Vector(-32.046758,194.497417,24.330356),Base.Rotation(-0.546406,-0.383231,0.000000,0.744698))
App.ActiveDocument.addObject("Part::Cylinder","C1302")
App.ActiveDocument.C1302.Radius=0.550591
App.ActiveDocument.C1302.Height=20.00
App.ActiveDocument.C1302.Angle=360.00 
App.ActiveDocument.C1302.Placement=Base.Placement(Base.Vector(-35.191246,192.088559,24.282362),Base.Rotation(-0.503973,-0.436463,0.000000,0.745326))
App.ActiveDocument.addObject("Part::Cylinder","C1303")
App.ActiveDocument.C1303.Radius=0.544839
App.ActiveDocument.C1303.Height=20.00
App.ActiveDocument.C1303.Angle=360.00 
App.ActiveDocument.C1303.Placement=Base.Placement(Base.Vector(-38.137568,189.351077,23.893374),Base.Rotation(-0.461123,-0.483266,0.000000,0.744190))
App.ActiveDocument.addObject("Part::Cylinder","C1304")
App.ActiveDocument.C1304.Radius=0.541551
App.ActiveDocument.C1304.Height=20.00
App.ActiveDocument.C1304.Angle=360.00 
App.ActiveDocument.C1304.Placement=Base.Placement(Base.Vector(-40.485607,186.487976,24.212868),Base.Rotation(-0.397467,-0.533637,0.000000,0.746492))
App.ActiveDocument.addObject("Part::Cylinder","C1305")
App.ActiveDocument.C1305.Radius=0.537282
App.ActiveDocument.C1305.Height=20.00
App.ActiveDocument.C1305.Angle=360.00 
App.ActiveDocument.C1305.Placement=Base.Placement(Base.Vector(-42.766734,183.140305,23.865028),Base.Rotation(-0.346694,-0.564438,0.000000,0.749141))
App.ActiveDocument.addObject("Part::Cylinder","C1306")
App.ActiveDocument.C1306.Radius=0.534335
App.ActiveDocument.C1306.Height=20.00
App.ActiveDocument.C1306.Angle=360.00 
App.ActiveDocument.C1306.Placement=Base.Placement(Base.Vector(-44.812506,179.482326,23.834400),Base.Rotation(-0.286859,-0.588987,0.000000,0.755517))
App.ActiveDocument.addObject("Part::Cylinder","C1307")
App.ActiveDocument.C1307.Radius=0.531076
App.ActiveDocument.C1307.Height=20.00
App.ActiveDocument.C1307.Angle=360.00 
App.ActiveDocument.C1307.Placement=Base.Placement(Base.Vector(-46.470916,175.746261,23.453568),Base.Rotation(-0.223780,-0.610530,0.000000,0.759721))
App.ActiveDocument.addObject("Part::Cylinder","C1308")
App.ActiveDocument.C1308.Radius=0.529034
App.ActiveDocument.C1308.Height=20.00
App.ActiveDocument.C1308.Angle=360.00 
App.ActiveDocument.C1308.Placement=Base.Placement(Base.Vector(-47.693602,171.934733,23.401833),Base.Rotation(-0.179662,-0.625195,0.000000,0.759508))
App.ActiveDocument.addObject("Part::Cylinder","C1309")
App.ActiveDocument.C1309.Radius=0.527503
App.ActiveDocument.C1309.Height=20.00
App.ActiveDocument.C1309.Angle=360.00 
App.ActiveDocument.C1309.Placement=Base.Placement(Base.Vector(-48.846798,167.426016,23.594373),Base.Rotation(-0.154368,-0.636588,0.000000,0.755597))
App.ActiveDocument.addObject("Part::Cylinder","C1310")
App.ActiveDocument.C1310.Radius=0.525750
App.ActiveDocument.C1310.Height=20.00
App.ActiveDocument.C1310.Angle=360.00 
App.ActiveDocument.C1310.Placement=Base.Placement(Base.Vector(-49.816404,163.143880,23.382951),Base.Rotation(-0.106500,-0.643200,0.000000,0.758255))
App.ActiveDocument.addObject("Part::Cylinder","C1311")
App.ActiveDocument.C1311.Radius=0.525461
App.ActiveDocument.C1311.Height=20.00
App.ActiveDocument.C1311.Angle=360.00 
App.ActiveDocument.C1311.Placement=Base.Placement(Base.Vector(-50.340629,159.307816,23.147060),Base.Rotation(-0.030440,-0.633863,0.000000,0.772846))
App.ActiveDocument.addObject("Part::Cylinder","C1312")
App.ActiveDocument.C1312.Radius=0.524743
App.ActiveDocument.C1312.Height=20.00
App.ActiveDocument.C1312.Angle=360.00 
App.ActiveDocument.C1312.Placement=Base.Placement(Base.Vector(-50.405895,155.979511,22.338411),Base.Rotation(0.067864,-0.613478,0.000000,0.786791))
App.ActiveDocument.addObject("Part::Cylinder","C1313")
App.ActiveDocument.C1313.Radius=0.526389
App.ActiveDocument.C1313.Height=20.00
App.ActiveDocument.C1313.Angle=360.00 
App.ActiveDocument.C1313.Placement=Base.Placement(Base.Vector(-49.731092,151.765481,22.114632),Base.Rotation(0.119325,-0.588108,0.000000,0.799932))
App.ActiveDocument.addObject("Part::Cylinder","C1314")
App.ActiveDocument.C1314.Radius=0.528384
App.ActiveDocument.C1314.Height=20.00
App.ActiveDocument.C1314.Angle=360.00 
App.ActiveDocument.C1314.Placement=Base.Placement(Base.Vector(-48.717500,146.696647,22.068259),Base.Rotation(0.107899,-0.577323,0.000000,0.809356))
App.ActiveDocument.addObject("Part::Cylinder","C1315")
App.ActiveDocument.C1315.Radius=0.527956
App.ActiveDocument.C1315.Height=20.00
App.ActiveDocument.C1315.Angle=360.00 
App.ActiveDocument.C1315.Placement=Base.Placement(Base.Vector(-48.692485,138.672959,21.433876),Base.Rotation(-0.086378,-0.564429,0.000000,0.820950))
App.ActiveDocument.addObject("Part::Cylinder","C1316")
App.ActiveDocument.C1316.Radius=0.527542
App.ActiveDocument.C1316.Height=20.00
App.ActiveDocument.C1316.Angle=360.00 
App.ActiveDocument.C1316.Placement=Base.Placement(Base.Vector(-49.164886,135.117329,21.646860),Base.Rotation(-0.018801,-0.572641,0.000000,0.819591))
App.ActiveDocument.addObject("Part::Cylinder","C1317")
App.ActiveDocument.C1317.Radius=0.529559
App.ActiveDocument.C1317.Height=20.00
App.ActiveDocument.C1317.Angle=360.00 
App.ActiveDocument.C1317.Placement=Base.Placement(Base.Vector(-48.586756,132.027835,22.152672),Base.Rotation(0.095413,-0.565460,0.000000,0.819238))
App.ActiveDocument.addObject("Part::Cylinder","C1318")
App.ActiveDocument.C1318.Radius=0.529386
App.ActiveDocument.C1318.Height=20.00
App.ActiveDocument.C1318.Angle=360.00 
App.ActiveDocument.C1318.Placement=Base.Placement(Base.Vector(-48.051962,128.327039,21.328706),Base.Rotation(0.155020,-0.541475,0.000000,0.826301))
App.ActiveDocument.addObject("Part::Cylinder","C1319")
App.ActiveDocument.C1319.Radius=0.530725
App.ActiveDocument.C1319.Height=20.00
App.ActiveDocument.C1319.Angle=360.00 
App.ActiveDocument.C1319.Placement=Base.Placement(Base.Vector(-46.888586,124.278351,20.849640),Base.Rotation(0.191137,-0.519790,0.000000,0.832637))
App.ActiveDocument.addObject("Part::Cylinder","C1320")
App.ActiveDocument.C1320.Radius=0.530998
App.ActiveDocument.C1320.Height=20.00
App.ActiveDocument.C1320.Angle=360.00 
App.ActiveDocument.C1320.Placement=Base.Placement(Base.Vector(-45.695187,119.828880,19.853627),Base.Rotation(0.199627,-0.502799,0.000000,0.841037))
App.ActiveDocument.addObject("Part::Cylinder","C1321")
App.ActiveDocument.C1321.Radius=0.533289
App.ActiveDocument.C1321.Height=20.00
App.ActiveDocument.C1321.Angle=360.00 
App.ActiveDocument.C1321.Placement=Base.Placement(Base.Vector(-50.413888,122.371824,18.695773),Base.Rotation(0.539726,-0.007906,0.000000,0.841803))
App.ActiveDocument.addObject("Part::Cylinder","C1322")
App.ActiveDocument.C1322.Radius=0.608906
App.ActiveDocument.C1322.Height=20.00
App.ActiveDocument.C1322.Angle=360.00 
App.ActiveDocument.C1322.Placement=Base.Placement(Base.Vector(-3.999677,205.349631,28.652904),Base.Rotation(-0.652474,-0.090168,0.000000,0.752427))
App.ActiveDocument.addObject("Part::Cylinder","C1323")
App.ActiveDocument.C1323.Radius=0.603381
App.ActiveDocument.C1323.Height=20.00
App.ActiveDocument.C1323.Angle=360.00 
App.ActiveDocument.C1323.Placement=Base.Placement(Base.Vector(-8.042320,204.566391,29.034699),Base.Rotation(-0.640056,-0.146180,0.000000,0.754294))
App.ActiveDocument.addObject("Part::Cylinder","C1324")
App.ActiveDocument.C1324.Radius=0.595870
App.ActiveDocument.C1324.Height=20.00
App.ActiveDocument.C1324.Angle=360.00 
App.ActiveDocument.C1324.Placement=Base.Placement(Base.Vector(-12.182246,203.465335,28.655943),Base.Rotation(-0.625544,-0.202615,0.000000,0.753420))
App.ActiveDocument.addObject("Part::Cylinder","C1325")
App.ActiveDocument.C1325.Radius=0.590024
App.ActiveDocument.C1325.Height=20.00
App.ActiveDocument.C1325.Angle=360.00 
App.ActiveDocument.C1325.Placement=Base.Placement(Base.Vector(-16.629757,201.858187,28.876608),Base.Rotation(-0.614961,-0.228290,0.000000,0.754789))
App.ActiveDocument.addObject("Part::Cylinder","C1326")
App.ActiveDocument.C1326.Radius=0.584798
App.ActiveDocument.C1326.Height=20.00
App.ActiveDocument.C1326.Angle=360.00 
App.ActiveDocument.C1326.Placement=Base.Placement(Base.Vector(-20.845185,200.078602,29.346362),Base.Rotation(-0.599665,-0.263783,0.000000,0.755526))
App.ActiveDocument.addObject("Part::Cylinder","C1327")
App.ActiveDocument.C1327.Radius=0.576870
App.ActiveDocument.C1327.Height=20.00
App.ActiveDocument.C1327.Angle=360.00 
App.ActiveDocument.C1327.Placement=Base.Placement(Base.Vector(-24.701783,198.395559,28.514834),Base.Rotation(-0.583464,-0.304714,0.000000,0.752808))
App.ActiveDocument.addObject("Part::Cylinder","C1328")
App.ActiveDocument.C1328.Radius=0.571957
App.ActiveDocument.C1328.Height=20.00
App.ActiveDocument.C1328.Angle=360.00 
App.ActiveDocument.C1328.Placement=Base.Placement(Base.Vector(-28.502100,196.181959,28.926268),Base.Rotation(-0.557545,-0.347168,0.000000,0.754067))
App.ActiveDocument.addObject("Part::Cylinder","C1329")
App.ActiveDocument.C1329.Radius=0.565908
App.ActiveDocument.C1329.Height=20.00
App.ActiveDocument.C1329.Angle=360.00 
App.ActiveDocument.C1329.Placement=Base.Placement(Base.Vector(-32.091673,193.803041,28.673131),Base.Rotation(-0.532182,-0.384366,0.000000,0.754351))
App.ActiveDocument.addObject("Part::Cylinder","C1330")
App.ActiveDocument.C1330.Radius=0.560773
App.ActiveDocument.C1330.Height=20.00
App.ActiveDocument.C1330.Angle=360.00 
App.ActiveDocument.C1330.Placement=Base.Placement(Base.Vector(-35.380338,191.172196,28.753633),Base.Rotation(-0.490133,-0.434800,0.000000,0.755459))
App.ActiveDocument.addObject("Part::Cylinder","C1331")
App.ActiveDocument.C1331.Radius=0.555591
App.ActiveDocument.C1331.Height=20.00
App.ActiveDocument.C1331.Angle=360.00 
App.ActiveDocument.C1331.Placement=Base.Placement(Base.Vector(-38.103496,188.546530,28.520224),Base.Rotation(-0.439372,-0.486533,0.000000,0.755141))
App.ActiveDocument.addObject("Part::Cylinder","C1332")
App.ActiveDocument.C1332.Radius=0.552550
App.ActiveDocument.C1332.Height=20.00
App.ActiveDocument.C1332.Angle=360.00 
App.ActiveDocument.C1332.Placement=Base.Placement(Base.Vector(-40.342253,185.651694,28.831873),Base.Rotation(-0.375065,-0.532974,0.000000,0.758462))
App.ActiveDocument.addObject("Part::Cylinder","C1333")
App.ActiveDocument.C1333.Radius=0.548449
App.ActiveDocument.C1333.Height=20.00
App.ActiveDocument.C1333.Angle=360.00 
App.ActiveDocument.C1333.Placement=Base.Placement(Base.Vector(-42.545087,182.249009,28.495059),Base.Rotation(-0.320481,-0.563087,0.000000,0.761725))
App.ActiveDocument.addObject("Part::Cylinder","C1334")
App.ActiveDocument.C1334.Radius=0.545613
App.ActiveDocument.C1334.Height=20.00
App.ActiveDocument.C1334.Angle=360.00 
App.ActiveDocument.C1334.Placement=Base.Placement(Base.Vector(-44.378789,178.715062,28.426410),Base.Rotation(-0.263306,-0.586455,0.000000,0.765990))
App.ActiveDocument.addObject("Part::Cylinder","C1335")
App.ActiveDocument.C1335.Radius=0.542547
App.ActiveDocument.C1335.Height=20.00
App.ActiveDocument.C1335.Angle=360.00 
App.ActiveDocument.C1335.Placement=Base.Placement(Base.Vector(-45.896632,175.015035,28.087497),Base.Rotation(-0.210254,-0.605493,0.000000,0.767575))
App.ActiveDocument.addObject("Part::Cylinder","C1336")
App.ActiveDocument.C1336.Radius=0.540894
App.ActiveDocument.C1336.Height=20.00
App.ActiveDocument.C1336.Angle=360.00 
App.ActiveDocument.C1336.Placement=Base.Placement(Base.Vector(-47.169476,170.795105,28.197853),Base.Rotation(-0.176504,-0.616003,0.000000,0.767716))
App.ActiveDocument.addObject("Part::Cylinder","C1337")
App.ActiveDocument.C1337.Radius=0.539650
App.ActiveDocument.C1337.Height=20.00
App.ActiveDocument.C1337.Angle=360.00 
App.ActiveDocument.C1337.Placement=Base.Placement(Base.Vector(-48.243018,166.546070,28.219766),Base.Rotation(-0.135811,-0.620742,0.000000,0.772162))
App.ActiveDocument.addObject("Part::Cylinder","C1338")
App.ActiveDocument.C1338.Radius=0.536996
App.ActiveDocument.C1338.Height=20.00
App.ActiveDocument.C1338.Angle=360.00 
App.ActiveDocument.C1338.Placement=Base.Placement(Base.Vector(-49.116704,162.655018,27.336706),Base.Rotation(-0.069738,-0.620805,0.000000,0.780857))
App.ActiveDocument.addObject("Part::Cylinder","C1339")
App.ActiveDocument.C1339.Radius=0.537610
App.ActiveDocument.C1339.Height=20.00
App.ActiveDocument.C1339.Angle=360.00 
App.ActiveDocument.C1339.Placement=Base.Placement(Base.Vector(-49.267906,159.100629,27.547586),Base.Rotation(0.016534,-0.617663,0.000000,0.786269))
App.ActiveDocument.addObject("Part::Cylinder","C1340")
App.ActiveDocument.C1340.Radius=0.537248
App.ActiveDocument.C1340.Height=20.00
App.ActiveDocument.C1340.Angle=360.00 
App.ActiveDocument.C1340.Placement=Base.Placement(Base.Vector(-49.017852,155.323541,27.118417),Base.Rotation(0.095949,-0.608781,0.000000,0.787515))
App.ActiveDocument.addObject("Part::Cylinder","C1341")
App.ActiveDocument.C1341.Radius=0.539366
App.ActiveDocument.C1341.Height=20.00
App.ActiveDocument.C1341.Angle=360.00 
App.ActiveDocument.C1341.Placement=Base.Placement(Base.Vector(-48.087278,150.948467,27.604819),Base.Rotation(0.131469,-0.607416,0.000000,0.783430))
App.ActiveDocument.addObject("Part::Cylinder","C1342")
App.ActiveDocument.C1342.Radius=0.541037
App.ActiveDocument.C1342.Height=20.00
App.ActiveDocument.C1342.Angle=360.00 
App.ActiveDocument.C1342.Placement=Base.Placement(Base.Vector(-46.977559,145.815984,27.191526),Base.Rotation(0.120702,-0.590942,0.000000,0.797633))
App.ActiveDocument.addObject("Part::Cylinder","C1343")
App.ActiveDocument.C1343.Radius=0.541185
App.ActiveDocument.C1343.Height=20.00
App.ActiveDocument.C1343.Angle=360.00 
App.ActiveDocument.C1343.Placement=Base.Placement(Base.Vector(-47.140328,137.392112,26.706803),Base.Rotation(-0.095907,-0.570669,0.000000,0.815560))
App.ActiveDocument.addObject("Part::Cylinder","C1344")
App.ActiveDocument.C1344.Radius=0.540953
App.ActiveDocument.C1344.Height=20.00
App.ActiveDocument.C1344.Angle=360.00 
App.ActiveDocument.C1344.Placement=Base.Placement(Base.Vector(-47.442800,134.897396,26.315657),Base.Rotation(0.045563,-0.557905,0.000000,0.828653))
App.ActiveDocument.addObject("Part::Cylinder","C1345")
App.ActiveDocument.C1345.Radius=0.542712
App.ActiveDocument.C1345.Height=20.00
App.ActiveDocument.C1345.Angle=360.00 
App.ActiveDocument.C1345.Placement=Base.Placement(Base.Vector(-46.854239,131.429849,26.293523),Base.Rotation(0.124049,-0.533226,0.000000,0.836829))
App.ActiveDocument.addObject("Part::Cylinder","C1346")
App.ActiveDocument.C1346.Radius=0.542456
App.ActiveDocument.C1346.Height=20.00
App.ActiveDocument.C1346.Angle=360.00 
App.ActiveDocument.C1346.Placement=Base.Placement(Base.Vector(-46.158124,127.582396,25.372431),Base.Rotation(0.175438,-0.509747,0.000000,0.842247))
App.ActiveDocument.addObject("Part::Cylinder","C1347")
App.ActiveDocument.C1347.Radius=0.543632
App.ActiveDocument.C1347.Height=20.00
App.ActiveDocument.C1347.Angle=360.00 
App.ActiveDocument.C1347.Placement=Base.Placement(Base.Vector(-44.729960,123.248116,24.896351),Base.Rotation(0.195927,-0.499469,0.000000,0.843886))
App.ActiveDocument.addObject("Part::Cylinder","C1348")
App.ActiveDocument.C1348.Radius=0.544636
App.ActiveDocument.C1348.Height=20.00
App.ActiveDocument.C1348.Angle=360.00 
App.ActiveDocument.C1348.Placement=Base.Placement(Base.Vector(-46.793280,123.260707,23.199317),Base.Rotation(0.428378,-0.245084,0.000000,0.869728))
App.ActiveDocument.addObject("Part::Cylinder","C1349")
App.ActiveDocument.C1349.Radius=0.619633
App.ActiveDocument.C1349.Height=20.00
App.ActiveDocument.C1349.Angle=360.00 
App.ActiveDocument.C1349.Placement=Base.Placement(Base.Vector(-3.918436,204.677234,33.030097),Base.Rotation(-0.635899,-0.087558,0.000000,0.766789))
App.ActiveDocument.addObject("Part::Cylinder","C1350")
App.ActiveDocument.C1350.Radius=0.614262
App.ActiveDocument.C1350.Height=20.00
App.ActiveDocument.C1350.Angle=360.00 
App.ActiveDocument.C1350.Placement=Base.Placement(Base.Vector(-7.934539,203.863836,33.469409),Base.Rotation(-0.624227,-0.141803,0.000000,0.768266))
App.ActiveDocument.addObject("Part::Cylinder","C1351")
App.ActiveDocument.C1351.Radius=0.607463
App.ActiveDocument.C1351.Height=20.00
App.ActiveDocument.C1351.Angle=360.00 
App.ActiveDocument.C1351.Placement=Base.Placement(Base.Vector(-11.840987,202.815484,33.298715),Base.Rotation(-0.610844,-0.197704,0.000000,0.766670))
App.ActiveDocument.addObject("Part::Cylinder","C1352")
App.ActiveDocument.C1352.Radius=0.601497
App.ActiveDocument.C1352.Height=20.00
App.ActiveDocument.C1352.Angle=360.00 
App.ActiveDocument.C1352.Placement=Base.Placement(Base.Vector(-16.121297,201.283575,33.399905),Base.Rotation(-0.601809,-0.223201,0.000000,0.766816))
App.ActiveDocument.addObject("Part::Cylinder","C1353")
App.ActiveDocument.C1353.Radius=0.596042
App.ActiveDocument.C1353.Height=20.00
App.ActiveDocument.C1353.Angle=360.00 
App.ActiveDocument.C1353.Placement=Base.Placement(Base.Vector(-20.289602,199.558557,33.695263),Base.Rotation(-0.587748,-0.254695,0.000000,0.767908))
App.ActiveDocument.addObject("Part::Cylinder","C1354")
App.ActiveDocument.C1354.Radius=0.588935
App.ActiveDocument.C1354.Height=20.00
App.ActiveDocument.C1354.Angle=360.00 
App.ActiveDocument.C1354.Placement=Base.Placement(Base.Vector(-24.079800,197.899874,33.139879),Base.Rotation(-0.570079,-0.294224,0.000000,0.767099))
App.ActiveDocument.addObject("Part::Cylinder","C1355")
App.ActiveDocument.C1355.Radius=0.583884
App.ActiveDocument.C1355.Height=20.00
App.ActiveDocument.C1355.Angle=360.00 
App.ActiveDocument.C1355.Placement=Base.Placement(Base.Vector(-27.790867,195.763268,33.410169),Base.Rotation(-0.545030,-0.334546,0.000000,0.768779))
App.ActiveDocument.addObject("Part::Cylinder","C1356")
App.ActiveDocument.C1356.Radius=0.577283
App.ActiveDocument.C1356.Height=20.00
App.ActiveDocument.C1356.Angle=360.00 
App.ActiveDocument.C1356.Placement=Base.Placement(Base.Vector(-31.416068,193.428518,32.910864),Base.Rotation(-0.516022,-0.373836,0.000000,0.770693))
App.ActiveDocument.addObject("Part::Cylinder","C1357")
App.ActiveDocument.C1357.Radius=0.572579
App.ActiveDocument.C1357.Height=20.00
App.ActiveDocument.C1357.Angle=360.00 
App.ActiveDocument.C1357.Placement=Base.Placement(Base.Vector(-34.726123,190.750752,33.127804),Base.Rotation(-0.477509,-0.418158,0.000000,0.772741))
App.ActiveDocument.addObject("Part::Cylinder","C1358")
App.ActiveDocument.C1358.Radius=0.567114
App.ActiveDocument.C1358.Height=20.00
App.ActiveDocument.C1358.Angle=360.00 
App.ActiveDocument.C1358.Placement=Base.Placement(Base.Vector(-37.561718,188.044893,32.867969),Base.Rotation(-0.421491,-0.474072,0.000000,0.773047))
App.ActiveDocument.addObject("Part::Cylinder","C1359")
App.ActiveDocument.C1359.Radius=0.563793
App.ActiveDocument.C1359.Height=20.00
App.ActiveDocument.C1359.Angle=360.00 
App.ActiveDocument.C1359.Placement=Base.Placement(Base.Vector(-39.884905,184.939196,33.212861),Base.Rotation(-0.352418,-0.525764,0.000000,0.774192))
App.ActiveDocument.addObject("Part::Cylinder","C1360")
App.ActiveDocument.C1360.Radius=0.560179
App.ActiveDocument.C1360.Height=20.00
App.ActiveDocument.C1360.Angle=360.00 
App.ActiveDocument.C1360.Placement=Base.Placement(Base.Vector(-42.015805,181.460483,33.115684),Base.Rotation(-0.303799,-0.554702,0.000000,0.774604))
App.ActiveDocument.addObject("Part::Cylinder","C1361")
App.ActiveDocument.C1361.Radius=0.557061
App.ActiveDocument.C1361.Height=20.00
App.ActiveDocument.C1361.Angle=360.00 
App.ActiveDocument.C1361.Placement=Base.Placement(Base.Vector(-43.843909,177.733616,33.078458),Base.Rotation(-0.252433,-0.581413,0.000000,0.773457))
App.ActiveDocument.addObject("Part::Cylinder","C1362")
App.ActiveDocument.C1362.Radius=0.554304
App.ActiveDocument.C1362.Height=20.00
App.ActiveDocument.C1362.Angle=360.00 
App.ActiveDocument.C1362.Placement=Base.Placement(Base.Vector(-45.273951,173.977984,32.946816),Base.Rotation(-0.202934,-0.603412,0.000000,0.771176))
App.ActiveDocument.addObject("Part::Cylinder","C1363")
App.ActiveDocument.C1363.Radius=0.552846
App.ActiveDocument.C1363.Height=20.00
App.ActiveDocument.C1363.Angle=360.00 
App.ActiveDocument.C1363.Placement=Base.Placement(Base.Vector(-46.498117,169.707787,33.165627),Base.Rotation(-0.166200,-0.615963,0.000000,0.770044))
App.ActiveDocument.addObject("Part::Cylinder","C1364")
App.ActiveDocument.C1364.Radius=0.551401
App.ActiveDocument.C1364.Height=20.00
App.ActiveDocument.C1364.Angle=360.00 
App.ActiveDocument.C1364.Placement=Base.Placement(Base.Vector(-47.472045,165.282610,33.277354),Base.Rotation(-0.118006,-0.629769,0.000000,0.767767))
App.ActiveDocument.addObject("Part::Cylinder","C1365")
App.ActiveDocument.C1365.Radius=0.549346
App.ActiveDocument.C1365.Height=20.00
App.ActiveDocument.C1365.Angle=360.00 
App.ActiveDocument.C1365.Placement=Base.Placement(Base.Vector(-48.098067,161.579415,32.907202),Base.Rotation(-0.049692,-0.642401,0.000000,0.764756))
App.ActiveDocument.addObject("Part::Cylinder","C1366")
App.ActiveDocument.C1366.Radius=0.549874
App.ActiveDocument.C1366.Height=20.00
App.ActiveDocument.C1366.Angle=360.00 
App.ActiveDocument.C1366.Placement=Base.Placement(Base.Vector(-48.110857,158.091573,32.995751),Base.Rotation(0.057308,-0.636383,0.000000,0.769242))
App.ActiveDocument.addObject("Part::Cylinder","C1367")
App.ActiveDocument.C1367.Radius=0.550040
App.ActiveDocument.C1367.Height=20.00
App.ActiveDocument.C1367.Angle=360.00 
App.ActiveDocument.C1367.Placement=Base.Placement(Base.Vector(-47.658530,154.456119,32.462641),Base.Rotation(0.117440,-0.618891,0.000000,0.776648))
App.ActiveDocument.addObject("Part::Cylinder","C1368")
App.ActiveDocument.C1368.Radius=0.552229
App.ActiveDocument.C1368.Height=20.00
App.ActiveDocument.C1368.Angle=360.00 
App.ActiveDocument.C1368.Placement=Base.Placement(Base.Vector(-46.789429,150.510738,32.517341),Base.Rotation(0.169434,-0.595892,0.000000,0.784987))
App.ActiveDocument.addObject("Part::Cylinder","C1369")
App.ActiveDocument.C1369.Radius=0.553947
App.ActiveDocument.C1369.Height=20.00
App.ActiveDocument.C1369.Angle=360.00 
App.ActiveDocument.C1369.Placement=Base.Placement(Base.Vector(-45.066032,143.774468,31.392689),Base.Rotation(0.057871,-0.579000,0.000000,0.813271))
App.ActiveDocument.addObject("Part::Cylinder","C1370")
App.ActiveDocument.C1370.Radius=0.553695
App.ActiveDocument.C1370.Height=20.00
App.ActiveDocument.C1370.Angle=360.00 
App.ActiveDocument.C1370.Placement=Base.Placement(Base.Vector(-45.398616,136.464959,32.567227),Base.Rotation(-0.093142,-0.614793,0.000000,0.783170))
App.ActiveDocument.addObject("Part::Cylinder","C1371")
App.ActiveDocument.C1371.Radius=0.554026
App.ActiveDocument.C1371.Height=20.00
App.ActiveDocument.C1371.Angle=360.00 
App.ActiveDocument.C1371.Placement=Base.Placement(Base.Vector(-45.245289,134.701620,32.814942),Base.Rotation(0.100053,-0.620790,0.000000,0.777566))
App.ActiveDocument.addObject("Part::Cylinder","C1372")
App.ActiveDocument.C1372.Radius=0.555846
App.ActiveDocument.C1372.Height=20.00
App.ActiveDocument.C1372.Angle=360.00 
App.ActiveDocument.C1372.Placement=Base.Placement(Base.Vector(-44.470914,131.353028,32.491085),Base.Rotation(0.189764,-0.582020,0.000000,0.790722))
App.ActiveDocument.addObject("Part::Cylinder","C1373")
App.ActiveDocument.C1373.Radius=0.555285
App.ActiveDocument.C1373.Height=20.00
App.ActiveDocument.C1373.Angle=360.00 
App.ActiveDocument.C1373.Placement=Base.Placement(Base.Vector(-43.562918,127.341995,30.566140),Base.Rotation(0.212954,-0.535568,0.000000,0.817201))
App.ActiveDocument.addObject("Part::Cylinder","C1374")
App.ActiveDocument.C1374.Radius=0.556801
App.ActiveDocument.C1374.Height=20.00
App.ActiveDocument.C1374.Angle=360.00 
App.ActiveDocument.C1374.Placement=Base.Placement(Base.Vector(-44.980638,126.228601,28.776861),Base.Rotation(0.411064,-0.313834,0.000000,0.855882))
App.ActiveDocument.addObject("Part::Cylinder","C1375")
App.ActiveDocument.C1375.Radius=0.555663
App.ActiveDocument.C1375.Height=20.00
App.ActiveDocument.C1375.Angle=360.00 
App.ActiveDocument.C1375.Placement=Base.Placement(Base.Vector(-46.686523,125.700349,25.829628),Base.Rotation(0.506418,0.000118,0.000000,0.862288))
App.ActiveDocument.addObject("Part::Cylinder","C1376")
App.ActiveDocument.C1376.Radius=0.630473
App.ActiveDocument.C1376.Height=20.00
App.ActiveDocument.C1376.Angle=360.00 
App.ActiveDocument.C1376.Placement=Base.Placement(Base.Vector(-3.760775,203.810889,37.323605),Base.Rotation(-0.615349,-0.084651,0.000000,0.783696))
App.ActiveDocument.addObject("Part::Cylinder","C1377")
App.ActiveDocument.C1377.Radius=0.625353
App.ActiveDocument.C1377.Height=20.00
App.ActiveDocument.C1377.Angle=360.00 
App.ActiveDocument.C1377.Placement=Base.Placement(Base.Vector(-7.813211,202.942452,37.881644),Base.Rotation(-0.604946,-0.134795,0.000000,0.784774))
App.ActiveDocument.addObject("Part::Cylinder","C1378")
App.ActiveDocument.C1378.Radius=0.618286
App.ActiveDocument.C1378.Height=20.00
App.ActiveDocument.C1378.Angle=360.00 
App.ActiveDocument.C1378.Placement=Base.Placement(Base.Vector(-11.657734,201.951712,37.619031),Base.Rotation(-0.593684,-0.191549,0.000000,0.781567))
App.ActiveDocument.addObject("Part::Cylinder","C1379")
App.ActiveDocument.C1379.Radius=0.612765
App.ActiveDocument.C1379.Height=20.00
App.ActiveDocument.C1379.Angle=360.00 
App.ActiveDocument.C1379.Placement=Base.Placement(Base.Vector(-15.898676,200.393727,37.859365),Base.Rotation(-0.582335,-0.217377,0.000000,0.783347))
App.ActiveDocument.addObject("Part::Cylinder","C1380")
App.ActiveDocument.C1380.Radius=0.607457
App.ActiveDocument.C1380.Height=20.00
App.ActiveDocument.C1380.Angle=360.00 
App.ActiveDocument.C1380.Placement=Base.Placement(Base.Vector(-20.009747,198.671904,38.155257),Base.Rotation(-0.569169,-0.245615,0.000000,0.784678))
App.ActiveDocument.addObject("Part::Cylinder","C1381")
App.ActiveDocument.C1381.Radius=0.599986
App.ActiveDocument.C1381.Height=20.00
App.ActiveDocument.C1381.Angle=360.00 
App.ActiveDocument.C1381.Placement=Base.Placement(Base.Vector(-23.738448,197.077651,37.462460),Base.Rotation(-0.552026,-0.287589,0.000000,0.782662))
App.ActiveDocument.addObject("Part::Cylinder","C1382")
App.ActiveDocument.C1382.Radius=0.595541
App.ActiveDocument.C1382.Height=20.00
App.ActiveDocument.C1382.Angle=360.00 
App.ActiveDocument.C1382.Placement=Base.Placement(Base.Vector(-27.276855,194.944064,37.809757),Base.Rotation(-0.520285,-0.328609,0.000000,0.788239))
App.ActiveDocument.addObject("Part::Cylinder","C1383")
App.ActiveDocument.C1383.Radius=0.588917
App.ActiveDocument.C1383.Height=20.00
App.ActiveDocument.C1383.Angle=360.00 
App.ActiveDocument.C1383.Placement=Base.Placement(Base.Vector(-30.832388,192.644686,37.339606),Base.Rotation(-0.495064,-0.367536,0.000000,0.787292))
App.ActiveDocument.addObject("Part::Cylinder","C1384")
App.ActiveDocument.C1384.Radius=0.583979
App.ActiveDocument.C1384.Height=20.00
App.ActiveDocument.C1384.Angle=360.00 
App.ActiveDocument.C1384.Placement=Base.Placement(Base.Vector(-34.026170,190.096029,37.303868),Base.Rotation(-0.457401,-0.406888,0.000000,0.790713))
App.ActiveDocument.addObject("Part::Cylinder","C1385")
App.ActiveDocument.C1385.Radius=0.578966
App.ActiveDocument.C1385.Height=20.00
App.ActiveDocument.C1385.Angle=360.00 
App.ActiveDocument.C1385.Placement=Base.Placement(Base.Vector(-36.810938,187.418445,37.187734),Base.Rotation(-0.405112,-0.458412,0.000000,0.791039))
App.ActiveDocument.addObject("Part::Cylinder","C1386")
App.ActiveDocument.C1386.Radius=0.576302
App.ActiveDocument.C1386.Height=20.00
App.ActiveDocument.C1386.Angle=360.00 
App.ActiveDocument.C1386.Placement=Base.Placement(Base.Vector(-39.046762,184.326213,37.805142),Base.Rotation(-0.348810,-0.504860,0.000000,0.789587))
App.ActiveDocument.addObject("Part::Cylinder","C1387")
App.ActiveDocument.C1387.Radius=0.572476
App.ActiveDocument.C1387.Height=20.00
App.ActiveDocument.C1387.Angle=360.00 
App.ActiveDocument.C1387.Placement=Base.Placement(Base.Vector(-41.143479,180.903548,37.812289),Base.Rotation(-0.305029,-0.540688,0.000000,0.783973))
App.ActiveDocument.addObject("Part::Cylinder","C1388")
App.ActiveDocument.C1388.Radius=0.568841
App.ActiveDocument.C1388.Height=20.00
App.ActiveDocument.C1388.Angle=360.00 
App.ActiveDocument.C1388.Placement=Base.Placement(Base.Vector(-42.983686,177.284278,37.701434),Base.Rotation(-0.255450,-0.572919,0.000000,0.778787))
App.ActiveDocument.addObject("Part::Cylinder","C1389")
App.ActiveDocument.C1389.Radius=0.566312
App.ActiveDocument.C1389.Height=20.00
App.ActiveDocument.C1389.Angle=360.00 
App.ActiveDocument.C1389.Placement=Base.Placement(Base.Vector(-44.472170,173.386628,37.773802),Base.Rotation(-0.205698,-0.597638,0.000000,0.774930))
App.ActiveDocument.addObject("Part::Cylinder","C1390")
App.ActiveDocument.C1390.Radius=0.565030
App.ActiveDocument.C1390.Height=20.00
App.ActiveDocument.C1390.Angle=360.00 
App.ActiveDocument.C1390.Placement=Base.Placement(Base.Vector(-45.629155,169.334923,38.146989),Base.Rotation(-0.169618,-0.614346,0.000000,0.770590))
App.ActiveDocument.addObject("Part::Cylinder","C1391")
App.ActiveDocument.C1391.Radius=0.563557
App.ActiveDocument.C1391.Height=20.00
App.ActiveDocument.C1391.Angle=360.00 
App.ActiveDocument.C1391.Placement=Base.Placement(Base.Vector(-46.657805,164.955101,38.338945),Base.Rotation(-0.127786,-0.629641,0.000000,0.766304))
App.ActiveDocument.addObject("Part::Cylinder","C1392")
App.ActiveDocument.C1392.Radius=0.560848
App.ActiveDocument.C1392.Height=20.00
App.ActiveDocument.C1392.Angle=360.00 
App.ActiveDocument.C1392.Placement=Base.Placement(Base.Vector(-47.328922,161.505891,37.541459),Base.Rotation(-0.038407,-0.638516,0.000000,0.768650))
App.ActiveDocument.addObject("Part::Cylinder","C1393")
App.ActiveDocument.C1393.Radius=0.562518
App.ActiveDocument.C1393.Height=20.00
App.ActiveDocument.C1393.Angle=360.00 
App.ActiveDocument.C1393.Placement=Base.Placement(Base.Vector(-47.117238,158.017078,38.245159),Base.Rotation(0.064136,-0.639692,0.000000,0.765950))
App.ActiveDocument.addObject("Part::Cylinder","C1394")
App.ActiveDocument.C1394.Radius=0.562411
App.ActiveDocument.C1394.Height=20.00
App.ActiveDocument.C1394.Angle=360.00 
App.ActiveDocument.C1394.Placement=Base.Placement(Base.Vector(-46.511812,153.967155,38.108191),Base.Rotation(0.123474,-0.643588,0.000000,0.755346))
App.ActiveDocument.addObject("Part::Cylinder","C1395")
App.ActiveDocument.C1395.Radius=0.564570
App.ActiveDocument.C1395.Height=20.00
App.ActiveDocument.C1395.Angle=360.00 
App.ActiveDocument.C1395.Placement=Base.Placement(Base.Vector(-45.686179,150.606209,38.367999),Base.Rotation(0.225914,-0.616445,0.000000,0.754293))
App.ActiveDocument.addObject("Part::Cylinder","C1396")
App.ActiveDocument.C1396.Radius=0.566538
App.ActiveDocument.C1396.Height=20.00
App.ActiveDocument.C1396.Angle=360.00 
App.ActiveDocument.C1396.Placement=Base.Placement(Base.Vector(-43.412819,142.693245,37.088682),Base.Rotation(0.024596,-0.615123,0.000000,0.788047))
App.ActiveDocument.addObject("Part::Cylinder","C1397")
App.ActiveDocument.C1397.Radius=0.566456
App.ActiveDocument.C1397.Height=20.00
App.ActiveDocument.C1397.Angle=360.00 
App.ActiveDocument.C1397.Placement=Base.Placement(Base.Vector(-44.638947,136.929474,34.887831),Base.Rotation(-0.024586,-0.510749,0.000000,0.859378))
App.ActiveDocument.addObject("Part::Cylinder","C1398")
App.ActiveDocument.C1398.Radius=0.566844
App.ActiveDocument.C1398.Height=20.00
App.ActiveDocument.C1398.Angle=360.00 
App.ActiveDocument.C1398.Placement=Base.Placement(Base.Vector(-44.525105,133.932309,34.443636),Base.Rotation(0.090665,-0.485550,0.000000,0.869495))
App.ActiveDocument.addObject("Part::Cylinder","C1399")
App.ActiveDocument.C1399.Radius=0.568380
App.ActiveDocument.C1399.Height=20.00
App.ActiveDocument.C1399.Angle=360.00 
App.ActiveDocument.C1399.Placement=Base.Placement(Base.Vector(-43.245000,130.355346,35.085440),Base.Rotation(0.177657,-0.497904,0.000000,0.848840))
App.ActiveDocument.addObject("Part::Cylinder","C1400")
App.ActiveDocument.C1400.Radius=0.567917
App.ActiveDocument.C1400.Height=20.00
App.ActiveDocument.C1400.Angle=360.00 
App.ActiveDocument.C1400.Placement=Base.Placement(Base.Vector(-42.384232,127.330352,34.435762),Base.Rotation(0.273133,-0.473803,0.000000,0.837204))
App.ActiveDocument.addObject("Part::Cylinder","C1401")
App.ActiveDocument.C1401.Radius=0.569419
App.ActiveDocument.C1401.Height=20.00
App.ActiveDocument.C1401.Angle=360.00 
App.ActiveDocument.C1401.Placement=Base.Placement(Base.Vector(-46.451662,128.960563,32.338359),Base.Rotation(0.525850,-0.000127,0.000000,0.850577))
App.ActiveDocument.addObject("Part::Cylinder","C1402")
App.ActiveDocument.C1402.Radius=0.567237
App.ActiveDocument.C1402.Height=20.00
App.ActiveDocument.C1402.Angle=360.00 
App.ActiveDocument.C1402.Placement=Base.Placement(Base.Vector(-42.829843,127.517744,29.309422),Base.Rotation(0.532735,0.000028,0.000000,0.846282))
App.ActiveDocument.addObject("Part::Cylinder","C1403")
App.ActiveDocument.C1403.Radius=0.641121
App.ActiveDocument.C1403.Height=20.00
App.ActiveDocument.C1403.Angle=360.00 
App.ActiveDocument.C1403.Placement=Base.Placement(Base.Vector(-3.831339,202.643423,41.670795),Base.Rotation(-0.593826,-0.082605,0.000000,0.800342))
App.ActiveDocument.addObject("Part::Cylinder","C1404")
App.ActiveDocument.C1404.Radius=0.635444
App.ActiveDocument.C1404.Height=20.00
App.ActiveDocument.C1404.Angle=360.00 
App.ActiveDocument.C1404.Placement=Base.Placement(Base.Vector(-7.973201,201.756849,42.038243),Base.Rotation(-0.582556,-0.133595,0.000000,0.801736))
App.ActiveDocument.addObject("Part::Cylinder","C1405")
App.ActiveDocument.C1405.Radius=0.628698
App.ActiveDocument.C1405.Height=20.00
App.ActiveDocument.C1405.Angle=360.00 
App.ActiveDocument.C1405.Placement=Base.Placement(Base.Vector(-11.915034,200.687283,41.947297),Base.Rotation(-0.570981,-0.187697,0.000000,0.799218))
App.ActiveDocument.addObject("Part::Cylinder","C1406")
App.ActiveDocument.C1406.Radius=0.623459
App.ActiveDocument.C1406.Height=20.00
App.ActiveDocument.C1406.Angle=360.00 
App.ActiveDocument.C1406.Placement=Base.Placement(Base.Vector(-16.138460,199.063974,42.291835),Base.Rotation(-0.558477,-0.213475,0.000000,0.801581))
App.ActiveDocument.addObject("Part::Cylinder","C1407")
App.ActiveDocument.C1407.Radius=0.617644
App.ActiveDocument.C1407.Height=20.00
App.ActiveDocument.C1407.Angle=360.00 
App.ActiveDocument.C1407.Placement=Base.Placement(Base.Vector(-20.324004,197.281619,42.452513),Base.Rotation(-0.543445,-0.245701,0.000000,0.802682))
App.ActiveDocument.addObject("Part::Cylinder","C1408")
App.ActiveDocument.C1408.Radius=0.610275
App.ActiveDocument.C1408.Height=20.00
App.ActiveDocument.C1408.Angle=360.00 
App.ActiveDocument.C1408.Placement=Base.Placement(Base.Vector(-23.960764,195.684281,41.733774),Base.Rotation(-0.521810,-0.289761,0.000000,0.802342))
App.ActiveDocument.addObject("Part::Cylinder","C1409")
App.ActiveDocument.C1409.Radius=0.605720
App.ActiveDocument.C1409.Height=20.00
App.ActiveDocument.C1409.Angle=360.00 
App.ActiveDocument.C1409.Placement=Base.Placement(Base.Vector(-27.447369,193.404249,42.081132),Base.Rotation(-0.493198,-0.329885,0.000000,0.804942))
App.ActiveDocument.addObject("Part::Cylinder","C1410")
App.ActiveDocument.C1410.Radius=0.599062
App.ActiveDocument.C1410.Height=20.00
App.ActiveDocument.C1410.Angle=360.00 
App.ActiveDocument.C1410.Placement=Base.Placement(Base.Vector(-30.925476,191.113760,41.496327),Base.Rotation(-0.466771,-0.365854,0.000000,0.805156))
App.ActiveDocument.addObject("Part::Cylinder","C1411")
App.ActiveDocument.C1411.Radius=0.594554
App.ActiveDocument.C1411.Height=20.00
App.ActiveDocument.C1411.Angle=360.00 
App.ActiveDocument.C1411.Placement=Base.Placement(Base.Vector(-34.024669,188.394873,41.691972),Base.Rotation(-0.428176,-0.407951,0.000000,0.806375))
App.ActiveDocument.addObject("Part::Cylinder","C1412")
App.ActiveDocument.C1412.Radius=0.590148
App.ActiveDocument.C1412.Height=20.00
App.ActiveDocument.C1412.Angle=360.00 
App.ActiveDocument.C1412.Placement=Base.Placement(Base.Vector(-36.596834,185.704208,41.728778),Base.Rotation(-0.383325,-0.453426,0.000000,0.804654))
App.ActiveDocument.addObject("Part::Cylinder","C1413")
App.ActiveDocument.C1413.Radius=0.587277
App.ActiveDocument.C1413.Height=20.00
App.ActiveDocument.C1413.Angle=360.00 
App.ActiveDocument.C1413.Placement=Base.Placement(Base.Vector(-38.787258,182.532412,42.284858),Base.Rotation(-0.334695,-0.497452,0.000000,0.800325))
App.ActiveDocument.addObject("Part::Cylinder","C1414")
App.ActiveDocument.C1414.Radius=0.583113
App.ActiveDocument.C1414.Height=20.00
App.ActiveDocument.C1414.Angle=360.00 
App.ActiveDocument.C1414.Placement=Base.Placement(Base.Vector(-40.928469,179.058894,42.208190),Base.Rotation(-0.298057,-0.531729,0.000000,0.792733))
App.ActiveDocument.addObject("Part::Cylinder","C1415")
App.ActiveDocument.C1415.Radius=0.580167
App.ActiveDocument.C1415.Height=20.00
App.ActiveDocument.C1415.Angle=360.00 
App.ActiveDocument.C1415.Placement=Base.Placement(Base.Vector(-42.497791,175.740015,42.283335),Base.Rotation(-0.237938,-0.568032,0.000000,0.787861))
App.ActiveDocument.addObject("Part::Cylinder","C1416")
App.ActiveDocument.C1416.Radius=0.578068
App.ActiveDocument.C1416.Height=20.00
App.ActiveDocument.C1416.Angle=360.00 
App.ActiveDocument.C1416.Placement=Base.Placement(Base.Vector(-43.920983,171.862514,42.438613),Base.Rotation(-0.202483,-0.586023,0.000000,0.784588))
App.ActiveDocument.addObject("Part::Cylinder","C1417")
App.ActiveDocument.C1417.Radius=0.576964
App.ActiveDocument.C1417.Height=20.00
App.ActiveDocument.C1417.Angle=360.00 
App.ActiveDocument.C1417.Placement=Base.Placement(Base.Vector(-45.089399,167.708907,42.883409),Base.Rotation(-0.162148,-0.602912,0.000000,0.781157))
App.ActiveDocument.addObject("Part::Cylinder","C1418")
App.ActiveDocument.C1418.Radius=0.575112
App.ActiveDocument.C1418.Height=20.00
App.ActiveDocument.C1418.Angle=360.00 
App.ActiveDocument.C1418.Placement=Base.Placement(Base.Vector(-46.002259,163.726368,42.688227),Base.Rotation(-0.095323,-0.615706,0.000000,0.782189))
App.ActiveDocument.addObject("Part::Cylinder","C1419")
App.ActiveDocument.C1419.Radius=0.572927
App.ActiveDocument.C1419.Height=20.00
App.ActiveDocument.C1419.Angle=360.00 
App.ActiveDocument.C1419.Placement=Base.Placement(Base.Vector(-46.422541,160.361091,42.320967),Base.Rotation(-0.022437,-0.633437,0.000000,0.773469))
App.ActiveDocument.addObject("Part::Cylinder","C1420")
App.ActiveDocument.C1420.Radius=0.574552
App.ActiveDocument.C1420.Height=20.00
App.ActiveDocument.C1420.Angle=360.00 
App.ActiveDocument.C1420.Placement=Base.Placement(Base.Vector(-46.169715,156.639522,43.461685),Base.Rotation(0.054014,-0.651700,0.000000,0.756551))
App.ActiveDocument.addObject("Part::Cylinder","C1421")
App.ActiveDocument.C1421.Radius=0.574705
App.ActiveDocument.C1421.Height=20.00
App.ActiveDocument.C1421.Angle=360.00 
App.ActiveDocument.C1421.Placement=Base.Placement(Base.Vector(-45.683263,153.023257,43.324375),Base.Rotation(0.141589,-0.645786,0.000000,0.750275))
App.ActiveDocument.addObject("Part::Cylinder","C1422")
App.ActiveDocument.C1422.Radius=0.576834
App.ActiveDocument.C1422.Height=20.00
App.ActiveDocument.C1422.Angle=360.00 
App.ActiveDocument.C1422.Placement=Base.Placement(Base.Vector(-44.733717,149.912735,43.516251),Base.Rotation(0.259594,-0.613083,0.000000,0.746151))
App.ActiveDocument.addObject("Part::Cylinder","C1423")
App.ActiveDocument.C1423.Radius=0.579165
App.ActiveDocument.C1423.Height=20.00
App.ActiveDocument.C1423.Angle=360.00 
App.ActiveDocument.C1423.Placement=Base.Placement(Base.Vector(-42.948743,145.587444,41.662399),Base.Rotation(0.248361,-0.548972,0.000000,0.798089))
App.ActiveDocument.addObject("Part::Cylinder","C1424")
App.ActiveDocument.C1424.Radius=0.579298
App.ActiveDocument.C1424.Height=20.00
App.ActiveDocument.C1424.Angle=360.00 
App.ActiveDocument.C1424.Placement=Base.Placement(Base.Vector(-42.404530,138.836920,37.752806),Base.Rotation(0.108470,-0.442517,0.000000,0.890176))
App.ActiveDocument.addObject("Part::Cylinder","C1425")
App.ActiveDocument.C1425.Radius=0.579788
App.ActiveDocument.C1425.Height=20.00
App.ActiveDocument.C1425.Angle=360.00 
App.ActiveDocument.C1425.Placement=Base.Placement(Base.Vector(-42.277494,133.138238,36.748188),Base.Rotation(0.062431,-0.402504,0.000000,0.913287))
App.ActiveDocument.addObject("Part::Cylinder","C1426")
App.ActiveDocument.C1426.Radius=0.581509
App.ActiveDocument.C1426.Height=20.00
App.ActiveDocument.C1426.Angle=360.00 
App.ActiveDocument.C1426.Placement=Base.Placement(Base.Vector(-41.110834,129.261642,37.165244),Base.Rotation(0.123629,-0.408175,0.000000,0.904494))
App.ActiveDocument.addObject("Part::Cylinder","C1427")
App.ActiveDocument.C1427.Radius=0.581067
App.ActiveDocument.C1427.Height=20.00
App.ActiveDocument.C1427.Angle=360.00 
App.ActiveDocument.C1427.Placement=Base.Placement(Base.Vector(-42.838063,130.083551,36.736436),Base.Rotation(0.414726,-0.223662,0.000000,0.882030))
App.ActiveDocument.addObject("Part::Cylinder","C1428")
App.ActiveDocument.C1428.Radius=0.651534
App.ActiveDocument.C1428.Height=20.00
App.ActiveDocument.C1428.Angle=360.00 
App.ActiveDocument.C1428.Placement=Base.Placement(Base.Vector(-3.967616,201.206480,45.858513),Base.Rotation(-0.565772,-0.083183,0.000000,0.820355))
App.ActiveDocument.addObject("Part::Cylinder","C1429")
App.ActiveDocument.C1429.Radius=0.645434
App.ActiveDocument.C1429.Height=20.00
App.ActiveDocument.C1429.Angle=360.00 
App.ActiveDocument.C1429.Placement=Base.Placement(Base.Vector(-8.222323,200.298593,46.122226),Base.Rotation(-0.556329,-0.131286,0.000000,0.820525))
App.ActiveDocument.addObject("Part::Cylinder","C1430")
App.ActiveDocument.C1430.Radius=0.639151
App.ActiveDocument.C1430.Height=20.00
App.ActiveDocument.C1430.Angle=360.00 
App.ActiveDocument.C1430.Placement=Base.Placement(Base.Vector(-12.080295,199.187637,46.169743),Base.Rotation(-0.545116,-0.182504,0.000000,0.818255))
App.ActiveDocument.addObject("Part::Cylinder","C1431")
App.ActiveDocument.C1431.Radius=0.634199
App.ActiveDocument.C1431.Height=20.00
App.ActiveDocument.C1431.Angle=360.00 
App.ActiveDocument.C1431.Placement=Base.Placement(Base.Vector(-16.077895,197.578331,46.552850),Base.Rotation(-0.533196,-0.209424,0.000000,0.819661))
App.ActiveDocument.addObject("Part::Cylinder","C1432")
App.ActiveDocument.C1432.Radius=0.628239
App.ActiveDocument.C1432.Height=20.00
App.ActiveDocument.C1432.Angle=360.00 
App.ActiveDocument.C1432.Placement=Base.Placement(Base.Vector(-20.046533,195.917688,46.518185),Base.Rotation(-0.518674,-0.240347,0.000000,0.820494))
App.ActiveDocument.addObject("Part::Cylinder","C1433")
App.ActiveDocument.C1433.Radius=0.621054
App.ActiveDocument.C1433.Height=20.00
App.ActiveDocument.C1433.Angle=360.00 
App.ActiveDocument.C1433.Placement=Base.Placement(Base.Vector(-23.645010,194.271130,45.968676),Base.Rotation(-0.500312,-0.285924,0.000000,0.817273))
App.ActiveDocument.addObject("Part::Cylinder","C1434")
App.ActiveDocument.C1434.Radius=0.616451
App.ActiveDocument.C1434.Height=20.00
App.ActiveDocument.C1434.Angle=360.00 
App.ActiveDocument.C1434.Placement=Base.Placement(Base.Vector(-27.125383,191.893782,46.305773),Base.Rotation(-0.469880,-0.327101,0.000000,0.819889))
App.ActiveDocument.addObject("Part::Cylinder","C1435")
App.ActiveDocument.C1435.Radius=0.609589
App.ActiveDocument.C1435.Height=20.00
App.ActiveDocument.C1435.Angle=360.00 
App.ActiveDocument.C1435.Placement=Base.Placement(Base.Vector(-30.740637,189.425604,45.740787),Base.Rotation(-0.443847,-0.363042,0.000000,0.819268))
App.ActiveDocument.addObject("Part::Cylinder","C1436")
App.ActiveDocument.C1436.Radius=0.605274
App.ActiveDocument.C1436.Height=20.00
App.ActiveDocument.C1436.Angle=360.00 
App.ActiveDocument.C1436.Placement=Base.Placement(Base.Vector(-33.710877,186.647397,45.997396),Base.Rotation(-0.405837,-0.405558,0.000000,0.819035))
App.ActiveDocument.addObject("Part::Cylinder","C1437")
App.ActiveDocument.C1437.Radius=0.601571
App.ActiveDocument.C1437.Height=20.00
App.ActiveDocument.C1437.Angle=360.00 
App.ActiveDocument.C1437.Placement=Base.Placement(Base.Vector(-36.186535,183.824815,46.229983),Base.Rotation(-0.363625,-0.445613,0.000000,0.818050))
App.ActiveDocument.addObject("Part::Cylinder","C1438")
App.ActiveDocument.C1438.Radius=0.598393
App.ActiveDocument.C1438.Height=20.00
App.ActiveDocument.C1438.Angle=360.00 
App.ActiveDocument.C1438.Placement=Base.Placement(Base.Vector(-38.439227,180.566851,46.606254),Base.Rotation(-0.326008,-0.481023,0.000000,0.813840))
App.ActiveDocument.addObject("Part::Cylinder","C1439")
App.ActiveDocument.C1439.Radius=0.594535
App.ActiveDocument.C1439.Height=20.00
App.ActiveDocument.C1439.Angle=360.00 
App.ActiveDocument.C1439.Placement=Base.Placement(Base.Vector(-40.464153,177.227944,46.637080),Base.Rotation(-0.274346,-0.521931,0.000000,0.807665))
App.ActiveDocument.addObject("Part::Cylinder","C1440")
App.ActiveDocument.C1440.Radius=0.591334
App.ActiveDocument.C1440.Height=20.00
App.ActiveDocument.C1440.Angle=360.00 
App.ActiveDocument.C1440.Placement=Base.Placement(Base.Vector(-42.005486,173.872852,46.597228),Base.Rotation(-0.227027,-0.554068,0.000000,0.800917))
App.ActiveDocument.addObject("Part::Cylinder","C1441")
App.ActiveDocument.C1441.Radius=0.589740
App.ActiveDocument.C1441.Height=20.00
App.ActiveDocument.C1441.Angle=360.00 
App.ActiveDocument.C1441.Placement=Base.Placement(Base.Vector(-43.357417,169.923657,46.944776),Base.Rotation(-0.191560,-0.571995,0.000000,0.797575))
App.ActiveDocument.addObject("Part::Cylinder","C1442")
App.ActiveDocument.C1442.Radius=0.588600
App.ActiveDocument.C1442.Height=20.00
App.ActiveDocument.C1442.Angle=360.00 
App.ActiveDocument.C1442.Placement=Base.Placement(Base.Vector(-44.371946,166.103742,47.248823),Base.Rotation(-0.142884,-0.588748,0.000000,0.795588))
App.ActiveDocument.addObject("Part::Cylinder","C1443")
App.ActiveDocument.C1443.Radius=0.587105
App.ActiveDocument.C1443.Height=20.00
App.ActiveDocument.C1443.Angle=360.00 
App.ActiveDocument.C1443.Placement=Base.Placement(Base.Vector(-45.085884,162.063501,47.374397),Base.Rotation(-0.089520,-0.608931,0.000000,0.788155))
App.ActiveDocument.addObject("Part::Cylinder","C1444")
App.ActiveDocument.C1444.Radius=0.585026
App.ActiveDocument.C1444.Height=20.00
App.ActiveDocument.C1444.Angle=360.00 
App.ActiveDocument.C1444.Placement=Base.Placement(Base.Vector(-45.545487,158.613001,47.200286),Base.Rotation(-0.030812,-0.630162,0.000000,0.775852))
App.ActiveDocument.addObject("Part::Cylinder","C1445")
App.ActiveDocument.C1445.Radius=0.586532
App.ActiveDocument.C1445.Height=20.00
App.ActiveDocument.C1445.Angle=360.00 
App.ActiveDocument.C1445.Placement=Base.Placement(Base.Vector(-45.323473,155.260971,48.063758),Base.Rotation(0.065329,-0.639445,0.000000,0.766056))
App.ActiveDocument.addObject("Part::Cylinder","C1446")
App.ActiveDocument.C1446.Radius=0.586862
App.ActiveDocument.C1446.Height=20.00
App.ActiveDocument.C1446.Angle=360.00 
App.ActiveDocument.C1446.Placement=Base.Placement(Base.Vector(-44.767919,151.800981,48.099169),Base.Rotation(0.169764,-0.634237,0.000000,0.754270))
App.ActiveDocument.addObject("Part::Cylinder","C1447")
App.ActiveDocument.C1447.Radius=0.589484
App.ActiveDocument.C1447.Height=20.00
App.ActiveDocument.C1447.Angle=360.00 
App.ActiveDocument.C1447.Placement=Base.Placement(Base.Vector(-43.625585,148.813064,48.563464),Base.Rotation(0.268833,-0.609328,0.000000,0.745955))
App.ActiveDocument.addObject("Part::Cylinder","C1448")
App.ActiveDocument.C1448.Radius=0.591578
App.ActiveDocument.C1448.Height=20.00
App.ActiveDocument.C1448.Angle=360.00 
App.ActiveDocument.C1448.Placement=Base.Placement(Base.Vector(-42.141367,146.413785,48.045360),Base.Rotation(0.395515,-0.539159,0.000000,0.743556))
App.ActiveDocument.addObject("Part::Cylinder","C1449")
App.ActiveDocument.C1449.Radius=0.592133
App.ActiveDocument.C1449.Height=20.00
App.ActiveDocument.C1449.Angle=360.00 
App.ActiveDocument.C1449.Placement=Base.Placement(Base.Vector(-39.270338,140.112189,43.516279),Base.Rotation(0.216927,-0.489765,0.000000,0.844437))
App.ActiveDocument.addObject("Part::Cylinder","C1450")
App.ActiveDocument.C1450.Radius=0.592592
App.ActiveDocument.C1450.Height=20.00
App.ActiveDocument.C1450.Angle=360.00 
App.ActiveDocument.C1450.Placement=Base.Placement(Base.Vector(-38.348671,133.632575,41.448251),Base.Rotation(0.108898,-0.446426,0.000000,0.888170))
App.ActiveDocument.addObject("Part::Cylinder","C1451")
App.ActiveDocument.C1451.Radius=0.594473
App.ActiveDocument.C1451.Height=20.00
App.ActiveDocument.C1451.Angle=360.00 
App.ActiveDocument.C1451.Placement=Base.Placement(Base.Vector(-37.801859,129.640684,41.115826),Base.Rotation(0.159309,-0.403474,0.000000,0.901016))
App.ActiveDocument.addObject("Part::Cylinder","C1452")
App.ActiveDocument.C1452.Radius=0.591870
App.ActiveDocument.C1452.Height=20.00
App.ActiveDocument.C1452.Angle=360.00 
App.ActiveDocument.C1452.Placement=Base.Placement(Base.Vector(-42.503838,132.723830,40.609476),Base.Rotation(0.547134,0.000023,0.000000,0.837045))
App.ActiveDocument.addObject("Part::Cylinder","C1453")
App.ActiveDocument.C1453.Radius=0.661584
App.ActiveDocument.C1453.Height=20.00
App.ActiveDocument.C1453.Angle=360.00 
App.ActiveDocument.C1453.Placement=Base.Placement(Base.Vector(-3.861028,199.621523,49.744220),Base.Rotation(-0.538974,-0.080213,0.000000,0.838494))
App.ActiveDocument.addObject("Part::Cylinder","C1454")
App.ActiveDocument.C1454.Radius=0.655716
App.ActiveDocument.C1454.Height=20.00
App.ActiveDocument.C1454.Angle=360.00 
App.ActiveDocument.C1454.Placement=Base.Placement(Base.Vector(-8.231791,198.606974,50.157783),Base.Rotation(-0.528670,-0.126796,0.000000,0.839304))
App.ActiveDocument.addObject("Part::Cylinder","C1455")
App.ActiveDocument.C1455.Radius=0.649339
App.ActiveDocument.C1455.Height=20.00
App.ActiveDocument.C1455.Angle=360.00 
App.ActiveDocument.C1455.Placement=Base.Placement(Base.Vector(-12.190799,197.465398,50.197927),Base.Rotation(-0.519072,-0.173712,0.000000,0.836892))
App.ActiveDocument.addObject("Part::Cylinder","C1456")
App.ActiveDocument.C1456.Radius=0.644526
App.ActiveDocument.C1456.Height=20.00
App.ActiveDocument.C1456.Angle=360.00 
App.ActiveDocument.C1456.Placement=Base.Placement(Base.Vector(-16.211025,195.706440,50.734983),Base.Rotation(-0.506239,-0.205519,0.000000,0.837547))
App.ActiveDocument.addObject("Part::Cylinder","C1457")
App.ActiveDocument.C1457.Radius=0.637867
App.ActiveDocument.C1457.Height=20.00
App.ActiveDocument.C1457.Angle=360.00 
App.ActiveDocument.C1457.Placement=Base.Placement(Base.Vector(-20.320445,193.986717,50.547440),Base.Rotation(-0.491498,-0.239991,0.000000,0.837158))
App.ActiveDocument.addObject("Part::Cylinder","C1458")
App.ActiveDocument.C1458.Radius=0.631199
App.ActiveDocument.C1458.Height=20.00
App.ActiveDocument.C1458.Angle=360.00 
App.ActiveDocument.C1458.Placement=Base.Placement(Base.Vector(-23.894465,192.211270,50.186080),Base.Rotation(-0.472208,-0.283456,0.000000,0.834669))
App.ActiveDocument.addObject("Part::Cylinder","C1459")
App.ActiveDocument.C1459.Radius=0.626697
App.ActiveDocument.C1459.Height=20.00
App.ActiveDocument.C1459.Angle=360.00 
App.ActiveDocument.C1459.Placement=Base.Placement(Base.Vector(-27.146156,189.834084,50.538406),Base.Rotation(-0.445839,-0.325023,0.000000,0.834019))
App.ActiveDocument.addObject("Part::Cylinder","C1460")
App.ActiveDocument.C1460.Radius=0.620152
App.ActiveDocument.C1460.Height=20.00
App.ActiveDocument.C1460.Angle=360.00 
App.ActiveDocument.C1460.Placement=Base.Placement(Base.Vector(-30.429775,187.533390,49.955199),Base.Rotation(-0.421789,-0.360221,0.000000,0.832066))
App.ActiveDocument.addObject("Part::Cylinder","C1461")
App.ActiveDocument.C1461.Radius=0.616312
App.ActiveDocument.C1461.Height=20.00
App.ActiveDocument.C1461.Angle=360.00 
App.ActiveDocument.C1461.Placement=Base.Placement(Base.Vector(-33.236113,184.735381,50.307048),Base.Rotation(-0.387885,-0.398233,0.000000,0.831237))
App.ActiveDocument.addObject("Part::Cylinder","C1462")
App.ActiveDocument.C1462.Radius=0.612400
App.ActiveDocument.C1462.Height=20.00
App.ActiveDocument.C1462.Angle=360.00 
App.ActiveDocument.C1462.Placement=Base.Placement(Base.Vector(-35.753377,181.722903,50.556548),Base.Rotation(-0.345729,-0.440884,0.000000,0.828307))
App.ActiveDocument.addObject("Part::Cylinder","C1463")
App.ActiveDocument.C1463.Radius=0.609579
App.ActiveDocument.C1463.Height=20.00
App.ActiveDocument.C1463.Angle=360.00 
App.ActiveDocument.C1463.Placement=Base.Placement(Base.Vector(-37.943398,178.406623,50.920022),Base.Rotation(-0.307642,-0.470281,0.000000,0.827159))
App.ActiveDocument.addObject("Part::Cylinder","C1464")
App.ActiveDocument.C1464.Radius=0.605567
App.ActiveDocument.C1464.Height=20.00
App.ActiveDocument.C1464.Angle=360.00 
App.ActiveDocument.C1464.Placement=Base.Placement(Base.Vector(-39.926822,175.122198,50.808556),Base.Rotation(-0.257764,-0.507903,0.000000,0.821944))
App.ActiveDocument.addObject("Part::Cylinder","C1465")
App.ActiveDocument.C1465.Radius=0.602634
App.ActiveDocument.C1465.Height=20.00
App.ActiveDocument.C1465.Angle=360.00 
App.ActiveDocument.C1465.Placement=Base.Placement(Base.Vector(-41.466227,171.495625,50.869730),Base.Rotation(-0.208400,-0.539169,0.000000,0.816006))
App.ActiveDocument.addObject("Part::Cylinder","C1466")
App.ActiveDocument.C1466.Radius=0.601417
App.ActiveDocument.C1466.Height=20.00
App.ActiveDocument.C1466.Angle=360.00 
App.ActiveDocument.C1466.Placement=Base.Placement(Base.Vector(-42.640855,167.811358,51.274960),Base.Rotation(-0.172573,-0.556315,0.000000,0.812854))
App.ActiveDocument.addObject("Part::Cylinder","C1467")
App.ActiveDocument.C1467.Radius=0.600242
App.ActiveDocument.C1467.Height=20.00
App.ActiveDocument.C1467.Angle=360.00 
App.ActiveDocument.C1467.Placement=Base.Placement(Base.Vector(-43.526928,164.071960,51.513576),Base.Rotation(-0.126130,-0.572871,0.000000,0.809883))
App.ActiveDocument.addObject("Part::Cylinder","C1468")
App.ActiveDocument.C1468.Radius=0.598883
App.ActiveDocument.C1468.Height=20.00
App.ActiveDocument.C1468.Angle=360.00 
App.ActiveDocument.C1468.Placement=Base.Placement(Base.Vector(-44.215665,160.004230,51.693771),Base.Rotation(-0.084866,-0.591443,0.000000,0.801868))
App.ActiveDocument.addObject("Part::Cylinder","C1469")
App.ActiveDocument.C1469.Radius=0.597828
App.ActiveDocument.C1469.Height=20.00
App.ActiveDocument.C1469.Angle=360.00 
App.ActiveDocument.C1469.Placement=Base.Placement(Base.Vector(-44.540382,156.831524,51.729368),Base.Rotation(-0.019462,-0.606517,0.000000,0.794832))
App.ActiveDocument.addObject("Part::Cylinder","C1470")
App.ActiveDocument.C1470.Radius=0.598667
App.ActiveDocument.C1470.Height=20.00
App.ActiveDocument.C1470.Angle=360.00 
App.ActiveDocument.C1470.Placement=Base.Placement(Base.Vector(-44.265511,153.672620,52.456749),Base.Rotation(0.091078,-0.620344,0.000000,0.779024))
App.ActiveDocument.addObject("Part::Cylinder","C1471")
App.ActiveDocument.C1471.Radius=0.599741
App.ActiveDocument.C1471.Height=20.00
App.ActiveDocument.C1471.Angle=360.00 
App.ActiveDocument.C1471.Placement=Base.Placement(Base.Vector(-43.601678,150.372722,52.628422),Base.Rotation(0.174814,-0.611275,0.000000,0.771869))
App.ActiveDocument.addObject("Part::Cylinder","C1472")
App.ActiveDocument.C1472.Radius=0.602075
App.ActiveDocument.C1472.Height=20.00
App.ActiveDocument.C1472.Angle=360.00 
App.ActiveDocument.C1472.Placement=Base.Placement(Base.Vector(-42.330925,147.336579,53.291815),Base.Rotation(0.277822,-0.598958,0.000000,0.751042))
App.ActiveDocument.addObject("Part::Cylinder","C1473")
App.ActiveDocument.C1473.Radius=0.603540
App.ActiveDocument.C1473.Height=20.00
App.ActiveDocument.C1473.Angle=360.00 
App.ActiveDocument.C1473.Placement=Base.Placement(Base.Vector(-40.585739,144.495700,53.680028),Base.Rotation(0.386230,-0.587231,0.000000,0.711327))
App.ActiveDocument.addObject("Part::Cylinder","C1474")
App.ActiveDocument.C1474.Radius=0.604795
App.ActiveDocument.C1474.Height=20.00
App.ActiveDocument.C1474.Angle=360.00 
App.ActiveDocument.C1474.Placement=Base.Placement(Base.Vector(-37.502669,140.990854,51.709705),Base.Rotation(0.391586,-0.558667,0.000000,0.731130))
App.ActiveDocument.addObject("Part::Cylinder","C1475")
App.ActiveDocument.C1475.Radius=0.605815
App.ActiveDocument.C1475.Height=20.00
App.ActiveDocument.C1475.Angle=360.00 
App.ActiveDocument.C1475.Placement=Base.Placement(Base.Vector(-34.715273,134.344630,48.313361),Base.Rotation(0.208503,-0.541609,0.000000,0.814362))
App.ActiveDocument.addObject("Part::Cylinder","C1476")
App.ActiveDocument.C1476.Radius=0.606933
App.ActiveDocument.C1476.Height=20.00
App.ActiveDocument.C1476.Angle=360.00 
App.ActiveDocument.C1476.Placement=Base.Placement(Base.Vector(-35.332834,132.368181,45.722646),Base.Rotation(0.336408,-0.357858,0.000000,0.871073))
App.ActiveDocument.addObject("Part::Cylinder","C1477")
App.ActiveDocument.C1477.Radius=0.671048
App.ActiveDocument.C1477.Height=20.00
App.ActiveDocument.C1477.Angle=360.00 
App.ActiveDocument.C1477.Placement=Base.Placement(Base.Vector(-4.234259,197.650080,53.686532),Base.Rotation(-0.511082,-0.079406,0.000000,0.855856))
App.ActiveDocument.addObject("Part::Cylinder","C1478")
App.ActiveDocument.C1478.Radius=0.665824
App.ActiveDocument.C1478.Height=20.00
App.ActiveDocument.C1478.Angle=360.00 
App.ActiveDocument.C1478.Placement=Base.Placement(Base.Vector(-8.404394,196.531363,54.259919),Base.Rotation(-0.504067,-0.119713,0.000000,0.855328))
App.ActiveDocument.addObject("Part::Cylinder","C1479")
App.ActiveDocument.C1479.Radius=0.659701
App.ActiveDocument.C1479.Height=20.00
App.ActiveDocument.C1479.Angle=360.00 
App.ActiveDocument.C1479.Placement=Base.Placement(Base.Vector(-12.214399,195.391406,54.348361),Base.Rotation(-0.493756,-0.168455,0.000000,0.853128))
App.ActiveDocument.addObject("Part::Cylinder","C1480")
App.ActiveDocument.C1480.Radius=0.655162
App.ActiveDocument.C1480.Height=20.00
App.ActiveDocument.C1480.Angle=360.00 
App.ActiveDocument.C1480.Placement=Base.Placement(Base.Vector(-15.983367,193.665597,54.875705),Base.Rotation(-0.482172,-0.199272,0.000000,0.853113))
App.ActiveDocument.addObject("Part::Cylinder","C1481")
App.ActiveDocument.C1481.Radius=0.648027
App.ActiveDocument.C1481.Height=20.00
App.ActiveDocument.C1481.Angle=360.00 
App.ActiveDocument.C1481.Placement=Base.Placement(Base.Vector(-20.035171,192.059649,54.472235),Base.Rotation(-0.470362,-0.232333,0.000000,0.851341))
App.ActiveDocument.addObject("Part::Cylinder","C1482")
App.ActiveDocument.C1482.Radius=0.641928
App.ActiveDocument.C1482.Height=20.00
App.ActiveDocument.C1482.Angle=360.00 
App.ActiveDocument.C1482.Placement=Base.Placement(Base.Vector(-23.571501,190.160716,54.398344),Base.Rotation(-0.452704,-0.276502,0.000000,0.847706))
App.ActiveDocument.addObject("Part::Cylinder","C1483")
App.ActiveDocument.C1483.Radius=0.637138
App.ActiveDocument.C1483.Height=20.00
App.ActiveDocument.C1483.Angle=360.00 
App.ActiveDocument.C1483.Placement=Base.Placement(Base.Vector(-26.836389,187.732260,54.730530),Base.Rotation(-0.426865,-0.321787,0.000000,0.845127))
App.ActiveDocument.addObject("Part::Cylinder","C1484")
App.ActiveDocument.C1484.Radius=0.630965
App.ActiveDocument.C1484.Height=20.00
App.ActiveDocument.C1484.Angle=360.00 
App.ActiveDocument.C1484.Placement=Base.Placement(Base.Vector(-30.136463,185.236586,54.342607),Base.Rotation(-0.403352,-0.356634,0.000000,0.842686))
App.ActiveDocument.addObject("Part::Cylinder","C1485")
App.ActiveDocument.C1485.Radius=0.627048
App.ActiveDocument.C1485.Height=20.00
App.ActiveDocument.C1485.Angle=360.00 
App.ActiveDocument.C1485.Placement=Base.Placement(Base.Vector(-32.839076,182.435866,54.643836),Base.Rotation(-0.369124,-0.395886,0.000000,0.840846))
App.ActiveDocument.addObject("Part::Cylinder","C1486")
App.ActiveDocument.C1486.Radius=0.623508
App.ActiveDocument.C1486.Height=20.00
App.ActiveDocument.C1486.Angle=360.00 
App.ActiveDocument.C1486.Placement=Base.Placement(Base.Vector(-35.245429,179.303555,54.975562),Base.Rotation(-0.324366,-0.437742,0.000000,0.838551))
App.ActiveDocument.addObject("Part::Cylinder","C1487")
App.ActiveDocument.C1487.Radius=0.620422
App.ActiveDocument.C1487.Height=20.00
App.ActiveDocument.C1487.Angle=360.00 
App.ActiveDocument.C1487.Placement=Base.Placement(Base.Vector(-37.355991,176.021977,55.140156),Base.Rotation(-0.281858,-0.466486,0.000000,0.838420))
App.ActiveDocument.addObject("Part::Cylinder","C1488")
App.ActiveDocument.C1488.Radius=0.616661
App.ActiveDocument.C1488.Height=20.00
App.ActiveDocument.C1488.Angle=360.00 
App.ActiveDocument.C1488.Placement=Base.Placement(Base.Vector(-39.217083,172.757557,54.986314),Base.Rotation(-0.235848,-0.498241,0.000000,0.834345))
App.ActiveDocument.addObject("Part::Cylinder","C1489")
App.ActiveDocument.C1489.Radius=0.614791
App.ActiveDocument.C1489.Height=20.00
App.ActiveDocument.C1489.Angle=360.00 
App.ActiveDocument.C1489.Placement=Base.Placement(Base.Vector(-40.517390,169.375554,55.213704),Base.Rotation(-0.193406,-0.520384,0.000000,0.831742))
App.ActiveDocument.addObject("Part::Cylinder","C1490")
App.ActiveDocument.C1490.Radius=0.613239
App.ActiveDocument.C1490.Height=20.00
App.ActiveDocument.C1490.Angle=360.00 
App.ActiveDocument.C1490.Placement=Base.Placement(Base.Vector(-41.721326,165.436371,55.432712),Base.Rotation(-0.147702,-0.537001,0.000000,0.830550))
App.ActiveDocument.addObject("Part::Cylinder","C1491")
App.ActiveDocument.C1491.Radius=0.612263
App.ActiveDocument.C1491.Height=20.00
App.ActiveDocument.C1491.Angle=360.00 
App.ActiveDocument.C1491.Placement=Base.Placement(Base.Vector(-42.536546,161.547748,55.664732),Base.Rotation(-0.113732,-0.548900,0.000000,0.828114))
App.ActiveDocument.addObject("Part::Cylinder","C1492")
App.ActiveDocument.C1492.Radius=0.611600
App.ActiveDocument.C1492.Height=20.00
App.ActiveDocument.C1492.Angle=360.00 
App.ActiveDocument.C1492.Placement=Base.Placement(Base.Vector(-43.034452,157.722760,56.025183),Base.Rotation(-0.068194,-0.566707,0.000000,0.821092))
App.ActiveDocument.addObject("Part::Cylinder","C1493")
App.ActiveDocument.C1493.Radius=0.610131
App.ActiveDocument.C1493.Height=20.00
App.ActiveDocument.C1493.Angle=360.00 
App.ActiveDocument.C1493.Placement=Base.Placement(Base.Vector(-43.319590,154.840478,55.887531),Base.Rotation(-0.000643,-0.582125,0.000000,0.813099))
App.ActiveDocument.addObject("Part::Cylinder","C1494")
App.ActiveDocument.C1494.Radius=0.612144
App.ActiveDocument.C1494.Height=20.00
App.ActiveDocument.C1494.Angle=360.00 
App.ActiveDocument.C1494.Placement=Base.Placement(Base.Vector(-42.849625,152.041425,56.718463),Base.Rotation(0.099757,-0.583709,0.000000,0.805812))
App.ActiveDocument.addObject("Part::Cylinder","C1495")
App.ActiveDocument.C1495.Radius=0.612496
App.ActiveDocument.C1495.Height=20.00
App.ActiveDocument.C1495.Angle=360.00 
App.ActiveDocument.C1495.Placement=Base.Placement(Base.Vector(-42.071052,148.671998,56.745734),Base.Rotation(0.171034,-0.584986,0.000000,0.792804))
App.ActiveDocument.addObject("Part::Cylinder","C1496")
App.ActiveDocument.C1496.Radius=0.614789
App.ActiveDocument.C1496.Height=20.00
App.ActiveDocument.C1496.Angle=360.00 
App.ActiveDocument.C1496.Placement=Base.Placement(Base.Vector(-40.711224,145.354348,57.515983),Base.Rotation(0.265286,-0.581737,0.000000,0.768899))
App.ActiveDocument.addObject("Part::Cylinder","C1497")
App.ActiveDocument.C1497.Radius=0.615581
App.ActiveDocument.C1497.Height=20.00
App.ActiveDocument.C1497.Angle=360.00 
App.ActiveDocument.C1497.Placement=Base.Placement(Base.Vector(-38.898719,141.938535,57.650279),Base.Rotation(0.344638,-0.586402,0.000000,0.733046))
App.ActiveDocument.addObject("Part::Cylinder","C1498")
App.ActiveDocument.C1498.Radius=0.616530
App.ActiveDocument.C1498.Height=20.00
App.ActiveDocument.C1498.Angle=360.00 
App.ActiveDocument.C1498.Placement=Base.Placement(Base.Vector(-36.733120,139.084848,58.612888),Base.Rotation(0.461272,-0.603498,0.000000,0.650398))
App.ActiveDocument.addObject("Part::Cylinder","C1499")
App.ActiveDocument.C1499.Radius=0.618698
App.ActiveDocument.C1499.Height=20.00
App.ActiveDocument.C1499.Angle=360.00 
App.ActiveDocument.C1499.Placement=Base.Placement(Base.Vector(-35.650078,136.957594,54.049466),Base.Rotation(0.488714,-0.385023,0.000000,0.782890))
App.ActiveDocument.addObject("Part::Cylinder","C1500")
App.ActiveDocument.C1500.Radius=0.618448
App.ActiveDocument.C1500.Height=20.00
App.ActiveDocument.C1500.Angle=360.00 
App.ActiveDocument.C1500.Placement=Base.Placement(Base.Vector(-37.654097,136.731250,49.756271),Base.Rotation(0.547130,-0.000000,0.000000,0.837048))
App.ActiveDocument.addObject("Part::Cylinder","C1501")
App.ActiveDocument.C1501.Radius=0.680783
App.ActiveDocument.C1501.Height=20.00
App.ActiveDocument.C1501.Angle=360.00 
App.ActiveDocument.C1501.Placement=Base.Placement(Base.Vector(-3.998799,195.588311,57.433720),Base.Rotation(-0.490960,-0.068964,0.000000,0.868448))
App.ActiveDocument.addObject("Part::Cylinder","C1502")
App.ActiveDocument.C1502.Radius=0.676215
App.ActiveDocument.C1502.Height=20.00
App.ActiveDocument.C1502.Angle=360.00 
App.ActiveDocument.C1502.Placement=Base.Placement(Base.Vector(-8.061068,194.324906,58.282944),Base.Rotation(-0.483636,-0.112878,0.000000,0.867960))
App.ActiveDocument.addObject("Part::Cylinder","C1503")
App.ActiveDocument.C1503.Radius=0.669779
App.ActiveDocument.C1503.Height=20.00
App.ActiveDocument.C1503.Angle=360.00 
App.ActiveDocument.C1503.Placement=Base.Placement(Base.Vector(-12.084200,193.147974,58.333505),Base.Rotation(-0.474419,-0.158800,0.000000,0.865858))
App.ActiveDocument.addObject("Part::Cylinder","C1504")
App.ActiveDocument.C1504.Radius=0.664918
App.ActiveDocument.C1504.Height=20.00
App.ActiveDocument.C1504.Angle=360.00 
App.ActiveDocument.C1504.Placement=Base.Placement(Base.Vector(-15.847059,191.427909,58.761465),Base.Rotation(-0.461213,-0.193955,0.000000,0.865831))
App.ActiveDocument.addObject("Part::Cylinder","C1505")
App.ActiveDocument.C1505.Radius=0.658101
App.ActiveDocument.C1505.Height=20.00
App.ActiveDocument.C1505.Angle=360.00 
App.ActiveDocument.C1505.Placement=Base.Placement(Base.Vector(-19.785965,189.792500,58.470816),Base.Rotation(-0.449935,-0.228054,0.000000,0.863452))
App.ActiveDocument.addObject("Part::Cylinder","C1506")
App.ActiveDocument.C1506.Radius=0.652211
App.ActiveDocument.C1506.Height=20.00
App.ActiveDocument.C1506.Angle=360.00 
App.ActiveDocument.C1506.Placement=Base.Placement(Base.Vector(-23.594728,187.613056,58.541686),Base.Rotation(-0.431853,-0.266249,0.000000,0.861751))
App.ActiveDocument.addObject("Part::Cylinder","C1507")
App.ActiveDocument.C1507.Radius=0.646811
App.ActiveDocument.C1507.Height=20.00
App.ActiveDocument.C1507.Angle=360.00 
App.ActiveDocument.C1507.Placement=Base.Placement(Base.Vector(-26.797869,185.225986,58.731025),Base.Rotation(-0.406494,-0.318659,0.000000,0.856282))
App.ActiveDocument.addObject("Part::Cylinder","C1508")
App.ActiveDocument.C1508.Radius=0.641751
App.ActiveDocument.C1508.Height=20.00
App.ActiveDocument.C1508.Angle=360.00 
App.ActiveDocument.C1508.Placement=Base.Placement(Base.Vector(-29.697550,182.830667,58.643164),Base.Rotation(-0.383380,-0.354066,0.000000,0.853028))
App.ActiveDocument.addObject("Part::Cylinder","C1509")
App.ActiveDocument.C1509.Radius=0.637865
App.ActiveDocument.C1509.Height=20.00
App.ActiveDocument.C1509.Angle=360.00 
App.ActiveDocument.C1509.Placement=Base.Placement(Base.Vector(-32.299901,179.986424,58.941687),Base.Rotation(-0.344568,-0.396389,0.000000,0.850969))
App.ActiveDocument.addObject("Part::Cylinder","C1510")
App.ActiveDocument.C1510.Radius=0.634934
App.ActiveDocument.C1510.Height=20.00
App.ActiveDocument.C1510.Angle=360.00 
App.ActiveDocument.C1510.Placement=Base.Placement(Base.Vector(-34.455580,176.952661,59.287152),Base.Rotation(-0.301338,-0.431408,0.000000,0.850343))
App.ActiveDocument.addObject("Part::Cylinder","C1511")
App.ActiveDocument.C1511.Radius=0.631347
App.ActiveDocument.C1511.Height=20.00
App.ActiveDocument.C1511.Angle=360.00 
App.ActiveDocument.C1511.Placement=Base.Placement(Base.Vector(-36.542586,173.602481,59.280142),Base.Rotation(-0.255664,-0.462748,0.000000,0.848823))
App.ActiveDocument.addObject("Part::Cylinder","C1512")
App.ActiveDocument.C1512.Radius=0.627963
App.ActiveDocument.C1512.Height=20.00
App.ActiveDocument.C1512.Angle=360.00 
App.ActiveDocument.C1512.Placement=Base.Placement(Base.Vector(-38.308294,170.254846,59.051866),Base.Rotation(-0.209105,-0.485987,0.000000,0.848582))
App.ActiveDocument.addObject("Part::Cylinder","C1513")
App.ActiveDocument.C1513.Radius=0.626725
App.ActiveDocument.C1513.Height=20.00
App.ActiveDocument.C1513.Angle=360.00 
App.ActiveDocument.C1513.Placement=Base.Placement(Base.Vector(-39.474528,166.771491,59.258317),Base.Rotation(-0.158914,-0.499972,0.000000,0.851337))
App.ActiveDocument.addObject("Part::Cylinder","C1514")
App.ActiveDocument.C1514.Radius=0.625738
App.ActiveDocument.C1514.Height=20.00
App.ActiveDocument.C1514.Angle=360.00 
App.ActiveDocument.C1514.Placement=Base.Placement(Base.Vector(-40.489665,162.845099,59.459908),Base.Rotation(-0.133614,-0.505941,0.000000,0.852157))
App.ActiveDocument.addObject("Part::Cylinder","C1515")
App.ActiveDocument.C1515.Radius=0.624967
App.ActiveDocument.C1515.Height=20.00
App.ActiveDocument.C1515.Angle=360.00 
App.ActiveDocument.C1515.Placement=Base.Placement(Base.Vector(-41.235837,158.826480,59.872594),Base.Rotation(-0.107879,-0.521275,0.000000,0.846543))
App.ActiveDocument.addObject("Part::Cylinder","C1516")
App.ActiveDocument.C1516.Radius=0.623649
App.ActiveDocument.C1516.Height=20.00
App.ActiveDocument.C1516.Angle=360.00 
App.ActiveDocument.C1516.Placement=Base.Placement(Base.Vector(-41.664943,155.339231,60.033576),Base.Rotation(-0.042808,-0.545342,0.000000,0.837120))
App.ActiveDocument.addObject("Part::Cylinder","C1517")
App.ActiveDocument.C1517.Radius=0.623943
App.ActiveDocument.C1517.Height=20.00
App.ActiveDocument.C1517.Angle=360.00 
App.ActiveDocument.C1517.Placement=Base.Placement(Base.Vector(-41.577308,152.737262,60.352900),Base.Rotation(0.041458,-0.554033,0.000000,0.831462))
App.ActiveDocument.addObject("Part::Cylinder","C1518")
App.ActiveDocument.C1518.Radius=0.625430
App.ActiveDocument.C1518.Height=20.00
App.ActiveDocument.C1518.Angle=360.00 
App.ActiveDocument.C1518.Placement=Base.Placement(Base.Vector(-40.852458,149.247757,60.884023),Base.Rotation(0.121942,-0.557029,0.000000,0.821492))
App.ActiveDocument.addObject("Part::Cylinder","C1519")
App.ActiveDocument.C1519.Radius=0.626555
App.ActiveDocument.C1519.Height=20.00
App.ActiveDocument.C1519.Angle=360.00 
App.ActiveDocument.C1519.Placement=Base.Placement(Base.Vector(-39.950020,146.224263,60.975831),Base.Rotation(0.194103,-0.548335,0.000000,0.813420))
App.ActiveDocument.addObject("Part::Cylinder","C1520")
App.ActiveDocument.C1520.Radius=0.627413
App.ActiveDocument.C1520.Height=20.00
App.ActiveDocument.C1520.Angle=360.00 
App.ActiveDocument.C1520.Placement=Base.Placement(Base.Vector(-38.399343,142.369541,61.076310),Base.Rotation(0.234855,-0.561855,0.000000,0.793197))
App.ActiveDocument.addObject("Part::Cylinder","C1521")
App.ActiveDocument.C1521.Radius=0.627390
App.ActiveDocument.C1521.Height=20.00
App.ActiveDocument.C1521.Angle=360.00 
App.ActiveDocument.C1521.Placement=Base.Placement(Base.Vector(-36.930105,139.164798,60.879094),Base.Rotation(0.310307,-0.563891,0.000000,0.765334))
App.ActiveDocument.addObject("Part::Cylinder","C1522")
App.ActiveDocument.C1522.Radius=0.629620
App.ActiveDocument.C1522.Height=20.00
App.ActiveDocument.C1522.Angle=360.00 
App.ActiveDocument.C1522.Placement=Base.Placement(Base.Vector(-40.642860,140.327462,58.312553),Base.Rotation(0.562851,-0.110403,0.000000,0.819152))
App.ActiveDocument.addObject("Part::Cylinder","C1523")
App.ActiveDocument.C1523.Radius=0.630852
App.ActiveDocument.C1523.Height=20.00
App.ActiveDocument.C1523.Angle=360.00 
App.ActiveDocument.C1523.Placement=Base.Placement(Base.Vector(-38.039951,139.300836,55.621261),Base.Rotation(0.547130,-0.000000,0.000000,0.837048))
App.ActiveDocument.addObject("Part::Cylinder","C1524")
App.ActiveDocument.C1524.Radius=0.630320
App.ActiveDocument.C1524.Height=20.00
App.ActiveDocument.C1524.Angle=360.00 
App.ActiveDocument.C1524.Placement=Base.Placement(Base.Vector(-33.800792,138.075820,52.825204),Base.Rotation(0.547130,-0.000000,0.000000,0.837048))
App.ActiveDocument.addObject("Part::Cylinder","C1525")
App.ActiveDocument.C1525.Radius=0.689913
App.ActiveDocument.C1525.Height=20.00
App.ActiveDocument.C1525.Angle=360.00 
App.ActiveDocument.C1525.Placement=Base.Placement(Base.Vector(-4.192300,193.172633,61.218215),Base.Rotation(-0.468248,-0.064987,0.000000,0.881204))
App.ActiveDocument.addObject("Part::Cylinder","C1526")
App.ActiveDocument.C1526.Radius=0.685897
App.ActiveDocument.C1526.Height=20.00
App.ActiveDocument.C1526.Angle=360.00 
App.ActiveDocument.C1526.Placement=Base.Placement(Base.Vector(-8.232410,191.728933,62.290825),Base.Rotation(-0.462423,-0.105720,0.000000,0.880334))
App.ActiveDocument.addObject("Part::Cylinder","C1527")
App.ActiveDocument.C1527.Radius=0.679594
App.ActiveDocument.C1527.Height=20.00
App.ActiveDocument.C1527.Angle=360.00 
App.ActiveDocument.C1527.Placement=Base.Placement(Base.Vector(-11.991594,190.631510,62.296531),Base.Rotation(-0.453285,-0.154715,0.000000,0.877836))
App.ActiveDocument.addObject("Part::Cylinder","C1528")
App.ActiveDocument.C1528.Radius=0.674389
App.ActiveDocument.C1528.Height=20.00
App.ActiveDocument.C1528.Angle=360.00 
App.ActiveDocument.C1528.Placement=Base.Placement(Base.Vector(-15.772787,188.934474,62.579236),Base.Rotation(-0.439683,-0.189675,0.000000,0.877897))
App.ActiveDocument.addObject("Part::Cylinder","C1529")
App.ActiveDocument.C1529.Radius=0.667860
App.ActiveDocument.C1529.Height=20.00
App.ActiveDocument.C1529.Angle=360.00 
App.ActiveDocument.C1529.Placement=Base.Placement(Base.Vector(-19.723468,187.204626,62.368734),Base.Rotation(-0.427700,-0.220814,0.000000,0.876535))
App.ActiveDocument.addObject("Part::Cylinder","C1530")
App.ActiveDocument.C1530.Radius=0.662572
App.ActiveDocument.C1530.Height=20.00
App.ActiveDocument.C1530.Angle=360.00 
App.ActiveDocument.C1530.Placement=Base.Placement(Base.Vector(-23.271152,185.022462,62.568252),Base.Rotation(-0.409991,-0.258822,0.000000,0.874596))
App.ActiveDocument.addObject("Part::Cylinder","C1531")
App.ActiveDocument.C1531.Radius=0.657544
App.ActiveDocument.C1531.Height=20.00
App.ActiveDocument.C1531.Angle=360.00 
App.ActiveDocument.C1531.Placement=Base.Placement(Base.Vector(-26.414216,182.666697,62.727972),Base.Rotation(-0.386403,-0.301831,0.000000,0.871545))
App.ActiveDocument.addObject("Part::Cylinder","C1532")
App.ActiveDocument.C1532.Radius=0.652336
App.ActiveDocument.C1532.Height=20.00
App.ActiveDocument.C1532.Angle=360.00 
App.ActiveDocument.C1532.Placement=Base.Placement(Base.Vector(-29.341277,180.131653,62.737903),Base.Rotation(-0.359252,-0.346006,0.000000,0.866728))
App.ActiveDocument.addObject("Part::Cylinder","C1533")
App.ActiveDocument.C1533.Radius=0.648584
App.ActiveDocument.C1533.Height=20.00
App.ActiveDocument.C1533.Angle=360.00 
App.ActiveDocument.C1533.Placement=Base.Placement(Base.Vector(-31.736865,177.302779,63.026290),Base.Rotation(-0.313716,-0.392473,0.000000,0.864608))
App.ActiveDocument.addObject("Part::Cylinder","C1534")
App.ActiveDocument.C1534.Radius=0.645833
App.ActiveDocument.C1534.Height=20.00
App.ActiveDocument.C1534.Angle=360.00 
App.ActiveDocument.C1534.Placement=Base.Placement(Base.Vector(-33.719492,174.183076,63.378443),Base.Rotation(-0.269653,-0.427121,0.000000,0.863050))
App.ActiveDocument.addObject("Part::Cylinder","C1535")
App.ActiveDocument.C1535.Radius=0.642052
App.ActiveDocument.C1535.Height=20.00
App.ActiveDocument.C1535.Angle=360.00 
App.ActiveDocument.C1535.Placement=Base.Placement(Base.Vector(-35.627944,171.080242,63.063940),Base.Rotation(-0.221334,-0.452958,0.000000,0.863620))
App.ActiveDocument.addObject("Part::Cylinder","C1536")
App.ActiveDocument.C1536.Radius=0.639745
App.ActiveDocument.C1536.Height=20.00
App.ActiveDocument.C1536.Angle=360.00 
App.ActiveDocument.C1536.Placement=Base.Placement(Base.Vector(-37.017679,168.019215,62.813138),Base.Rotation(-0.157547,-0.467079,0.000000,0.870066))
App.ActiveDocument.addObject("Part::Cylinder","C1537")
App.ActiveDocument.C1537.Radius=0.638610
App.ActiveDocument.C1537.Height=20.00
App.ActiveDocument.C1537.Angle=360.00 
App.ActiveDocument.C1537.Placement=Base.Placement(Base.Vector(-38.230471,163.842986,62.940174),Base.Rotation(-0.132929,-0.468283,0.000000,0.873522))
App.ActiveDocument.addObject("Part::Cylinder","C1538")
App.ActiveDocument.C1538.Radius=0.638546
App.ActiveDocument.C1538.Height=20.00
App.ActiveDocument.C1538.Angle=360.00 
App.ActiveDocument.C1538.Placement=Base.Placement(Base.Vector(-39.121738,159.612789,63.366702),Base.Rotation(-0.126716,-0.466204,0.000000,0.875555))
App.ActiveDocument.addObject("Part::Cylinder","C1539")
App.ActiveDocument.C1539.Radius=0.637100
App.ActiveDocument.C1539.Height=20.00
App.ActiveDocument.C1539.Angle=360.00 
App.ActiveDocument.C1539.Placement=Base.Placement(Base.Vector(-39.797242,155.871991,63.762220),Base.Rotation(-0.090690,-0.495467,0.000000,0.863880))
App.ActiveDocument.addObject("Part::Cylinder","C1540")
App.ActiveDocument.C1540.Radius=0.637025
App.ActiveDocument.C1540.Height=20.00
App.ActiveDocument.C1540.Angle=360.00 
App.ActiveDocument.C1540.Placement=Base.Placement(Base.Vector(-39.785125,152.865613,64.309793),Base.Rotation(-0.010765,-0.522144,0.000000,0.852790))
App.ActiveDocument.addObject("Part::Cylinder","C1541")
App.ActiveDocument.C1541.Radius=0.637061
App.ActiveDocument.C1541.Height=20.00
App.ActiveDocument.C1541.Angle=360.00 
App.ActiveDocument.C1541.Placement=Base.Placement(Base.Vector(-39.427202,149.982056,64.656427),Base.Rotation(0.077600,-0.538576,0.000000,0.838996))
App.ActiveDocument.addObject("Part::Cylinder","C1542")
App.ActiveDocument.C1542.Radius=0.639250
App.ActiveDocument.C1542.Height=20.00
App.ActiveDocument.C1542.Angle=360.00 
App.ActiveDocument.C1542.Placement=Base.Placement(Base.Vector(-38.229993,146.526309,65.591262),Base.Rotation(0.139756,-0.554766,0.000000,0.820185))
App.ActiveDocument.addObject("Part::Cylinder","C1543")
App.ActiveDocument.C1543.Radius=0.640060
App.ActiveDocument.C1543.Height=20.00
App.ActiveDocument.C1543.Angle=360.00 
App.ActiveDocument.C1543.Placement=Base.Placement(Base.Vector(-36.835155,142.378185,66.713108),Base.Rotation(0.144017,-0.611399,0.000000,0.778107))
App.ActiveDocument.addObject("Part::Cylinder","C1544")
App.ActiveDocument.C1544.Radius=0.639523
App.ActiveDocument.C1544.Height=20.00
App.ActiveDocument.C1544.Angle=360.00 
App.ActiveDocument.C1544.Placement=Base.Placement(Base.Vector(-38.645514,142.670133,65.343613),Base.Rotation(0.442845,-0.417797,0.000000,0.793306))
App.ActiveDocument.addObject("Part::Cylinder","C1545")
App.ActiveDocument.C1545.Radius=0.640736
App.ActiveDocument.C1545.Height=20.00
App.ActiveDocument.C1545.Angle=360.00 
App.ActiveDocument.C1545.Placement=Base.Placement(Base.Vector(-41.616059,142.354783,62.619478),Base.Rotation(0.549848,-0.027853,0.000000,0.834800))
App.ActiveDocument.addObject("Part::Cylinder","C1546")
App.ActiveDocument.C1546.Radius=0.642071
App.ActiveDocument.C1546.Height=20.00
App.ActiveDocument.C1546.Angle=360.00 
App.ActiveDocument.C1546.Placement=Base.Placement(Base.Vector(-37.875550,141.489313,60.616382),Base.Rotation(0.547130,-0.000000,0.000000,0.837048))
App.ActiveDocument.addObject("Part::Cylinder","C1547")
App.ActiveDocument.C1547.Radius=0.642838
App.ActiveDocument.C1547.Height=20.00
App.ActiveDocument.C1547.Angle=360.00 
App.ActiveDocument.C1547.Placement=Base.Placement(Base.Vector(-33.750941,140.552992,58.479263),Base.Rotation(0.547130,-0.000000,0.000000,0.837048))
App.ActiveDocument.addObject("Part::Cylinder","C1548")
App.ActiveDocument.C1548.Radius=0.641561
App.ActiveDocument.C1548.Height=20.00
App.ActiveDocument.C1548.Angle=360.00 
App.ActiveDocument.C1548.Placement=Base.Placement(Base.Vector(-29.834758,139.265151,55.539810),Base.Rotation(0.547130,-0.000000,0.000000,0.837048))
App.ActiveDocument.addObject("Part::Cylinder","C1549")
App.ActiveDocument.C1549.Radius=0.699782
App.ActiveDocument.C1549.Height=20.00
App.ActiveDocument.C1549.Angle=360.00 
App.ActiveDocument.C1549.Placement=Base.Placement(Base.Vector(-4.154507,190.388199,65.144425),Base.Rotation(-0.444629,-0.056578,0.000000,0.893926))
App.ActiveDocument.addObject("Part::Cylinder","C1550")
App.ActiveDocument.C1550.Radius=0.695434
App.ActiveDocument.C1550.Height=20.00
App.ActiveDocument.C1550.Angle=360.00 
App.ActiveDocument.C1550.Placement=Base.Placement(Base.Vector(-8.176024,189.056988,66.046534),Base.Rotation(-0.438627,-0.097027,0.000000,0.893416))
App.ActiveDocument.addObject("Part::Cylinder","C1551")
App.ActiveDocument.C1551.Radius=0.689085
App.ActiveDocument.C1551.Height=20.00
App.ActiveDocument.C1551.Angle=360.00 
App.ActiveDocument.C1551.Placement=Base.Placement(Base.Vector(-11.878530,187.950463,66.067872),Base.Rotation(-0.428359,-0.151434,0.000000,0.890829))
App.ActiveDocument.addObject("Part::Cylinder","C1552")
App.ActiveDocument.C1552.Radius=0.683485
App.ActiveDocument.C1552.Height=20.00
App.ActiveDocument.C1552.Angle=360.00 
App.ActiveDocument.C1552.Placement=Base.Placement(Base.Vector(-15.839637,186.125206,66.328995),Base.Rotation(-0.413245,-0.189719,0.000000,0.890637))
App.ActiveDocument.addObject("Part::Cylinder","C1553")
App.ActiveDocument.C1553.Radius=0.677276
App.ActiveDocument.C1553.Height=20.00
App.ActiveDocument.C1553.Angle=360.00 
App.ActiveDocument.C1553.Placement=Base.Placement(Base.Vector(-19.700482,184.388028,66.093799),Base.Rotation(-0.398187,-0.216258,0.000000,0.891448))
App.ActiveDocument.addObject("Part::Cylinder","C1554")
App.ActiveDocument.C1554.Radius=0.672299
App.ActiveDocument.C1554.Height=20.00
App.ActiveDocument.C1554.Angle=360.00 
App.ActiveDocument.C1554.Placement=Base.Placement(Base.Vector(-23.060001,182.257049,66.227208),Base.Rotation(-0.377953,-0.250308,0.000000,0.891346))
App.ActiveDocument.addObject("Part::Cylinder","C1555")
App.ActiveDocument.C1555.Radius=0.667199
App.ActiveDocument.C1555.Height=20.00
App.ActiveDocument.C1555.Angle=360.00 
App.ActiveDocument.C1555.Placement=Base.Placement(Base.Vector(-26.321952,179.699122,66.396461),Base.Rotation(-0.357607,-0.288874,0.000000,0.888070))
App.ActiveDocument.addObject("Part::Cylinder","C1556")
App.ActiveDocument.C1556.Radius=0.662272
App.ActiveDocument.C1556.Height=20.00
App.ActiveDocument.C1556.Angle=360.00 
App.ActiveDocument.C1556.Placement=Base.Placement(Base.Vector(-29.069268,177.153502,66.422641),Base.Rotation(-0.325979,-0.334468,0.000000,0.884234))
App.ActiveDocument.addObject("Part::Cylinder","C1557")
App.ActiveDocument.C1557.Radius=0.659444
App.ActiveDocument.C1557.Height=20.00
App.ActiveDocument.C1557.Angle=360.00 
App.ActiveDocument.C1557.Placement=Base.Placement(Base.Vector(-30.985527,174.477836,66.837283),Base.Rotation(-0.275989,-0.380688,0.000000,0.882557))
App.ActiveDocument.addObject("Part::Cylinder","C1558")
App.ActiveDocument.C1558.Radius=0.656077
App.ActiveDocument.C1558.Height=20.00
App.ActiveDocument.C1558.Angle=360.00 
App.ActiveDocument.C1558.Placement=Base.Placement(Base.Vector(-32.862456,171.622740,66.749433),Base.Rotation(-0.216381,-0.414204,0.000000,0.884089))
App.ActiveDocument.addObject("Part::Cylinder","C1559")
App.ActiveDocument.C1559.Radius=0.653372
App.ActiveDocument.C1559.Height=20.00
App.ActiveDocument.C1559.Angle=360.00 
App.ActiveDocument.C1559.Placement=Base.Placement(Base.Vector(-34.355309,168.639176,66.446908),Base.Rotation(-0.147631,-0.432270,0.000000,0.889578))
App.ActiveDocument.addObject("Part::Cylinder","C1560")
App.ActiveDocument.C1560.Radius=0.651712
App.ActiveDocument.C1560.Height=20.00
App.ActiveDocument.C1560.Angle=360.00 
App.ActiveDocument.C1560.Placement=Base.Placement(Base.Vector(-35.586938,164.966754,66.206554),Base.Rotation(-0.114529,-0.429124,0.000000,0.895955))
App.ActiveDocument.addObject("Part::Cylinder","C1561")
App.ActiveDocument.C1561.Radius=0.652016
App.ActiveDocument.C1561.Height=20.00
App.ActiveDocument.C1561.Angle=360.00 
App.ActiveDocument.C1561.Placement=Base.Placement(Base.Vector(-36.469328,160.922116,66.396109),Base.Rotation(-0.109248,-0.410938,0.000000,0.905094))
App.ActiveDocument.addObject("Part::Cylinder","C1562")
App.ActiveDocument.C1562.Radius=0.650617
App.ActiveDocument.C1562.Height=20.00
App.ActiveDocument.C1562.Angle=360.00 
App.ActiveDocument.C1562.Placement=Base.Placement(Base.Vector(-37.751866,156.197049,66.583625),Base.Rotation(-0.126537,-0.410124,0.000000,0.903209))
App.ActiveDocument.addObject("Part::Cylinder","C1563")
App.ActiveDocument.C1563.Radius=0.649636
App.ActiveDocument.C1563.Height=20.00
App.ActiveDocument.C1563.Angle=360.00 
App.ActiveDocument.C1563.Placement=Base.Placement(Base.Vector(-38.103106,152.984147,67.155941),Base.Rotation(-0.070850,-0.449087,0.000000,0.890675))
App.ActiveDocument.addObject("Part::Cylinder","C1564")
App.ActiveDocument.C1564.Radius=0.650267
App.ActiveDocument.C1564.Height=20.00
App.ActiveDocument.C1564.Angle=360.00 
App.ActiveDocument.C1564.Placement=Base.Placement(Base.Vector(-37.629330,149.945665,68.266305),Base.Rotation(0.007995,-0.494213,0.000000,0.869304))
App.ActiveDocument.addObject("Part::Cylinder","C1565")
App.ActiveDocument.C1565.Radius=0.651451
App.ActiveDocument.C1565.Height=20.00
App.ActiveDocument.C1565.Angle=360.00 
App.ActiveDocument.C1565.Placement=Base.Placement(Base.Vector(-36.701192,146.315524,69.490130),Base.Rotation(0.029670,-0.539477,0.000000,0.841478))
App.ActiveDocument.addObject("Part::Cylinder","C1566")
App.ActiveDocument.C1566.Radius=0.652413
App.ActiveDocument.C1566.Height=20.00
App.ActiveDocument.C1566.Angle=360.00 
App.ActiveDocument.C1566.Placement=Base.Placement(Base.Vector(-35.947849,140.357593,71.959035),Base.Rotation(-0.064748,-0.626386,0.000000,0.776820))
App.ActiveDocument.addObject("Part::Cylinder","C1567")
App.ActiveDocument.C1567.Radius=0.651320
App.ActiveDocument.C1567.Height=20.00
App.ActiveDocument.C1567.Angle=360.00 
App.ActiveDocument.C1567.Placement=Base.Placement(Base.Vector(-42.598788,145.309796,69.278962),Base.Rotation(0.528031,-0.154210,0.000000,0.835106))
App.ActiveDocument.addObject("Part::Cylinder","C1568")
App.ActiveDocument.C1568.Radius=0.708478
App.ActiveDocument.C1568.Height=20.00
App.ActiveDocument.C1568.Angle=360.00 
App.ActiveDocument.C1568.Placement=Base.Placement(Base.Vector(-4.402664,187.644319,68.470439),Base.Rotation(-0.408757,-0.043338,0.000000,0.911614))
App.ActiveDocument.addObject("Part::Cylinder","C1569")
App.ActiveDocument.C1569.Radius=0.703943
App.ActiveDocument.C1569.Height=20.00
App.ActiveDocument.C1569.Angle=360.00 
App.ActiveDocument.C1569.Placement=Base.Placement(Base.Vector(-8.288309,186.375618,69.274954),Base.Rotation(-0.404227,-0.087270,0.000000,0.910486))
App.ActiveDocument.addObject("Part::Cylinder","C1570")
App.ActiveDocument.C1570.Radius=0.697972
App.ActiveDocument.C1570.Height=20.00
App.ActiveDocument.C1570.Angle=360.00 
App.ActiveDocument.C1570.Placement=Base.Placement(Base.Vector(-11.974271,185.043996,69.514346),Base.Rotation(-0.391561,-0.146996,0.000000,0.908335))
App.ActiveDocument.addObject("Part::Cylinder","C1571")
App.ActiveDocument.C1571.Radius=0.692716
App.ActiveDocument.C1571.Height=20.00
App.ActiveDocument.C1571.Angle=360.00 
App.ActiveDocument.C1571.Placement=Base.Placement(Base.Vector(-15.795416,183.161794,69.776923),Base.Rotation(-0.374030,-0.181988,0.000000,0.909386))
App.ActiveDocument.addObject("Part::Cylinder","C1572")
App.ActiveDocument.C1572.Radius=0.686447
App.ActiveDocument.C1572.Height=20.00
App.ActiveDocument.C1572.Angle=360.00 
App.ActiveDocument.C1572.Placement=Base.Placement(Base.Vector(-19.543734,181.340604,69.600800),Base.Rotation(-0.362792,-0.212902,0.000000,0.907224))
App.ActiveDocument.addObject("Part::Cylinder","C1573")
App.ActiveDocument.C1573.Radius=0.681141
App.ActiveDocument.C1573.Height=20.00
App.ActiveDocument.C1573.Angle=360.00 
App.ActiveDocument.C1573.Placement=Base.Placement(Base.Vector(-23.008796,179.157948,69.563083),Base.Rotation(-0.344729,-0.239845,0.000000,0.907544))
App.ActiveDocument.addObject("Part::Cylinder","C1574")
App.ActiveDocument.C1574.Radius=0.676602
App.ActiveDocument.C1574.Height=20.00
App.ActiveDocument.C1574.Angle=360.00 
App.ActiveDocument.C1574.Placement=Base.Placement(Base.Vector(-26.057320,176.554938,69.763463),Base.Rotation(-0.318628,-0.276238,0.000000,0.906735))
App.ActiveDocument.addObject("Part::Cylinder","C1575")
App.ActiveDocument.C1575.Radius=0.672508
App.ActiveDocument.C1575.Height=20.00
App.ActiveDocument.C1575.Angle=360.00 
App.ActiveDocument.C1575.Placement=Base.Placement(Base.Vector(-28.473661,174.052802,69.854381),Base.Rotation(-0.271377,-0.322125,0.000000,0.906967))
App.ActiveDocument.addObject("Part::Cylinder","C1576")
App.ActiveDocument.C1576.Radius=0.669681
App.ActiveDocument.C1576.Height=20.00
App.ActiveDocument.C1576.Angle=360.00 
App.ActiveDocument.C1576.Placement=Base.Placement(Base.Vector(-30.157937,171.575789,69.959414),Base.Rotation(-0.203982,-0.362921,0.000000,0.909219))
App.ActiveDocument.addObject("Part::Cylinder","C1577")
App.ActiveDocument.C1577.Radius=0.666911
App.ActiveDocument.C1577.Height=20.00
App.ActiveDocument.C1577.Angle=360.00 
App.ActiveDocument.C1577.Placement=Base.Placement(Base.Vector(-31.553689,168.954778,69.658084),Base.Rotation(-0.129481,-0.385772,0.000000,0.913463))
App.ActiveDocument.addObject("Part::Cylinder","C1578")
App.ActiveDocument.C1578.Radius=0.665473
App.ActiveDocument.C1578.Height=20.00
App.ActiveDocument.C1578.Angle=360.00 
App.ActiveDocument.C1578.Placement=Base.Placement(Base.Vector(-32.626887,165.620559,69.434005),Base.Rotation(-0.082992,-0.383940,0.000000,0.919621))
App.ActiveDocument.addObject("Part::Cylinder","C1579")
App.ActiveDocument.C1579.Radius=0.664700
App.ActiveDocument.C1579.Height=20.00
App.ActiveDocument.C1579.Angle=360.00 
App.ActiveDocument.C1579.Placement=Base.Placement(Base.Vector(-33.442446,162.141402,69.269069),Base.Rotation(-0.068865,-0.372948,0.000000,0.925293))
App.ActiveDocument.addObject("Part::Cylinder","C1580")
App.ActiveDocument.C1580.Radius=0.664101
App.ActiveDocument.C1580.Height=20.00
App.ActiveDocument.C1580.Angle=360.00 
App.ActiveDocument.C1580.Placement=Base.Placement(Base.Vector(-34.614592,157.419791,69.212866),Base.Rotation(-0.105897,-0.347669,0.000000,0.931618))
App.ActiveDocument.addObject("Part::Cylinder","C1581")
App.ActiveDocument.C1581.Radius=0.663077
App.ActiveDocument.C1581.Height=20.00
App.ActiveDocument.C1581.Angle=360.00 
App.ActiveDocument.C1581.Placement=Base.Placement(Base.Vector(-35.944131,152.894406,69.414424),Base.Rotation(-0.116709,-0.340105,0.000000,0.933117))
App.ActiveDocument.addObject("Part::Cylinder","C1582")
App.ActiveDocument.C1582.Radius=0.662684
App.ActiveDocument.C1582.Height=20.00
App.ActiveDocument.C1582.Angle=360.00 
App.ActiveDocument.C1582.Placement=Base.Placement(Base.Vector(-36.001881,149.180437,70.451216),Base.Rotation(-0.075084,-0.394973,0.000000,0.915619))
App.ActiveDocument.addObject("Part::Cylinder","C1583")
App.ActiveDocument.C1583.Radius=0.664597
App.ActiveDocument.C1583.Height=20.00
App.ActiveDocument.C1583.Angle=360.00 
App.ActiveDocument.C1583.Placement=Base.Placement(Base.Vector(-35.399234,145.659905,71.731112),Base.Rotation(-0.063584,-0.426853,0.000000,0.902083))
App.ActiveDocument.addObject("Part::Cylinder","C1584")
App.ActiveDocument.C1584.Radius=0.664490
App.ActiveDocument.C1584.Height=20.00
App.ActiveDocument.C1584.Angle=360.00 
App.ActiveDocument.C1584.Placement=Base.Placement(Base.Vector(-35.646913,140.351135,72.986127),Base.Rotation(-0.123484,-0.464150,0.000000,0.877107))
App.ActiveDocument.addObject("Part::Cylinder","C1585")
App.ActiveDocument.C1585.Radius=0.663975
App.ActiveDocument.C1585.Height=20.00
App.ActiveDocument.C1585.Angle=360.00 
App.ActiveDocument.C1585.Placement=Base.Placement(Base.Vector(-39.239587,145.428046,71.955555),Base.Rotation(0.403824,-0.218627,0.000000,0.888329))
App.ActiveDocument.addObject("Part::Cylinder","C1586")
App.ActiveDocument.C1586.Radius=0.716200
App.ActiveDocument.C1586.Height=20.00
App.ActiveDocument.C1586.Angle=360.00 
App.ActiveDocument.C1586.Placement=Base.Placement(Base.Vector(-4.603087,184.895506,71.264943),Base.Rotation(-0.365395,-0.029855,0.000000,0.930374))
App.ActiveDocument.addObject("Part::Cylinder","C1587")
App.ActiveDocument.C1587.Radius=0.712078
App.ActiveDocument.C1587.Height=20.00
App.ActiveDocument.C1587.Angle=360.00 
App.ActiveDocument.C1587.Placement=Base.Placement(Base.Vector(-8.480676,183.469141,72.157877),Base.Rotation(-0.355868,-0.072408,0.000000,0.931727))
App.ActiveDocument.addObject("Part::Cylinder","C1588")
App.ActiveDocument.C1588.Radius=0.706241
App.ActiveDocument.C1588.Height=20.00
App.ActiveDocument.C1588.Angle=360.00 
App.ActiveDocument.C1588.Placement=Base.Placement(Base.Vector(-12.126851,181.898412,72.544986),Base.Rotation(-0.342733,-0.138960,0.000000,0.929099))
App.ActiveDocument.addObject("Part::Cylinder","C1589")
App.ActiveDocument.C1589.Radius=0.701279
App.ActiveDocument.C1589.Height=20.00
App.ActiveDocument.C1589.Angle=360.00 
App.ActiveDocument.C1589.Placement=Base.Placement(Base.Vector(-15.776422,179.948385,72.781014),Base.Rotation(-0.325178,-0.169052,0.000000,0.930420))
App.ActiveDocument.addObject("Part::Cylinder","C1590")
App.ActiveDocument.C1590.Radius=0.694664
App.ActiveDocument.C1590.Height=20.00
App.ActiveDocument.C1590.Angle=360.00 
App.ActiveDocument.C1590.Placement=Base.Placement(Base.Vector(-19.716318,177.948464,72.594257),Base.Rotation(-0.319338,-0.197472,0.000000,0.926838))
App.ActiveDocument.addObject("Part::Cylinder","C1591")
App.ActiveDocument.C1591.Radius=0.689810
App.ActiveDocument.C1591.Height=20.00
App.ActiveDocument.C1591.Angle=360.00 
App.ActiveDocument.C1591.Placement=Base.Placement(Base.Vector(-23.035706,175.519936,72.744535),Base.Rotation(-0.302640,-0.226217,0.000000,0.925870))
App.ActiveDocument.addObject("Part::Cylinder","C1592")
App.ActiveDocument.C1592.Radius=0.685759
App.ActiveDocument.C1592.Height=20.00
App.ActiveDocument.C1592.Angle=360.00 
App.ActiveDocument.C1592.Placement=Base.Placement(Base.Vector(-25.444853,173.456575,72.731556),Base.Rotation(-0.258477,-0.267240,0.000000,0.928317))
App.ActiveDocument.addObject("Part::Cylinder","C1593")
App.ActiveDocument.C1593.Radius=0.682702
App.ActiveDocument.C1593.Height=20.00
App.ActiveDocument.C1593.Angle=360.00 
App.ActiveDocument.C1593.Placement=Base.Placement(Base.Vector(-27.311645,171.017522,72.784049),Base.Rotation(-0.193400,-0.306531,0.000000,0.932006))
App.ActiveDocument.addObject("Part::Cylinder","C1594")
App.ActiveDocument.C1594.Radius=0.679938
App.ActiveDocument.C1594.Height=20.00
App.ActiveDocument.C1594.Angle=360.00 
App.ActiveDocument.C1594.Placement=Base.Placement(Base.Vector(-28.610177,168.750826,72.467116),Base.Rotation(-0.105437,-0.334085,0.000000,0.936627))
App.ActiveDocument.addObject("Part::Cylinder","C1595")
App.ActiveDocument.C1595.Radius=0.678225
App.ActiveDocument.C1595.Height=20.00
App.ActiveDocument.C1595.Angle=360.00 
App.ActiveDocument.C1595.Placement=Base.Placement(Base.Vector(-29.550627,165.570976,72.326229),Base.Rotation(-0.065104,-0.342350,0.000000,0.937314))
App.ActiveDocument.addObject("Part::Cylinder","C1596")
App.ActiveDocument.C1596.Radius=0.677066
App.ActiveDocument.C1596.Height=20.00
App.ActiveDocument.C1596.Angle=360.00 
App.ActiveDocument.C1596.Placement=Base.Placement(Base.Vector(-30.205121,162.383105,72.117215),Base.Rotation(-0.042444,-0.340930,0.000000,0.939130))
App.ActiveDocument.addObject("Part::Cylinder","C1597")
App.ActiveDocument.C1597.Radius=0.676869
App.ActiveDocument.C1597.Height=20.00
App.ActiveDocument.C1597.Angle=360.00 
App.ActiveDocument.C1597.Placement=Base.Placement(Base.Vector(-31.105219,157.876962,71.894145),Base.Rotation(-0.065292,-0.309664,0.000000,0.948602))
App.ActiveDocument.addObject("Part::Cylinder","C1598")
App.ActiveDocument.C1598.Radius=0.675426
App.ActiveDocument.C1598.Height=20.00
App.ActiveDocument.C1598.Angle=360.00 
App.ActiveDocument.C1598.Placement=Base.Placement(Base.Vector(-32.736701,152.634163,71.873143),Base.Rotation(-0.120740,-0.285552,0.000000,0.950727))
App.ActiveDocument.addObject("Part::Cylinder","C1599")
App.ActiveDocument.C1599.Radius=0.675332
App.ActiveDocument.C1599.Height=20.00
App.ActiveDocument.C1599.Angle=360.00 
App.ActiveDocument.C1599.Placement=Base.Placement(Base.Vector(-33.674995,148.258093,72.658350),Base.Rotation(-0.131735,-0.295215,0.000000,0.946305))
App.ActiveDocument.addObject("Part::Cylinder","C1600")
App.ActiveDocument.C1600.Radius=0.677120
App.ActiveDocument.C1600.Height=20.00
App.ActiveDocument.C1600.Angle=360.00 
App.ActiveDocument.C1600.Placement=Base.Placement(Base.Vector(-33.581430,144.395715,73.689307),Base.Rotation(-0.083320,-0.315882,0.000000,0.945133))
App.ActiveDocument.addObject("Part::Cylinder","C1601")
App.ActiveDocument.C1601.Radius=0.677088
App.ActiveDocument.C1601.Height=20.00
App.ActiveDocument.C1601.Angle=360.00 
App.ActiveDocument.C1601.Placement=Base.Placement(Base.Vector(-37.140320,146.824437,74.352369),Base.Rotation(0.333223,-0.144767,0.000000,0.931668))
App.ActiveDocument.addObject("Part::Cylinder","C1602")
App.ActiveDocument.C1602.Radius=0.723641
App.ActiveDocument.C1602.Height=20.00
App.ActiveDocument.C1602.Angle=360.00 
App.ActiveDocument.C1602.Placement=Base.Placement(Base.Vector(-4.844595,181.706231,73.880298),Base.Rotation(-0.313362,-0.012801,0.000000,0.949548))
App.ActiveDocument.addObject("Part::Cylinder","C1603")
App.ActiveDocument.C1603.Radius=0.719675
App.ActiveDocument.C1603.Height=20.00
App.ActiveDocument.C1603.Angle=360.00 
App.ActiveDocument.C1603.Placement=Base.Placement(Base.Vector(-8.749952,180.045388,74.892701),Base.Rotation(-0.307880,-0.054114,0.000000,0.949885))
App.ActiveDocument.addObject("Part::Cylinder","C1604")
App.ActiveDocument.C1604.Radius=0.714029
App.ActiveDocument.C1604.Height=20.00
App.ActiveDocument.C1604.Angle=360.00 
App.ActiveDocument.C1604.Placement=Base.Placement(Base.Vector(-11.988158,178.551953,75.230222),Base.Rotation(-0.298637,-0.125143,0.000000,0.946126))
App.ActiveDocument.addObject("Part::Cylinder","C1605")
App.ActiveDocument.C1605.Radius=0.708860
App.ActiveDocument.C1605.Height=20.00
App.ActiveDocument.C1605.Angle=360.00 
App.ActiveDocument.C1605.Placement=Base.Placement(Base.Vector(-15.801195,176.863381,75.144838),Base.Rotation(-0.260696,-0.147372,0.000000,0.954107))
App.ActiveDocument.addObject("Part::Cylinder","C1606")
App.ActiveDocument.C1606.Radius=0.703762
App.ActiveDocument.C1606.Height=20.00
App.ActiveDocument.C1606.Angle=360.00 
App.ActiveDocument.C1606.Placement=Base.Placement(Base.Vector(-19.540792,174.595102,75.230764),Base.Rotation(-0.255924,-0.158608,0.000000,0.953597))
App.ActiveDocument.addObject("Part::Cylinder","C1607")
App.ActiveDocument.C1607.Radius=0.698621
App.ActiveDocument.C1607.Height=20.00
App.ActiveDocument.C1607.Angle=360.00 
App.ActiveDocument.C1607.Placement=Base.Placement(Base.Vector(-22.337622,172.289260,75.318059),Base.Rotation(-0.232818,-0.210162,0.000000,0.949541))
App.ActiveDocument.addObject("Part::Cylinder","C1608")
App.ActiveDocument.C1608.Radius=0.694944
App.ActiveDocument.C1608.Height=20.00
App.ActiveDocument.C1608.Angle=360.00 
App.ActiveDocument.C1608.Placement=Base.Placement(Base.Vector(-24.240999,170.721162,74.918923),Base.Rotation(-0.149205,-0.246070,0.000000,0.957699))
App.ActiveDocument.addObject("Part::Cylinder","C1609")
App.ActiveDocument.C1609.Radius=0.691831
App.ActiveDocument.C1609.Height=20.00
App.ActiveDocument.C1609.Angle=360.00 
App.ActiveDocument.C1609.Placement=Base.Placement(Base.Vector(-25.713882,167.892354,74.725985),Base.Rotation(-0.086328,-0.274745,0.000000,0.957634))
App.ActiveDocument.addObject("Part::Cylinder","C1610")
App.ActiveDocument.C1610.Radius=0.690386
App.ActiveDocument.C1610.Height=20.00
App.ActiveDocument.C1610.Angle=360.00 
App.ActiveDocument.C1610.Placement=Base.Placement(Base.Vector(-26.504095,165.057395,74.641632),Base.Rotation(-0.052837,-0.283059,0.000000,0.957646))
App.ActiveDocument.addObject("Part::Cylinder","C1611")
App.ActiveDocument.C1611.Radius=0.688933
App.ActiveDocument.C1611.Height=20.00
App.ActiveDocument.C1611.Angle=360.00 
App.ActiveDocument.C1611.Placement=Base.Placement(Base.Vector(-27.211356,160.857144,74.365892),Base.Rotation(-0.014656,-0.283271,0.000000,0.958928))
App.ActiveDocument.addObject("Part::Cylinder","C1612")
App.ActiveDocument.C1612.Radius=0.688731
App.ActiveDocument.C1612.Height=20.00
App.ActiveDocument.C1612.Angle=360.00 
App.ActiveDocument.C1612.Placement=Base.Placement(Base.Vector(-27.986500,155.091557,74.313957),Base.Rotation(-0.067401,-0.259746,0.000000,0.963322))
App.ActiveDocument.addObject("Part::Cylinder","C1613")
App.ActiveDocument.C1613.Radius=0.686903
App.ActiveDocument.C1613.Height=20.00
App.ActiveDocument.C1613.Angle=360.00 
App.ActiveDocument.C1613.Placement=Base.Placement(Base.Vector(-29.868235,149.424998,74.537906),Base.Rotation(-0.132277,-0.244490,0.000000,0.960587))
App.ActiveDocument.addObject("Part::Cylinder","C1614")
App.ActiveDocument.C1614.Radius=0.688635
App.ActiveDocument.C1614.Height=20.00
App.ActiveDocument.C1614.Angle=360.00 
App.ActiveDocument.C1614.Placement=Base.Placement(Base.Vector(-30.627449,146.021449,75.201479),Base.Rotation(-0.089518,-0.224604,0.000000,0.970330))
App.ActiveDocument.addObject("Part::Cylinder","C1615")
App.ActiveDocument.C1615.Radius=0.688013
App.ActiveDocument.C1615.Height=20.00
App.ActiveDocument.C1615.Angle=360.00 
App.ActiveDocument.C1615.Placement=Base.Placement(Base.Vector(-31.498226,143.566604,75.111768),Base.Rotation(0.014422,-0.215235,0.000000,0.976456))
App.ActiveDocument.addObject("Part::Cylinder","C1616")
App.ActiveDocument.C1616.Radius=0.729889
App.ActiveDocument.C1616.Height=20.00
App.ActiveDocument.C1616.Angle=360.00 
App.ActiveDocument.C1616.Placement=Base.Placement(Base.Vector(-5.378054,178.290085,76.135030),Base.Rotation(-0.254078,0.007063,0.000000,0.967158))
App.ActiveDocument.addObject("Part::Cylinder","C1617")
App.ActiveDocument.C1617.Radius=0.726110
App.ActiveDocument.C1617.Height=20.00
App.ActiveDocument.C1617.Angle=360.00 
App.ActiveDocument.C1617.Placement=Base.Placement(Base.Vector(-8.988441,176.823876,76.957855),Base.Rotation(-0.242830,-0.031973,0.000000,0.969542))
App.ActiveDocument.addObject("Part::Cylinder","C1618")
App.ActiveDocument.C1618.Radius=0.720704
App.ActiveDocument.C1618.Height=20.00
App.ActiveDocument.C1618.Angle=360.00 
App.ActiveDocument.C1618.Placement=Base.Placement(Base.Vector(-11.876462,175.251348,77.305862),Base.Rotation(-0.226983,-0.115050,0.000000,0.967079))
App.ActiveDocument.addObject("Part::Cylinder","C1619")
App.ActiveDocument.C1619.Radius=0.715799
App.ActiveDocument.C1619.Height=20.00
App.ActiveDocument.C1619.Angle=360.00 
App.ActiveDocument.C1619.Placement=Base.Placement(Base.Vector(-15.233217,172.914180,77.531576),Base.Rotation(-0.232693,-0.138081,0.000000,0.962698))
App.ActiveDocument.addObject("Part::Cylinder","C1620")
App.ActiveDocument.C1620.Radius=0.710198
App.ActiveDocument.C1620.Height=20.00
App.ActiveDocument.C1620.Angle=360.00 
App.ActiveDocument.C1620.Placement=Base.Placement(Base.Vector(-18.995143,171.596963,76.874283),Base.Rotation(-0.162167,-0.146938,0.000000,0.975762))
App.ActiveDocument.addObject("Part::Cylinder","C1621")
App.ActiveDocument.C1621.Radius=0.706767
App.ActiveDocument.C1621.Height=20.00
App.ActiveDocument.C1621.Angle=360.00 
App.ActiveDocument.C1621.Placement=Base.Placement(Base.Vector(-20.995743,169.503606,76.735069),Base.Rotation(-0.105164,-0.175052,0.000000,0.978927))
App.ActiveDocument.addObject("Part::Cylinder","C1622")
App.ActiveDocument.C1622.Radius=0.703070
App.ActiveDocument.C1622.Height=20.00
App.ActiveDocument.C1622.Angle=360.00 
App.ActiveDocument.C1622.Placement=Base.Placement(Base.Vector(-22.639422,166.794236,76.507431),Base.Rotation(-0.063835,-0.206288,0.000000,0.976407))
App.ActiveDocument.addObject("Part::Cylinder","C1623")
App.ActiveDocument.C1623.Radius=0.700574
App.ActiveDocument.C1623.Height=20.00
App.ActiveDocument.C1623.Angle=360.00 
App.ActiveDocument.C1623.Placement=Base.Placement(Base.Vector(-23.669012,164.106229,76.286636),Base.Rotation(-0.029023,-0.224089,0.000000,0.974137))
App.ActiveDocument.addObject("Part::Cylinder","C1624")
App.ActiveDocument.C1624.Radius=0.699913
App.ActiveDocument.C1624.Height=20.00
App.ActiveDocument.C1624.Angle=360.00 
App.ActiveDocument.C1624.Placement=Base.Placement(Base.Vector(-24.010189,160.816773,76.230286),Base.Rotation(-0.008709,-0.226707,0.000000,0.973924))
App.ActiveDocument.addObject("Part::Cylinder","C1625")
App.ActiveDocument.C1625.Radius=0.700091
App.ActiveDocument.C1625.Height=20.00
App.ActiveDocument.C1625.Angle=360.00 
App.ActiveDocument.C1625.Placement=Base.Placement(Base.Vector(-24.088955,156.369978,76.297180),Base.Rotation(-0.035640,-0.222549,0.000000,0.974270))
App.ActiveDocument.addObject("Part::Cylinder","C1626")
App.ActiveDocument.C1626.Radius=0.698664
App.ActiveDocument.C1626.Height=20.00
App.ActiveDocument.C1626.Angle=360.00 
App.ActiveDocument.C1626.Placement=Base.Placement(Base.Vector(-25.446674,150.658272,76.498270),Base.Rotation(-0.107150,-0.214522,0.000000,0.970824))
App.ActiveDocument.addObject("Part::Cylinder","C1627")
App.ActiveDocument.C1627.Radius=0.699637
App.ActiveDocument.C1627.Height=20.00
App.ActiveDocument.C1627.Angle=360.00 
App.ActiveDocument.C1627.Placement=Base.Placement(Base.Vector(-26.102713,146.770431,77.194098),Base.Rotation(-0.101247,-0.208496,0.000000,0.972768))
App.ActiveDocument.addObject("Part::Cylinder","C1628")
App.ActiveDocument.C1628.Radius=0.699081
App.ActiveDocument.C1628.Height=20.00
App.ActiveDocument.C1628.Angle=360.00 
App.ActiveDocument.C1628.Placement=Base.Placement(Base.Vector(-27.002738,144.410978,77.212163),Base.Rotation(0.002277,-0.204400,0.000000,0.978885))
App.ActiveDocument.addObject("Part::Cylinder","C1629")
App.ActiveDocument.C1629.Radius=0.691579
App.ActiveDocument.C1629.Height=20.00
App.ActiveDocument.C1629.Angle=360.00 
App.ActiveDocument.C1629.Placement=Base.Placement(Base.Vector(-28.954989,145.167158,74.941548),Base.Rotation(0.240729,-0.142051,0.000000,0.960141))
App.ActiveDocument.addObject("Part::Cylinder","C1630")
App.ActiveDocument.C1630.Radius=0.734870
App.ActiveDocument.C1630.Height=20.00
App.ActiveDocument.C1630.Angle=360.00 
App.ActiveDocument.C1630.Placement=Base.Placement(Base.Vector(-5.594120,175.026088,77.630553),Base.Rotation(-0.175466,0.026707,0.000000,0.984123))
App.ActiveDocument.addObject("Part::Cylinder","C1631")
App.ActiveDocument.C1631.Radius=0.731020
App.ActiveDocument.C1631.Height=20.00
App.ActiveDocument.C1631.Angle=360.00 
App.ActiveDocument.C1631.Placement=Base.Placement(Base.Vector(-9.040302,173.520143,78.347485),Base.Rotation(-0.161177,-0.014983,0.000000,0.986812))
App.ActiveDocument.addObject("Part::Cylinder","C1632")
App.ActiveDocument.C1632.Radius=0.725851
App.ActiveDocument.C1632.Height=20.00
App.ActiveDocument.C1632.Angle=360.00 
App.ActiveDocument.C1632.Placement=Base.Placement(Base.Vector(-11.725287,171.944238,78.541024),Base.Rotation(-0.145246,-0.088206,0.000000,0.985456))
App.ActiveDocument.addObject("Part::Cylinder","C1633")
App.ActiveDocument.C1633.Radius=0.720287
App.ActiveDocument.C1633.Height=20.00
App.ActiveDocument.C1633.Angle=360.00 
App.ActiveDocument.C1633.Placement=Base.Placement(Base.Vector(-15.087077,170.095275,78.295816),Base.Rotation(-0.112364,-0.114742,0.000000,0.987020))
App.ActiveDocument.addObject("Part::Cylinder","C1634")
App.ActiveDocument.C1634.Radius=0.716282
App.ActiveDocument.C1634.Height=20.00
App.ActiveDocument.C1634.Angle=360.00 
App.ActiveDocument.C1634.Placement=Base.Placement(Base.Vector(-17.627050,167.651922,78.119834),Base.Rotation(-0.077720,-0.129142,0.000000,0.988576))
App.ActiveDocument.addObject("Part::Cylinder","C1635")
App.ActiveDocument.C1635.Radius=0.712393
App.ActiveDocument.C1635.Height=20.00
App.ActiveDocument.C1635.Angle=360.00 
App.ActiveDocument.C1635.Placement=Base.Placement(Base.Vector(-19.677192,164.889221,77.837214),Base.Rotation(-0.036788,-0.148740,0.000000,0.988192))
App.ActiveDocument.addObject("Part::Cylinder","C1636")
App.ActiveDocument.C1636.Radius=0.708907
App.ActiveDocument.C1636.Height=20.00
App.ActiveDocument.C1636.Angle=360.00 
App.ActiveDocument.C1636.Placement=Base.Placement(Base.Vector(-21.026647,161.538344,77.519135),Base.Rotation(-0.012658,-0.175047,0.000000,0.984479))
App.ActiveDocument.addObject("Part::Cylinder","C1637")
App.ActiveDocument.C1637.Radius=0.710892
App.ActiveDocument.C1637.Height=20.00
App.ActiveDocument.C1637.Angle=360.00 
App.ActiveDocument.C1637.Placement=Base.Placement(Base.Vector(-20.249122,157.293957,77.902797),Base.Rotation(-0.023994,-0.171948,0.000000,0.984814))
App.ActiveDocument.addObject("Part::Cylinder","C1638")
App.ActiveDocument.C1638.Radius=0.710114
App.ActiveDocument.C1638.Height=20.00
App.ActiveDocument.C1638.Angle=360.00 
App.ActiveDocument.C1638.Placement=Base.Placement(Base.Vector(-21.065385,151.596405,78.235732),Base.Rotation(-0.086281,-0.175448,0.000000,0.980701))
App.ActiveDocument.addObject("Part::Cylinder","C1639")
App.ActiveDocument.C1639.Radius=0.710114
App.ActiveDocument.C1639.Height=20.00
App.ActiveDocument.C1639.Angle=360.00 
App.ActiveDocument.C1639.Placement=Base.Placement(Base.Vector(-21.935743,147.126649,78.892057),Base.Rotation(-0.097347,-0.180473,0.000000,0.978751))
App.ActiveDocument.addObject("Part::Cylinder","C1640")
App.ActiveDocument.C1640.Radius=0.710002
App.ActiveDocument.C1640.Height=20.00
App.ActiveDocument.C1640.Angle=360.00 
App.ActiveDocument.C1640.Placement=Base.Placement(Base.Vector(-22.658527,145.452371,79.041343),Base.Rotation(0.035819,-0.176147,0.000000,0.983712))
App.ActiveDocument.addObject("Part::Cylinder","C1641")
App.ActiveDocument.C1641.Radius=0.738292
App.ActiveDocument.C1641.Height=20.00
App.ActiveDocument.C1641.Angle=360.00 
App.ActiveDocument.C1641.Placement=Base.Placement(Base.Vector(-5.720661,171.022758,78.767566),Base.Rotation(-0.110101,0.037626,0.000000,0.993208))
App.ActiveDocument.addObject("Part::Cylinder","C1642")
App.ActiveDocument.C1642.Radius=0.734089
App.ActiveDocument.C1642.Height=20.00
App.ActiveDocument.C1642.Angle=360.00 
App.ActiveDocument.C1642.Placement=Base.Placement(Base.Vector(-9.318143,169.449112,79.377777),Base.Rotation(-0.102331,0.003208,0.000000,0.994745))
App.ActiveDocument.addObject("Part::Cylinder","C1643")
App.ActiveDocument.C1643.Radius=0.728795
App.ActiveDocument.C1643.Height=20.00
App.ActiveDocument.C1643.Angle=360.00 
App.ActiveDocument.C1643.Placement=Base.Placement(Base.Vector(-11.662882,167.530325,79.480826),Base.Rotation(-0.077856,-0.083840,0.000000,0.993433))
App.ActiveDocument.addObject("Part::Cylinder","C1644")
App.ActiveDocument.C1644.Radius=0.724661
App.ActiveDocument.C1644.Height=20.00
App.ActiveDocument.C1644.Angle=360.00 
App.ActiveDocument.C1644.Placement=Base.Placement(Base.Vector(-13.969509,165.074717,79.336158),Base.Rotation(-0.051060,-0.109880,0.000000,0.992632))
App.ActiveDocument.addObject("Part::Cylinder","C1645")
App.ActiveDocument.C1645.Radius=0.720503
App.ActiveDocument.C1645.Height=20.00
App.ActiveDocument.C1645.Angle=360.00 
App.ActiveDocument.C1645.Placement=Base.Placement(Base.Vector(-16.048485,162.342259,79.020971),Base.Rotation(-0.026189,-0.131401,0.000000,0.990983))
App.ActiveDocument.addObject("Part::Cylinder","C1646")
App.ActiveDocument.C1646.Radius=0.717831
App.ActiveDocument.C1646.Height=20.00
App.ActiveDocument.C1646.Angle=360.00 
App.ActiveDocument.C1646.Placement=Base.Placement(Base.Vector(-17.263894,159.069636,78.827279),Base.Rotation(-0.019122,-0.148377,0.000000,0.988746))
App.ActiveDocument.addObject("Part::Cylinder","C1647")
App.ActiveDocument.C1647.Radius=0.720264
App.ActiveDocument.C1647.Height=20.00
App.ActiveDocument.C1647.Angle=360.00 
App.ActiveDocument.C1647.Placement=Base.Placement(Base.Vector(-16.447974,153.344343,79.508885),Base.Rotation(-0.060880,-0.148661,0.000000,0.987012))
App.ActiveDocument.addObject("Part::Cylinder","C1648")
App.ActiveDocument.C1648.Radius=0.720526
App.ActiveDocument.C1648.Height=20.00
App.ActiveDocument.C1648.Angle=360.00 
App.ActiveDocument.C1648.Placement=Base.Placement(Base.Vector(-17.337201,148.078838,80.314864),Base.Rotation(-0.082327,-0.153895,0.000000,0.984652))
App.ActiveDocument.addObject("Part::Cylinder","C1649")
App.ActiveDocument.C1649.Radius=0.721353
App.ActiveDocument.C1649.Height=20.00
App.ActiveDocument.C1649.Angle=360.00 
App.ActiveDocument.C1649.Placement=Base.Placement(Base.Vector(-17.849747,145.384155,80.796703),Base.Rotation(-0.009913,-0.149648,0.000000,0.988690))
App.ActiveDocument.addObject("Part::Cylinder","C1650")
App.ActiveDocument.C1650.Radius=0.740420
App.ActiveDocument.C1650.Height=20.00
App.ActiveDocument.C1650.Angle=360.00 
App.ActiveDocument.C1650.Placement=Base.Placement(Base.Vector(-5.771651,166.576936,79.580285),Base.Rotation(-0.066472,0.040367,0.000000,0.996971))
App.ActiveDocument.addObject("Part::Cylinder","C1651")
App.ActiveDocument.C1651.Radius=0.736478
App.ActiveDocument.C1651.Height=20.00
App.ActiveDocument.C1651.Angle=360.00 
App.ActiveDocument.C1651.Placement=Base.Placement(Base.Vector(-9.372670,164.741734,80.119279),Base.Rotation(-0.053934,0.022728,0.000000,0.998286))
App.ActiveDocument.addObject("Part::Cylinder","C1652")
App.ActiveDocument.C1652.Radius=0.731926
App.ActiveDocument.C1652.Height=20.00
App.ActiveDocument.C1652.Angle=360.00 
App.ActiveDocument.C1652.Placement=Base.Placement(Base.Vector(-11.105467,162.060256,80.189403),Base.Rotation(-0.041695,-0.064178,0.000000,0.997067))
App.ActiveDocument.addObject("Part::Cylinder","C1653")
App.ActiveDocument.C1653.Radius=0.728108
App.ActiveDocument.C1653.Height=20.00
App.ActiveDocument.C1653.Angle=360.00 
App.ActiveDocument.C1653.Placement=Base.Placement(Base.Vector(-12.598063,159.038883,80.098785),Base.Rotation(-0.034657,-0.113010,0.000000,0.992989))
App.ActiveDocument.addObject("Part::Cylinder","C1654")
App.ActiveDocument.C1654.Radius=0.729966
App.ActiveDocument.C1654.Height=20.00
App.ActiveDocument.C1654.Angle=360.00 
App.ActiveDocument.C1654.Placement=Base.Placement(Base.Vector(-12.119751,153.070864,80.828889),Base.Rotation(-0.077253,-0.118052,0.000000,0.989998))
App.ActiveDocument.addObject("Part::Cylinder","C1655")
App.ActiveDocument.C1655.Radius=0.729847
App.ActiveDocument.C1655.Height=20.00
App.ActiveDocument.C1655.Angle=360.00 
App.ActiveDocument.C1655.Placement=Base.Placement(Base.Vector(-13.280417,147.611548,81.682858),Base.Rotation(-0.088380,-0.128452,0.000000,0.987770))
App.ActiveDocument.addObject("Part::Cylinder","C1656")
App.ActiveDocument.C1656.Radius=0.729155
App.ActiveDocument.C1656.Height=20.00
App.ActiveDocument.C1656.Angle=360.00 
App.ActiveDocument.C1656.Placement=Base.Placement(Base.Vector(-13.704122,145.774657,81.448284),Base.Rotation(0.075000,-0.120453,0.000000,0.989882))
App.ActiveDocument.addObject("Part::Cylinder","C1657")
App.ActiveDocument.C1657.Radius=0.741903
App.ActiveDocument.C1657.Height=20.00
App.ActiveDocument.C1657.Angle=360.00 
App.ActiveDocument.C1657.Placement=Base.Placement(Base.Vector(-5.565957,161.766622,80.070030),Base.Rotation(-0.041676,0.040911,0.000000,0.998293))
App.ActiveDocument.addObject("Part::Cylinder","C1658")
App.ActiveDocument.C1658.Radius=0.738892
App.ActiveDocument.C1658.Height=20.00
App.ActiveDocument.C1658.Angle=360.00 
App.ActiveDocument.C1658.Placement=Base.Placement(Base.Vector(-8.513767,159.279118,80.563020),Base.Rotation(-0.041173,0.032833,0.000000,0.998612))
App.ActiveDocument.addObject("Part::Cylinder","C1659")
App.ActiveDocument.C1659.Radius=0.735986
App.ActiveDocument.C1659.Height=20.00
App.ActiveDocument.C1659.Angle=360.00 
App.ActiveDocument.C1659.Placement=Base.Placement(Base.Vector(-10.115883,156.017346,80.884474),Base.Rotation(-0.053722,-0.022288,0.000000,0.998307))
App.ActiveDocument.addObject("Part::Cylinder","C1660")
App.ActiveDocument.C1660.Radius=0.737039
App.ActiveDocument.C1660.Height=20.00
App.ActiveDocument.C1660.Angle=360.00 
App.ActiveDocument.C1660.Placement=Base.Placement(Base.Vector(-10.349995,149.312257,81.909151),Base.Rotation(-0.096893,-0.043106,0.000000,0.994361))
App.ActiveDocument.addObject("Part::Cylinder","C1661")
App.ActiveDocument.C1661.Radius=0.738246
App.ActiveDocument.C1661.Height=20.00
App.ActiveDocument.C1661.Angle=360.00 
App.ActiveDocument.C1661.Placement=Base.Placement(Base.Vector(-10.700111,150.028030,83.274236),Base.Rotation(0.204324,-0.040684,0.000000,0.978058))
App.ActiveDocument.addObject("Part::Cylinder","C1662")
App.ActiveDocument.C1662.Radius=0.743278
App.ActiveDocument.C1662.Height=20.00
App.ActiveDocument.C1662.Angle=360.00 
App.ActiveDocument.C1662.Placement=Base.Placement(Base.Vector(-5.446696,155.459507,80.565466),Base.Rotation(-0.046877,0.047385,0.000000,0.997776))
App.ActiveDocument.addObject("Part::Cylinder","C1663")
App.ActiveDocument.C1663.Radius=0.742212
App.ActiveDocument.C1663.Height=20.00
App.ActiveDocument.C1663.Angle=360.00 
App.ActiveDocument.C1663.Placement=Base.Placement(Base.Vector(-7.565993,151.750073,81.256575),Base.Rotation(-0.065685,0.062194,0.000000,0.995900))
App.ActiveDocument.addObject("Part::Cylinder","C1664")
App.ActiveDocument.C1664.Radius=0.743630
App.ActiveDocument.C1664.Height=20.00
App.ActiveDocument.C1664.Angle=360.00 
App.ActiveDocument.C1664.Placement=Base.Placement(Base.Vector(-8.099106,147.423457,81.983563),Base.Rotation(-0.052081,0.085042,0.000000,0.995015))
App.ActiveDocument.addObject("Part::Cylinder","C1665")
App.ActiveDocument.C1665.Radius=0.739176
App.ActiveDocument.C1665.Height=20.00
App.ActiveDocument.C1665.Angle=360.00 
App.ActiveDocument.C1665.Placement=Base.Placement(Base.Vector(-7.559692,152.585052,85.910497),Base.Rotation(0.525072,0.005976,0.000000,0.851037))
App.ActiveDocument.addObject("Part::Cylinder","C1666")
App.ActiveDocument.C1666.Radius=0.552865
App.ActiveDocument.C1666.Height=20.00
App.ActiveDocument.C1666.Angle=360.00 
App.ActiveDocument.C1666.Placement=Base.Placement(Base.Vector(-4.281986,206.418652,-3.803572),Base.Rotation(-0.724958,-0.061649,0.000000,0.686028))
App.ActiveDocument.addObject("Part::Cylinder","C1667")
App.ActiveDocument.C1667.Radius=0.563680
App.ActiveDocument.C1667.Height=20.00
App.ActiveDocument.C1667.Angle=360.00 
App.ActiveDocument.C1667.Placement=Base.Placement(Base.Vector(-4.435195,206.054485,-8.431249),Base.Rotation(-0.736498,-0.056624,0.000000,0.674065))
App.ActiveDocument.addObject("Part::Cylinder","C1668")
App.ActiveDocument.C1668.Radius=0.574442
App.ActiveDocument.C1668.Height=20.00
App.ActiveDocument.C1668.Angle=360.00 
App.ActiveDocument.C1668.Placement=Base.Placement(Base.Vector(-4.395650,205.564413,-12.901038),Base.Rotation(-0.748498,-0.051737,0.000000,0.661115))
App.ActiveDocument.addObject("Part::Cylinder","C1669")
App.ActiveDocument.C1669.Radius=0.585014
App.ActiveDocument.C1669.Height=20.00
App.ActiveDocument.C1669.Angle=360.00 
App.ActiveDocument.C1669.Placement=Base.Placement(Base.Vector(-4.397721,204.918107,-17.345129),Base.Rotation(-0.759765,-0.050035,0.000000,0.648270))
App.ActiveDocument.addObject("Part::Cylinder","C1670")
App.ActiveDocument.C1670.Radius=0.595674
App.ActiveDocument.C1670.Height=20.00
App.ActiveDocument.C1670.Angle=360.00 
App.ActiveDocument.C1670.Placement=Base.Placement(Base.Vector(-4.593221,204.074196,-21.903554),Base.Rotation(-0.772835,-0.051854,0.000000,0.632485))
App.ActiveDocument.addObject("Part::Cylinder","C1671")
App.ActiveDocument.C1671.Radius=0.606447
App.ActiveDocument.C1671.Height=20.00
App.ActiveDocument.C1671.Angle=360.00 
App.ActiveDocument.C1671.Placement=Base.Placement(Base.Vector(-4.398311,203.104581,-26.248281),Base.Rotation(-0.786115,-0.050921,0.000000,0.615979))
App.ActiveDocument.addObject("Part::Cylinder","C1672")
App.ActiveDocument.C1672.Radius=0.616918
App.ActiveDocument.C1672.Height=20.00
App.ActiveDocument.C1672.Angle=360.00 
App.ActiveDocument.C1672.Placement=Base.Placement(Base.Vector(-4.218827,201.973177,-30.415403),Base.Rotation(-0.800520,-0.048771,0.000000,0.597318))
App.ActiveDocument.addObject("Part::Cylinder","C1673")
App.ActiveDocument.C1673.Radius=0.626852
App.ActiveDocument.C1673.Height=20.00
App.ActiveDocument.C1673.Angle=360.00 
App.ActiveDocument.C1673.Placement=Base.Placement(Base.Vector(-4.464614,200.604350,-34.488357),Base.Rotation(-0.818811,-0.053199,0.000000,0.571593))
App.ActiveDocument.addObject("Part::Cylinder","C1674")
App.ActiveDocument.C1674.Radius=0.637068
App.ActiveDocument.C1674.Height=20.00
App.ActiveDocument.C1674.Angle=360.00 
App.ActiveDocument.C1674.Placement=Base.Placement(Base.Vector(-4.359624,199.031340,-38.302906),Base.Rotation(-0.841153,-0.053731,0.000000,0.538121))
App.ActiveDocument.addObject("Part::Cylinder","C1675")
App.ActiveDocument.C1675.Radius=0.646287
App.ActiveDocument.C1675.Height=20.00
App.ActiveDocument.C1675.Angle=360.00 
App.ActiveDocument.C1675.Placement=Base.Placement(Base.Vector(-4.483162,197.246792,-41.672293),Base.Rotation(-0.866711,-0.056112,0.000000,0.495645))
App.ActiveDocument.addObject("Part::Cylinder","C1676")
App.ActiveDocument.C1676.Radius=0.655288
App.ActiveDocument.C1676.Height=20.00
App.ActiveDocument.C1676.Angle=360.00 
App.ActiveDocument.C1676.Placement=Base.Placement(Base.Vector(-4.484507,195.101133,-44.860379),Base.Rotation(-0.891515,-0.057344,0.000000,0.449347))
App.ActiveDocument.addObject("Part::Cylinder","C1677")
App.ActiveDocument.C1677.Radius=0.663895
App.ActiveDocument.C1677.Height=20.00
App.ActiveDocument.C1677.Angle=360.00 
App.ActiveDocument.C1677.Placement=Base.Placement(Base.Vector(-4.430465,192.470353,-48.070848),Base.Rotation(-0.909591,-0.062251,0.000000,0.410814))
App.ActiveDocument.addObject("Part::Cylinder","C1678")
App.ActiveDocument.C1678.Radius=0.671910
App.ActiveDocument.C1678.Height=20.00
App.ActiveDocument.C1678.Angle=360.00 
App.ActiveDocument.C1678.Placement=Base.Placement(Base.Vector(-4.318274,189.517501,-51.236432),Base.Rotation(-0.920331,-0.064701,0.000000,0.385753))
App.ActiveDocument.addObject("Part::Cylinder","C1679")
App.ActiveDocument.C1679.Radius=0.679230
App.ActiveDocument.C1679.Height=20.00
App.ActiveDocument.C1679.Angle=360.00 
App.ActiveDocument.C1679.Placement=Base.Placement(Base.Vector(-4.488729,186.425771,-54.155651),Base.Rotation(-0.933540,-0.070982,0.000000,0.351376))
App.ActiveDocument.addObject("Part::Cylinder","C1680")
App.ActiveDocument.C1680.Radius=0.685990
App.ActiveDocument.C1680.Height=20.00
App.ActiveDocument.C1680.Angle=360.00 
App.ActiveDocument.C1680.Placement=Base.Placement(Base.Vector(-4.602257,183.262627,-56.627741),Base.Rotation(-0.950215,-0.078652,0.000000,0.301505))
App.ActiveDocument.addObject("Part::Cylinder","C1681")
App.ActiveDocument.C1681.Radius=0.691958
App.ActiveDocument.C1681.Height=20.00
App.ActiveDocument.C1681.Angle=360.00 
App.ActiveDocument.C1681.Placement=Base.Placement(Base.Vector(-4.466700,179.874250,-58.758863),Base.Rotation(-0.962041,-0.090373,0.000000,0.257507))
App.ActiveDocument.addObject("Part::Cylinder","C1682")
App.ActiveDocument.C1682.Radius=0.697079
App.ActiveDocument.C1682.Height=20.00
App.ActiveDocument.C1682.Angle=360.00 
App.ActiveDocument.C1682.Placement=Base.Placement(Base.Vector(-4.324876,176.059590,-60.777606),Base.Rotation(-0.965697,-0.122892,0.000000,0.228752))
App.ActiveDocument.addObject("Part::Cylinder","C1683")
App.ActiveDocument.C1683.Radius=0.701782
App.ActiveDocument.C1683.Height=20.00
App.ActiveDocument.C1683.Angle=360.00 
App.ActiveDocument.C1683.Placement=Base.Placement(Base.Vector(-4.268750,171.757244,-62.800442),Base.Rotation(-0.963494,-0.165292,0.000000,0.210612))
App.ActiveDocument.addObject("Part::Cylinder","C1684")
App.ActiveDocument.C1684.Radius=0.706066
App.ActiveDocument.C1684.Height=20.00
App.ActiveDocument.C1684.Angle=360.00 
App.ActiveDocument.C1684.Placement=Base.Placement(Base.Vector(-4.228814,167.488709,-64.618763),Base.Rotation(-0.960796,-0.199603,0.000000,0.192431))
App.ActiveDocument.addObject("Part::Cylinder","C1685")
App.ActiveDocument.C1685.Radius=0.709770
App.ActiveDocument.C1685.Height=20.00
App.ActiveDocument.C1685.Angle=360.00 
App.ActiveDocument.C1685.Placement=Base.Placement(Base.Vector(-4.324792,163.292653,-66.153431),Base.Rotation(-0.959985,-0.225916,0.000000,0.165504))
App.ActiveDocument.addObject("Part::Cylinder","C1686")
App.ActiveDocument.C1686.Radius=0.712869
App.ActiveDocument.C1686.Height=20.00
App.ActiveDocument.C1686.Angle=360.00 
App.ActiveDocument.C1686.Placement=Base.Placement(Base.Vector(-4.414631,159.248008,-67.370380),Base.Rotation(-0.963602,-0.229571,0.000000,0.136995))
App.ActiveDocument.addObject("Part::Cylinder","C1687")
App.ActiveDocument.C1687.Radius=0.715252
App.ActiveDocument.C1687.Height=20.00
App.ActiveDocument.C1687.Angle=360.00 
App.ActiveDocument.C1687.Placement=Base.Placement(Base.Vector(-4.574777,155.161282,-68.370081),Base.Rotation(-0.965674,-0.233788,0.000000,0.113214))
App.ActiveDocument.addObject("Part::Cylinder","C1688")
App.ActiveDocument.C1688.Radius=0.717142
App.ActiveDocument.C1688.Height=20.00
App.ActiveDocument.C1688.Angle=360.00 
App.ActiveDocument.C1688.Placement=Base.Placement(Base.Vector(-4.786273,150.785932,-69.236403),Base.Rotation(-0.960212,-0.263983,0.000000,0.091139))
App.ActiveDocument.addObject("Part::Cylinder","C1689")
App.ActiveDocument.C1689.Radius=0.718774
App.ActiveDocument.C1689.Height=20.00
App.ActiveDocument.C1689.Angle=360.00 
App.ActiveDocument.C1689.Placement=Base.Placement(Base.Vector(-4.807228,146.496109,-69.910686),Base.Rotation(-0.946107,-0.315791,0.000000,0.071819))
App.ActiveDocument.addObject("Part::Cylinder","C1690")
App.ActiveDocument.C1690.Radius=0.720015
App.ActiveDocument.C1690.Height=20.00
App.ActiveDocument.C1690.Angle=360.00 
App.ActiveDocument.C1690.Placement=Base.Placement(Base.Vector(-4.748930,142.233923,-70.392540),Base.Rotation(-0.878859,-0.474535,0.000000,0.049233))
App.ActiveDocument.addObject("Part::Cylinder","C1691")
App.ActiveDocument.C1691.Radius=0.720793
App.ActiveDocument.C1691.Height=20.00
App.ActiveDocument.C1691.Angle=360.00 
App.ActiveDocument.C1691.Placement=Base.Placement(Base.Vector(-4.652138,137.984620,-70.663101),Base.Rotation(-0.534873,-0.844454,0.000000,0.028439))
App.ActiveDocument.addObject("Part::Cylinder","C1692")
App.ActiveDocument.C1692.Radius=0.720968
App.ActiveDocument.C1692.Height=20.00
App.ActiveDocument.C1692.Angle=360.00 
App.ActiveDocument.C1692.Placement=Base.Placement(Base.Vector(-4.662513,133.734536,-70.693008),Base.Rotation(0.502960,-0.864005,0.000000,0.022966))
App.ActiveDocument.addObject("Part::Cylinder","C1693")
App.ActiveDocument.C1693.Radius=0.720644
App.ActiveDocument.C1693.Height=20.00
App.ActiveDocument.C1693.Angle=360.00 
App.ActiveDocument.C1693.Placement=Base.Placement(Base.Vector(-4.685220,129.561453,-70.472571),Base.Rotation(0.979547,-0.195176,0.000000,0.048929))
App.ActiveDocument.addObject("Part::Cylinder","C1694")
App.ActiveDocument.C1694.Radius=0.719609
App.ActiveDocument.C1694.Height=20.00
App.ActiveDocument.C1694.Angle=360.00 
App.ActiveDocument.C1694.Placement=Base.Placement(Base.Vector(-4.652947,125.417022,-69.969955),Base.Rotation(0.996284,-0.043562,0.000000,0.074295))
App.ActiveDocument.addObject("Part::Cylinder","C1695")
App.ActiveDocument.C1695.Radius=0.717138
App.ActiveDocument.C1695.Height=20.00
App.ActiveDocument.C1695.Angle=360.00 
App.ActiveDocument.C1695.Placement=Base.Placement(Base.Vector(-4.841756,121.372576,-69.169623),Base.Rotation(0.991250,-0.062683,0.000000,0.116161))
App.ActiveDocument.addObject("Part::Cylinder","C1696")
App.ActiveDocument.C1696.Radius=0.714280
App.ActiveDocument.C1696.Height=20.00
App.ActiveDocument.C1696.Angle=360.00 
App.ActiveDocument.C1696.Placement=Base.Placement(Base.Vector(-3.782901,117.617014,-68.139490),Base.Rotation(0.944298,-0.274219,0.000000,0.181950))
App.ActiveDocument.addObject("Part::Cylinder","C1697")
App.ActiveDocument.C1697.Radius=0.709829
App.ActiveDocument.C1697.Height=20.00
App.ActiveDocument.C1697.Angle=360.00 
App.ActiveDocument.C1697.Placement=Base.Placement(Base.Vector(-2.772410,114.032252,-66.822727),Base.Rotation(0.880545,-0.397132,0.000000,0.258702))
App.ActiveDocument.addObject("Part::Cylinder","C1698")
App.ActiveDocument.C1698.Radius=0.704029
App.ActiveDocument.C1698.Height=20.00
App.ActiveDocument.C1698.Angle=360.00 
App.ActiveDocument.C1698.Placement=Base.Placement(Base.Vector(-2.717615,111.070212,-64.977598),Base.Rotation(0.887215,-0.327225,0.000000,0.325228))
App.ActiveDocument.addObject("Part::Cylinder","C1699")
App.ActiveDocument.C1699.Radius=0.697445
App.ActiveDocument.C1699.Height=20.00
App.ActiveDocument.C1699.Angle=360.00 
App.ActiveDocument.C1699.Placement=Base.Placement(Base.Vector(-3.595194,108.822026,-62.920105),Base.Rotation(0.907620,-0.139261,0.000000,0.396020))
App.ActiveDocument.addObject("Part::Cylinder","C1700")
App.ActiveDocument.C1700.Radius=0.546890
App.ActiveDocument.C1700.Height=20.00
App.ActiveDocument.C1700.Angle=360.00 
App.ActiveDocument.C1700.Placement=Base.Placement(Base.Vector(-8.245134,205.906176,-4.040941),Base.Rotation(-0.714886,-0.119491,0.000000,0.688956))
App.ActiveDocument.addObject("Part::Cylinder","C1701")
App.ActiveDocument.C1701.Radius=0.557542
App.ActiveDocument.C1701.Height=20.00
App.ActiveDocument.C1701.Angle=360.00 
App.ActiveDocument.C1701.Placement=Base.Placement(Base.Vector(-8.407422,205.570857,-8.587607),Base.Rotation(-0.727307,-0.116028,0.000000,0.676434))
App.ActiveDocument.addObject("Part::Cylinder","C1702")
App.ActiveDocument.C1702.Radius=0.568658
App.ActiveDocument.C1702.Height=20.00
App.ActiveDocument.C1702.Angle=360.00 
App.ActiveDocument.C1702.Placement=Base.Placement(Base.Vector(-8.349121,205.106179,-13.185096),Base.Rotation(-0.740233,-0.111162,0.000000,0.663097))
App.ActiveDocument.addObject("Part::Cylinder","C1703")
App.ActiveDocument.C1703.Radius=0.578899
App.ActiveDocument.C1703.Height=20.00
App.ActiveDocument.C1703.Angle=360.00 
App.ActiveDocument.C1703.Placement=Base.Placement(Base.Vector(-8.420158,204.492929,-17.471786),Base.Rotation(-0.752758,-0.107014,0.000000,0.649541))
App.ActiveDocument.addObject("Part::Cylinder","C1704")
App.ActiveDocument.C1704.Radius=0.588870
App.ActiveDocument.C1704.Height=20.00
App.ActiveDocument.C1704.Angle=360.00 
App.ActiveDocument.C1704.Placement=Base.Placement(Base.Vector(-8.865411,203.634061,-21.886262),Base.Rotation(-0.765015,-0.109963,0.000000,0.634555))
App.ActiveDocument.addObject("Part::Cylinder","C1705")
App.ActiveDocument.C1705.Radius=0.600024
App.ActiveDocument.C1705.Height=20.00
App.ActiveDocument.C1705.Angle=360.00 
App.ActiveDocument.C1705.Placement=Base.Placement(Base.Vector(-8.555661,202.705457,-26.250891),Base.Rotation(-0.780051,-0.101872,0.000000,0.617367))
App.ActiveDocument.addObject("Part::Cylinder","C1706")
App.ActiveDocument.C1706.Radius=0.610278
App.ActiveDocument.C1706.Height=20.00
App.ActiveDocument.C1706.Angle=360.00 
App.ActiveDocument.C1706.Placement=Base.Placement(Base.Vector(-8.367511,201.633548,-30.302428),Base.Rotation(-0.794545,-0.097983,0.000000,0.599247))
App.ActiveDocument.addObject("Part::Cylinder","C1707")
App.ActiveDocument.C1707.Radius=0.620013
App.ActiveDocument.C1707.Height=20.00
App.ActiveDocument.C1707.Angle=360.00 
App.ActiveDocument.C1707.Placement=Base.Placement(Base.Vector(-8.664948,200.285017,-34.312017),Base.Rotation(-0.812301,-0.101259,0.000000,0.574381))
App.ActiveDocument.addObject("Part::Cylinder","C1708")
App.ActiveDocument.C1708.Radius=0.629859
App.ActiveDocument.C1708.Height=20.00
App.ActiveDocument.C1708.Angle=360.00 
App.ActiveDocument.C1708.Placement=Base.Placement(Base.Vector(-8.834743,198.708933,-38.145868),Base.Rotation(-0.833717,-0.103126,0.000000,0.542476))
App.ActiveDocument.addObject("Part::Cylinder","C1709")
App.ActiveDocument.C1709.Radius=0.639137
App.ActiveDocument.C1709.Height=20.00
App.ActiveDocument.C1709.Angle=360.00 
App.ActiveDocument.C1709.Placement=Base.Placement(Base.Vector(-9.099247,196.931039,-41.532879),Base.Rotation(-0.861077,-0.101576,0.000000,0.498226))
App.ActiveDocument.addObject("Part::Cylinder","C1710")
App.ActiveDocument.C1710.Radius=0.648039
App.ActiveDocument.C1710.Height=20.00
App.ActiveDocument.C1710.Angle=360.00 
App.ActiveDocument.C1710.Placement=Base.Placement(Base.Vector(-9.166350,194.826008,-44.703015),Base.Rotation(-0.885493,-0.097794,0.000000,0.454245))
App.ActiveDocument.addObject("Part::Cylinder","C1711")
App.ActiveDocument.C1711.Radius=0.656443
App.ActiveDocument.C1711.Height=20.00
App.ActiveDocument.C1711.Angle=360.00 
App.ActiveDocument.C1711.Placement=Base.Placement(Base.Vector(-9.133074,192.379254,-47.735839),Base.Rotation(-0.905310,-0.091861,0.000000,0.414699))
App.ActiveDocument.addObject("Part::Cylinder","C1712")
App.ActiveDocument.C1712.Radius=0.664762
App.ActiveDocument.C1712.Height=20.00
App.ActiveDocument.C1712.Angle=360.00 
App.ActiveDocument.C1712.Placement=Base.Placement(Base.Vector(-8.828522,189.502651,-50.864486),Base.Rotation(-0.917281,-0.093405,0.000000,0.387131))
App.ActiveDocument.addObject("Part::Cylinder","C1713")
App.ActiveDocument.C1713.Radius=0.671744
App.ActiveDocument.C1713.Height=20.00
App.ActiveDocument.C1713.Angle=360.00 
App.ActiveDocument.C1713.Placement=Base.Placement(Base.Vector(-9.075387,186.459777,-53.723088),Base.Rotation(-0.928713,-0.116051,0.000000,0.352170))
App.ActiveDocument.addObject("Part::Cylinder","C1714")
App.ActiveDocument.C1714.Radius=0.678205
App.ActiveDocument.C1714.Height=20.00
App.ActiveDocument.C1714.Angle=360.00 
App.ActiveDocument.C1714.Placement=Base.Placement(Base.Vector(-9.029003,183.484474,-56.094939),Base.Rotation(-0.940005,-0.147748,0.000000,0.307507))
App.ActiveDocument.addObject("Part::Cylinder","C1715")
App.ActiveDocument.C1715.Radius=0.684127
App.ActiveDocument.C1715.Height=20.00
App.ActiveDocument.C1715.Angle=360.00 
App.ActiveDocument.C1715.Placement=Base.Placement(Base.Vector(-8.778407,180.327984,-58.146393),Base.Rotation(-0.948070,-0.178560,0.000000,0.263212))
App.ActiveDocument.addObject("Part::Cylinder","C1716")
App.ActiveDocument.C1716.Radius=0.689122
App.ActiveDocument.C1716.Height=20.00
App.ActiveDocument.C1716.Angle=360.00 
App.ActiveDocument.C1716.Placement=Base.Placement(Base.Vector(-8.668964,176.693540,-60.080074),Base.Rotation(-0.947793,-0.219336,0.000000,0.231474))
App.ActiveDocument.addObject("Part::Cylinder","C1717")
App.ActiveDocument.C1717.Radius=0.694000
App.ActiveDocument.C1717.Height=20.00
App.ActiveDocument.C1717.Angle=360.00 
App.ActiveDocument.C1717.Placement=Base.Placement(Base.Vector(-8.308384,172.709683,-61.965894),Base.Rotation(-0.942452,-0.257487,0.000000,0.213270))
App.ActiveDocument.addObject("Part::Cylinder","C1718")
App.ActiveDocument.C1718.Radius=0.698029
App.ActiveDocument.C1718.Height=20.00
App.ActiveDocument.C1718.Angle=360.00 
App.ActiveDocument.C1718.Placement=Base.Placement(Base.Vector(-8.316683,168.488459,-63.756911),Base.Rotation(-0.932833,-0.299317,0.000000,0.200579))
App.ActiveDocument.addObject("Part::Cylinder","C1719")
App.ActiveDocument.C1719.Radius=0.701689
App.ActiveDocument.C1719.Height=20.00
App.ActiveDocument.C1719.Angle=360.00 
App.ActiveDocument.C1719.Placement=Base.Placement(Base.Vector(-8.361683,164.389248,-65.327729),Base.Rotation(-0.920959,-0.344972,0.000000,0.181189))
App.ActiveDocument.addObject("Part::Cylinder","C1720")
App.ActiveDocument.C1720.Radius=0.704835
App.ActiveDocument.C1720.Height=20.00
App.ActiveDocument.C1720.Angle=360.00 
App.ActiveDocument.C1720.Placement=Base.Placement(Base.Vector(-8.465419,160.318944,-66.660992),Base.Rotation(-0.906303,-0.391723,0.000000,0.158645))
App.ActiveDocument.addObject("Part::Cylinder","C1721")
App.ActiveDocument.C1721.Radius=0.707332
App.ActiveDocument.C1721.Height=20.00
App.ActiveDocument.C1721.Angle=360.00 
App.ActiveDocument.C1721.Placement=Base.Placement(Base.Vector(-8.691462,156.108763,-67.780422),Base.Rotation(-0.880341,-0.454803,0.000000,0.134732))
App.ActiveDocument.addObject("Part::Cylinder","C1722")
App.ActiveDocument.C1722.Radius=0.709412
App.ActiveDocument.C1722.Height=20.00
App.ActiveDocument.C1722.Angle=360.00 
App.ActiveDocument.C1722.Placement=Base.Placement(Base.Vector(-8.879659,151.745629,-68.711535),Base.Rotation(-0.839212,-0.532033,0.000000,0.112536))
App.ActiveDocument.addObject("Part::Cylinder","C1723")
App.ActiveDocument.C1723.Radius=0.711458
App.ActiveDocument.C1723.Height=20.00
App.ActiveDocument.C1723.Angle=360.00 
App.ActiveDocument.C1723.Placement=Base.Placement(Base.Vector(-8.763803,147.426541,-69.464160),Base.Rotation(-0.785978,-0.611076,0.000000,0.093936))
App.ActiveDocument.addObject("Part::Cylinder","C1724")
App.ActiveDocument.C1724.Radius=0.712743
App.ActiveDocument.C1724.Height=20.00
App.ActiveDocument.C1724.Angle=360.00 
App.ActiveDocument.C1724.Placement=Base.Placement(Base.Vector(-8.818685,143.089593,-69.999825),Base.Rotation(-0.664725,-0.743289,0.000000,0.075246))
App.ActiveDocument.addObject("Part::Cylinder","C1725")
App.ActiveDocument.C1725.Radius=0.713416
App.ActiveDocument.C1725.Height=20.00
App.ActiveDocument.C1725.Angle=360.00 
App.ActiveDocument.C1725.Placement=Base.Placement(Base.Vector(-8.948085,138.727046,-70.305080),Base.Rotation(-0.393200,-0.917620,0.000000,0.058026))
App.ActiveDocument.addObject("Part::Cylinder","C1726")
App.ActiveDocument.C1726.Radius=0.714235
App.ActiveDocument.C1726.Height=20.00
App.ActiveDocument.C1726.Angle=360.00 
App.ActiveDocument.C1726.Placement=Base.Placement(Base.Vector(-8.737657,134.404813,-70.424880),Base.Rotation(0.041020,-0.998139,0.000000,0.045128))
App.ActiveDocument.addObject("Part::Cylinder","C1727")
App.ActiveDocument.C1727.Radius=0.714053
App.ActiveDocument.C1727.Height=20.00
App.ActiveDocument.C1727.Angle=360.00 
App.ActiveDocument.C1727.Placement=Base.Placement(Base.Vector(-8.813654,129.985184,-70.295177),Base.Rotation(0.670664,-0.740107,0.000000,0.049513))
App.ActiveDocument.addObject("Part::Cylinder","C1728")
App.ActiveDocument.C1728.Radius=0.713143
App.ActiveDocument.C1728.Height=20.00
App.ActiveDocument.C1728.Angle=360.00 
App.ActiveDocument.C1728.Placement=Base.Placement(Base.Vector(-8.927491,125.709594,-69.906195),Base.Rotation(0.910159,-0.408216,0.000000,0.070506))
App.ActiveDocument.addObject("Part::Cylinder","C1729")
App.ActiveDocument.C1729.Radius=0.710638
App.ActiveDocument.C1729.Height=20.00
App.ActiveDocument.C1729.Angle=360.00 
App.ActiveDocument.C1729.Placement=Base.Placement(Base.Vector(-8.852155,122.227070,-69.248152),Base.Rotation(0.938098,-0.314506,0.000000,0.145116))
App.ActiveDocument.addObject("Part::Cylinder","C1730")
App.ActiveDocument.C1730.Radius=0.707440
App.ActiveDocument.C1730.Height=20.00
App.ActiveDocument.C1730.Angle=360.00 
App.ActiveDocument.C1730.Placement=Base.Placement(Base.Vector(-8.135045,118.934365,-68.162127),Base.Rotation(0.915662,-0.341614,0.000000,0.211809))
App.ActiveDocument.addObject("Part::Cylinder","C1731")
App.ActiveDocument.C1731.Radius=0.703081
App.ActiveDocument.C1731.Height=20.00
App.ActiveDocument.C1731.Angle=360.00 
App.ActiveDocument.C1731.Placement=Base.Placement(Base.Vector(-7.822145,115.387870,-66.501176),Base.Rotation(0.912229,-0.321276,0.000000,0.254203))
App.ActiveDocument.addObject("Part::Cylinder","C1732")
App.ActiveDocument.C1732.Radius=0.698058
App.ActiveDocument.C1732.Height=20.00
App.ActiveDocument.C1732.Angle=360.00 
App.ActiveDocument.C1732.Placement=Base.Placement(Base.Vector(-7.783381,111.884245,-64.468376),Base.Rotation(0.921156,-0.263732,0.000000,0.286212))
App.ActiveDocument.addObject("Part::Cylinder","C1733")
App.ActiveDocument.C1733.Radius=0.691956
App.ActiveDocument.C1733.Height=20.00
App.ActiveDocument.C1733.Angle=360.00 
App.ActiveDocument.C1733.Placement=Base.Placement(Base.Vector(-8.226080,109.038122,-62.365185),Base.Rotation(0.924775,-0.185834,0.000000,0.332048))
App.ActiveDocument.addObject("Part::Cylinder","C1734")
App.ActiveDocument.C1734.Radius=0.540553
App.ActiveDocument.C1734.Height=20.00
App.ActiveDocument.C1734.Angle=360.00 
App.ActiveDocument.C1734.Placement=Base.Placement(Base.Vector(-12.197886,205.082107,-4.102814),Base.Rotation(-0.700139,-0.174089,0.000000,0.692458))
App.ActiveDocument.addObject("Part::Cylinder","C1735")
App.ActiveDocument.C1735.Radius=0.551430
App.ActiveDocument.C1735.Height=20.00
App.ActiveDocument.C1735.Angle=360.00 
App.ActiveDocument.C1735.Placement=Base.Placement(Base.Vector(-12.316180,204.777121,-8.701780),Base.Rotation(-0.713528,-0.169215,0.000000,0.679885))
App.ActiveDocument.addObject("Part::Cylinder","C1736")
App.ActiveDocument.C1736.Radius=0.562232
App.ActiveDocument.C1736.Height=20.00
App.ActiveDocument.C1736.Angle=360.00 
App.ActiveDocument.C1736.Placement=Base.Placement(Base.Vector(-12.383648,204.326465,-13.236695),Base.Rotation(-0.726691,-0.165732,0.000000,0.666673))
App.ActiveDocument.addObject("Part::Cylinder","C1737")
App.ActiveDocument.C1737.Radius=0.572773
App.ActiveDocument.C1737.Height=20.00
App.ActiveDocument.C1737.Angle=360.00 
App.ActiveDocument.C1737.Placement=Base.Placement(Base.Vector(-12.479501,203.713130,-17.659999),Base.Rotation(-0.739985,-0.163813,0.000000,0.652371))
App.ActiveDocument.addObject("Part::Cylinder","C1738")
App.ActiveDocument.C1738.Radius=0.582856
App.ActiveDocument.C1738.Height=20.00
App.ActiveDocument.C1738.Angle=360.00 
App.ActiveDocument.C1738.Placement=Base.Placement(Base.Vector(-12.959658,202.821233,-22.131478),Base.Rotation(-0.752379,-0.167670,0.000000,0.637035))
App.ActiveDocument.addObject("Part::Cylinder","C1739")
App.ActiveDocument.C1739.Radius=0.593971
App.ActiveDocument.C1739.Height=20.00
App.ActiveDocument.C1739.Angle=360.00 
App.ActiveDocument.C1739.Placement=Base.Placement(Base.Vector(-12.455603,201.999444,-26.381261),Base.Rotation(-0.767391,-0.164631,0.000000,0.619684))
App.ActiveDocument.addObject("Part::Cylinder","C1740")
App.ActiveDocument.C1740.Radius=0.603996
App.ActiveDocument.C1740.Height=20.00
App.ActiveDocument.C1740.Angle=360.00 
App.ActiveDocument.C1740.Placement=Base.Placement(Base.Vector(-12.494362,200.876496,-30.513817),Base.Rotation(-0.780612,-0.172269,0.000000,0.600807))
App.ActiveDocument.addObject("Part::Cylinder","C1741")
App.ActiveDocument.C1741.Radius=0.613489
App.ActiveDocument.C1741.Height=20.00
App.ActiveDocument.C1741.Angle=360.00 
App.ActiveDocument.C1741.Placement=Base.Placement(Base.Vector(-12.725490,199.541119,-34.434948),Base.Rotation(-0.795860,-0.180330,0.000000,0.578003))
App.ActiveDocument.addObject("Part::Cylinder","C1742")
App.ActiveDocument.C1742.Radius=0.622941
App.ActiveDocument.C1742.Height=20.00
App.ActiveDocument.C1742.Angle=360.00 
App.ActiveDocument.C1742.Placement=Base.Placement(Base.Vector(-12.884078,198.026879,-38.115985),Base.Rotation(-0.815639,-0.185576,0.000000,0.547991))
App.ActiveDocument.addObject("Part::Cylinder","C1743")
App.ActiveDocument.C1743.Radius=0.632937
App.ActiveDocument.C1743.Height=20.00
App.ActiveDocument.C1743.Angle=360.00 
App.ActiveDocument.C1743.Placement=Base.Placement(Base.Vector(-12.800155,196.266607,-41.622874),Base.Rotation(-0.842281,-0.187544,0.000000,0.505361))
App.ActiveDocument.addObject("Part::Cylinder","C1744")
App.ActiveDocument.C1744.Radius=0.641151
App.ActiveDocument.C1744.Height=20.00
App.ActiveDocument.C1744.Angle=360.00 
App.ActiveDocument.C1744.Placement=Base.Placement(Base.Vector(-13.214894,194.177563,-44.719852),Base.Rotation(-0.864848,-0.195028,0.000000,0.462604))
App.ActiveDocument.addObject("Part::Cylinder","C1745")
App.ActiveDocument.C1745.Radius=0.650279
App.ActiveDocument.C1745.Height=20.00
App.ActiveDocument.C1745.Angle=360.00 
App.ActiveDocument.C1745.Placement=Base.Placement(Base.Vector(-12.939833,191.798080,-47.786728),Base.Rotation(-0.888780,-0.184038,0.000000,0.419761))
App.ActiveDocument.addObject("Part::Cylinder","C1746")
App.ActiveDocument.C1746.Radius=0.657532
App.ActiveDocument.C1746.Height=20.00
App.ActiveDocument.C1746.Angle=360.00 
App.ActiveDocument.C1746.Placement=Base.Placement(Base.Vector(-13.172709,189.009645,-50.717795),Base.Rotation(-0.899739,-0.198248,0.000000,0.388802))
App.ActiveDocument.addObject("Part::Cylinder","C1747")
App.ActiveDocument.C1747.Radius=0.664766
App.ActiveDocument.C1747.Height=20.00
App.ActiveDocument.C1747.Angle=360.00 
App.ActiveDocument.C1747.Placement=Base.Placement(Base.Vector(-13.074258,186.100789,-53.425286),Base.Rotation(-0.907964,-0.228611,0.000000,0.351196))
App.ActiveDocument.addObject("Part::Cylinder","C1748")
App.ActiveDocument.C1748.Radius=0.670987
App.ActiveDocument.C1748.Height=20.00
App.ActiveDocument.C1748.Angle=360.00 
App.ActiveDocument.C1748.Placement=Base.Placement(Base.Vector(-13.175191,183.012092,-55.784767),Base.Rotation(-0.913674,-0.262467,0.000000,0.310339))
App.ActiveDocument.addObject("Part::Cylinder","C1749")
App.ActiveDocument.C1749.Radius=0.677078
App.ActiveDocument.C1749.Height=20.00
App.ActiveDocument.C1749.Angle=360.00 
App.ActiveDocument.C1749.Placement=Base.Placement(Base.Vector(-13.036016,179.651980,-57.914435),Base.Rotation(-0.916319,-0.300826,0.000000,0.264317))
App.ActiveDocument.addObject("Part::Cylinder","C1750")
App.ActiveDocument.C1750.Radius=0.682074
App.ActiveDocument.C1750.Height=20.00
App.ActiveDocument.C1750.Angle=360.00 
App.ActiveDocument.C1750.Placement=Base.Placement(Base.Vector(-12.949429,176.024415,-59.797941),Base.Rotation(-0.914195,-0.331227,0.000000,0.233528))
App.ActiveDocument.addObject("Part::Cylinder","C1751")
App.ActiveDocument.C1751.Radius=0.687064
App.ActiveDocument.C1751.Height=20.00
App.ActiveDocument.C1751.Angle=360.00 
App.ActiveDocument.C1751.Placement=Base.Placement(Base.Vector(-12.571284,172.041886,-61.655351),Base.Rotation(-0.908848,-0.357901,0.000000,0.214247))
App.ActiveDocument.addObject("Part::Cylinder","C1752")
App.ActiveDocument.C1752.Radius=0.690648
App.ActiveDocument.C1752.Height=20.00
App.ActiveDocument.C1752.Angle=360.00 
App.ActiveDocument.C1752.Placement=Base.Placement(Base.Vector(-12.685054,167.885147,-63.340253),Base.Rotation(-0.887082,-0.414875,0.000000,0.202398))
App.ActiveDocument.addObject("Part::Cylinder","C1753")
App.ActiveDocument.C1753.Radius=0.694008
App.ActiveDocument.C1753.Height=20.00
App.ActiveDocument.C1753.Angle=360.00 
App.ActiveDocument.C1753.Placement=Base.Placement(Base.Vector(-12.831276,163.598372,-64.903083),Base.Rotation(-0.859164,-0.476074,0.000000,0.187592))
App.ActiveDocument.addObject("Part::Cylinder","C1754")
App.ActiveDocument.C1754.Radius=0.697366
App.ActiveDocument.C1754.Height=20.00
App.ActiveDocument.C1754.Angle=360.00 
App.ActiveDocument.C1754.Placement=Base.Placement(Base.Vector(-12.719662,159.440173,-66.255312),Base.Rotation(-0.817092,-0.551632,0.000000,0.167516))
App.ActiveDocument.addObject("Part::Cylinder","C1755")
App.ActiveDocument.C1755.Radius=0.699705
App.ActiveDocument.C1755.Height=20.00
App.ActiveDocument.C1755.Angle=360.00 
App.ActiveDocument.C1755.Placement=Base.Placement(Base.Vector(-12.857726,155.256717,-67.340603),Base.Rotation(-0.753544,-0.639917,0.000000,0.150590))
App.ActiveDocument.addObject("Part::Cylinder","C1756")
App.ActiveDocument.C1756.Radius=0.701673
App.ActiveDocument.C1756.Height=20.00
App.ActiveDocument.C1756.Angle=360.00 
App.ActiveDocument.C1756.Placement=Base.Placement(Base.Vector(-12.880641,151.118097,-68.216297),Base.Rotation(-0.670820,-0.728801,0.000000,0.137290))
App.ActiveDocument.addObject("Part::Cylinder","C1757")
App.ActiveDocument.C1757.Radius=0.703359
App.ActiveDocument.C1757.Height=20.00
App.ActiveDocument.C1757.Angle=360.00 
App.ActiveDocument.C1757.Placement=Base.Placement(Base.Vector(-12.907861,146.693094,-68.947687),Base.Rotation(-0.565141,-0.815559,0.000000,0.124415))
App.ActiveDocument.addObject("Part::Cylinder","C1758")
App.ActiveDocument.C1758.Radius=0.704715
App.ActiveDocument.C1758.Height=20.00
App.ActiveDocument.C1758.Angle=360.00 
App.ActiveDocument.C1758.Placement=Base.Placement(Base.Vector(-12.893273,142.362406,-69.470116),Base.Rotation(-0.416591,-0.902338,0.000000,0.110625))
App.ActiveDocument.addObject("Part::Cylinder","C1759")
App.ActiveDocument.C1759.Radius=0.705617
App.ActiveDocument.C1759.Height=20.00
App.ActiveDocument.C1759.Angle=360.00 
App.ActiveDocument.C1759.Placement=Base.Placement(Base.Vector(-12.854244,137.972794,-69.792491),Base.Rotation(-0.249790,-0.962965,0.000000,0.101510))
App.ActiveDocument.addObject("Part::Cylinder","C1760")
App.ActiveDocument.C1760.Radius=0.706485
App.ActiveDocument.C1760.Height=20.00
App.ActiveDocument.C1760.Angle=360.00 
App.ActiveDocument.C1760.Placement=Base.Placement(Base.Vector(-12.638608,133.584853,-69.938631),Base.Rotation(0.013624,-0.995709,0.000000,0.091535))
App.ActiveDocument.addObject("Part::Cylinder","C1761")
App.ActiveDocument.C1761.Radius=0.706298
App.ActiveDocument.C1761.Height=20.00
App.ActiveDocument.C1761.Angle=360.00 
App.ActiveDocument.C1761.Placement=Base.Placement(Base.Vector(-12.882158,129.271617,-69.791845),Base.Rotation(0.340270,-0.936763,0.000000,0.081797))
App.ActiveDocument.addObject("Part::Cylinder","C1762")
App.ActiveDocument.C1762.Radius=0.705385
App.ActiveDocument.C1762.Height=20.00
App.ActiveDocument.C1762.Angle=360.00 
App.ActiveDocument.C1762.Placement=Base.Placement(Base.Vector(-12.624729,125.457126,-69.490109),Base.Rotation(0.700896,-0.702827,0.000000,0.121567))
App.ActiveDocument.addObject("Part::Cylinder","C1763")
App.ActiveDocument.C1763.Radius=0.702077
App.ActiveDocument.C1763.Height=20.00
App.ActiveDocument.C1763.Angle=360.00 
App.ActiveDocument.C1763.Placement=Base.Placement(Base.Vector(-12.452147,122.278766,-68.659243),Base.Rotation(0.820817,-0.534721,0.000000,0.200832))
App.ActiveDocument.addObject("Part::Cylinder","C1764")
App.ActiveDocument.C1764.Radius=0.698335
App.ActiveDocument.C1764.Height=20.00
App.ActiveDocument.C1764.Angle=360.00 
App.ActiveDocument.C1764.Placement=Base.Placement(Base.Vector(-12.149270,118.677314,-67.203112),Base.Rotation(0.850824,-0.466613,0.000000,0.241599))
App.ActiveDocument.addObject("Part::Cylinder","C1765")
App.ActiveDocument.C1765.Radius=0.693664
App.ActiveDocument.C1765.Height=20.00
App.ActiveDocument.C1765.Angle=360.00 
App.ActiveDocument.C1765.Placement=Base.Placement(Base.Vector(-12.142579,114.939885,-65.334924),Base.Rotation(0.866886,-0.420846,0.000000,0.267203))
App.ActiveDocument.addObject("Part::Cylinder","C1766")
App.ActiveDocument.C1766.Radius=0.688741
App.ActiveDocument.C1766.Height=20.00
App.ActiveDocument.C1766.Angle=360.00 
App.ActiveDocument.C1766.Placement=Base.Placement(Base.Vector(-12.028275,111.494308,-63.361469),Base.Rotation(0.874149,-0.385679,0.000000,0.295152))
App.ActiveDocument.addObject("Part::Cylinder","C1767")
App.ActiveDocument.C1767.Radius=0.682470
App.ActiveDocument.C1767.Height=20.00
App.ActiveDocument.C1767.Angle=360.00 
App.ActiveDocument.C1767.Placement=Base.Placement(Base.Vector(-12.283563,108.413427,-61.073384),Base.Rotation(0.893664,-0.292134,0.000000,0.340621))
App.ActiveDocument.addObject("Part::Cylinder","C1768")
App.ActiveDocument.C1768.Radius=0.534569
App.ActiveDocument.C1768.Height=20.00
App.ActiveDocument.C1768.Angle=360.00 
App.ActiveDocument.C1768.Placement=Base.Placement(Base.Vector(-16.274023,203.922018,-4.306241),Base.Rotation(-0.684479,-0.217591,0.000000,0.695804))
App.ActiveDocument.addObject("Part::Cylinder","C1769")
App.ActiveDocument.C1769.Radius=0.544846
App.ActiveDocument.C1769.Height=20.00
App.ActiveDocument.C1769.Angle=360.00 
App.ActiveDocument.C1769.Placement=Base.Placement(Base.Vector(-16.512667,203.623176,-8.757208),Base.Rotation(-0.696366,-0.217467,0.000000,0.683946))
App.ActiveDocument.addObject("Part::Cylinder","C1770")
App.ActiveDocument.C1770.Radius=0.555622
App.ActiveDocument.C1770.Height=20.00
App.ActiveDocument.C1770.Angle=360.00 
App.ActiveDocument.C1770.Placement=Base.Placement(Base.Vector(-16.602328,203.201339,-13.272129),Base.Rotation(-0.710488,-0.215101,0.000000,0.670029))
App.ActiveDocument.addObject("Part::Cylinder","C1771")
App.ActiveDocument.C1771.Radius=0.565993
App.ActiveDocument.C1771.Height=20.00
App.ActiveDocument.C1771.Angle=360.00 
App.ActiveDocument.C1771.Placement=Base.Placement(Base.Vector(-16.517013,202.689975,-17.500856),Base.Rotation(-0.724176,-0.213755,0.000000,0.655651))
App.ActiveDocument.addObject("Part::Cylinder","C1772")
App.ActiveDocument.C1772.Radius=0.575705
App.ActiveDocument.C1772.Height=20.00
App.ActiveDocument.C1772.Angle=360.00 
App.ActiveDocument.C1772.Placement=Base.Placement(Base.Vector(-17.003174,201.812628,-21.845350),Base.Rotation(-0.734542,-0.226719,0.000000,0.639567))
App.ActiveDocument.addObject("Part::Cylinder","C1773")
App.ActiveDocument.C1773.Radius=0.587239
App.ActiveDocument.C1773.Height=20.00
App.ActiveDocument.C1773.Angle=360.00 
App.ActiveDocument.C1773.Placement=Base.Placement(Base.Vector(-16.522998,201.008435,-26.216789),Base.Rotation(-0.752585,-0.219323,0.000000,0.620897))
App.ActiveDocument.addObject("Part::Cylinder","C1774")
App.ActiveDocument.C1774.Radius=0.597097
App.ActiveDocument.C1774.Height=20.00
App.ActiveDocument.C1774.Angle=360.00 
App.ActiveDocument.C1774.Placement=Base.Placement(Base.Vector(-16.776375,199.802182,-30.392799),Base.Rotation(-0.765329,-0.228320,0.000000,0.601782))
App.ActiveDocument.addObject("Part::Cylinder","C1775")
App.ActiveDocument.C1775.Radius=0.607185
App.ActiveDocument.C1775.Height=20.00
App.ActiveDocument.C1775.Angle=360.00 
App.ActiveDocument.C1775.Placement=Base.Placement(Base.Vector(-16.875493,198.404895,-34.496324),Base.Rotation(-0.780012,-0.237260,0.000000,0.579041))
App.ActiveDocument.addObject("Part::Cylinder","C1776")
App.ActiveDocument.C1776.Radius=0.616589
App.ActiveDocument.C1776.Height=20.00
App.ActiveDocument.C1776.Angle=360.00 
App.ActiveDocument.C1776.Placement=Base.Placement(Base.Vector(-17.012376,196.872587,-38.150770),Base.Rotation(-0.798313,-0.248180,0.000000,0.548729))
App.ActiveDocument.addObject("Part::Cylinder","C1777")
App.ActiveDocument.C1777.Radius=0.626508
App.ActiveDocument.C1777.Height=20.00
App.ActiveDocument.C1777.Angle=360.00 
App.ActiveDocument.C1777.Placement=Base.Placement(Base.Vector(-16.860061,195.139417,-41.648238),Base.Rotation(-0.821935,-0.255829,0.000000,0.508895))
App.ActiveDocument.addObject("Part::Cylinder","C1778")
App.ActiveDocument.C1778.Radius=0.635401
App.ActiveDocument.C1778.Height=20.00
App.ActiveDocument.C1778.Angle=360.00 
App.ActiveDocument.C1778.Placement=Base.Placement(Base.Vector(-17.287451,192.822901,-45.020474),Base.Rotation(-0.843092,-0.272008,0.000000,0.463904))
App.ActiveDocument.addObject("Part::Cylinder","C1779")
App.ActiveDocument.C1779.Radius=0.643938
App.ActiveDocument.C1779.Height=20.00
App.ActiveDocument.C1779.Angle=360.00 
App.ActiveDocument.C1779.Placement=Base.Placement(Base.Vector(-17.006936,190.604741,-47.902259),Base.Rotation(-0.862445,-0.277497,0.000000,0.423301))
App.ActiveDocument.addObject("Part::Cylinder","C1780")
App.ActiveDocument.C1780.Radius=0.650582
App.ActiveDocument.C1780.Height=20.00
App.ActiveDocument.C1780.Angle=360.00 
App.ActiveDocument.C1780.Placement=Base.Placement(Base.Vector(-17.438361,187.860404,-50.629358),Base.Rotation(-0.869068,-0.306523,0.000000,0.388284))
App.ActiveDocument.addObject("Part::Cylinder","C1781")
App.ActiveDocument.C1781.Radius=0.657727
App.ActiveDocument.C1781.Height=20.00
App.ActiveDocument.C1781.Angle=360.00 
App.ActiveDocument.C1781.Placement=Base.Placement(Base.Vector(-17.386794,184.920850,-53.264573),Base.Rotation(-0.874363,-0.335884,0.000000,0.350244))
App.ActiveDocument.addObject("Part::Cylinder","C1782")
App.ActiveDocument.C1782.Radius=0.663896
App.ActiveDocument.C1782.Height=20.00
App.ActiveDocument.C1782.Angle=360.00 
App.ActiveDocument.C1782.Placement=Base.Placement(Base.Vector(-17.496085,181.729363,-55.590740),Base.Rotation(-0.872407,-0.378091,0.000000,0.309765))
App.ActiveDocument.addObject("Part::Cylinder","C1783")
App.ActiveDocument.C1783.Radius=0.669803
App.ActiveDocument.C1783.Height=20.00
App.ActiveDocument.C1783.Angle=360.00 
App.ActiveDocument.C1783.Placement=Base.Placement(Base.Vector(-17.298854,178.414577,-57.642466),Base.Rotation(-0.864884,-0.423929,0.000000,0.268811))
App.ActiveDocument.addObject("Part::Cylinder","C1784")
App.ActiveDocument.C1784.Radius=0.675038
App.ActiveDocument.C1784.Height=20.00
App.ActiveDocument.C1784.Angle=360.00 
App.ActiveDocument.C1784.Placement=Base.Placement(Base.Vector(-17.096572,174.655426,-59.555477),Base.Rotation(-0.849573,-0.470966,0.000000,0.237523))
App.ActiveDocument.addObject("Part::Cylinder","C1785")
App.ActiveDocument.C1785.Radius=0.679847
App.ActiveDocument.C1785.Height=20.00
App.ActiveDocument.C1785.Angle=360.00 
App.ActiveDocument.C1785.Placement=Base.Placement(Base.Vector(-16.661176,170.721043,-61.340199),Base.Rotation(-0.828013,-0.515613,0.000000,0.220313))
App.ActiveDocument.addObject("Part::Cylinder","C1786")
App.ActiveDocument.C1786.Radius=0.682735
App.ActiveDocument.C1786.Height=20.00
App.ActiveDocument.C1786.Angle=360.00 
App.ActiveDocument.C1786.Placement=Base.Placement(Base.Vector(-16.836992,166.769940,-62.821006),Base.Rotation(-0.782602,-0.585089,0.000000,0.212612))
App.ActiveDocument.addObject("Part::Cylinder","C1787")
App.ActiveDocument.C1787.Radius=0.685867
App.ActiveDocument.C1787.Height=20.00
App.ActiveDocument.C1787.Angle=360.00 
App.ActiveDocument.C1787.Placement=Base.Placement(Base.Vector(-16.772443,162.608804,-64.276014),Base.Rotation(-0.716451,-0.667090,0.000000,0.204177))
App.ActiveDocument.addObject("Part::Cylinder","C1788")
App.ActiveDocument.C1788.Radius=0.688889
App.ActiveDocument.C1788.Height=20.00
App.ActiveDocument.C1788.Angle=360.00 
App.ActiveDocument.C1788.Placement=Base.Placement(Base.Vector(-16.571446,158.437932,-65.571473),Base.Rotation(-0.634306,-0.748073,0.000000,0.195046))
App.ActiveDocument.addObject("Part::Cylinder","C1789")
App.ActiveDocument.C1789.Radius=0.691327
App.ActiveDocument.C1789.Height=20.00
App.ActiveDocument.C1789.Angle=360.00 
App.ActiveDocument.C1789.Placement=Base.Placement(Base.Vector(-16.410702,154.268653,-66.641943),Base.Rotation(-0.530945,-0.826279,0.000000,0.188045))
App.ActiveDocument.addObject("Part::Cylinder","C1790")
App.ActiveDocument.C1790.Radius=0.693013
App.ActiveDocument.C1790.Height=20.00
App.ActiveDocument.C1790.Angle=360.00 
App.ActiveDocument.C1790.Placement=Base.Placement(Base.Vector(-16.424478,150.092332,-67.451533),Base.Rotation(-0.440586,-0.878773,0.000000,0.183420))
App.ActiveDocument.addObject("Part::Cylinder","C1791")
App.ActiveDocument.C1791.Radius=0.694343
App.ActiveDocument.C1791.Height=20.00
App.ActiveDocument.C1791.Angle=360.00 
App.ActiveDocument.C1791.Placement=Base.Placement(Base.Vector(-16.430526,145.672611,-68.126847),Base.Rotation(-0.336616,-0.923950,0.000000,0.181678))
App.ActiveDocument.addObject("Part::Cylinder","C1792")
App.ActiveDocument.C1792.Radius=0.695703
App.ActiveDocument.C1792.Height=20.00
App.ActiveDocument.C1792.Angle=360.00 
App.ActiveDocument.C1792.Placement=Base.Placement(Base.Vector(-16.311993,141.435825,-68.639713),Base.Rotation(-0.242547,-0.953972,0.000000,0.176376))
App.ActiveDocument.addObject("Part::Cylinder","C1793")
App.ActiveDocument.C1793.Radius=0.696426
App.ActiveDocument.C1793.Height=20.00
App.ActiveDocument.C1793.Angle=360.00 
App.ActiveDocument.C1793.Placement=Base.Placement(Base.Vector(-16.335202,137.133101,-68.912490),Base.Rotation(-0.124997,-0.977489,0.000000,0.169974))
App.ActiveDocument.addObject("Part::Cylinder","C1794")
App.ActiveDocument.C1794.Radius=0.696949
App.ActiveDocument.C1794.Height=20.00
App.ActiveDocument.C1794.Angle=360.00 
App.ActiveDocument.C1794.Placement=Base.Placement(Base.Vector(-16.215453,132.952115,-69.015672),Base.Rotation(0.037765,-0.985440,0.000000,0.165773))
App.ActiveDocument.addObject("Part::Cylinder","C1795")
App.ActiveDocument.C1795.Radius=0.696924
App.ActiveDocument.C1795.Height=20.00
App.ActiveDocument.C1795.Angle=360.00 
App.ActiveDocument.C1795.Placement=Base.Placement(Base.Vector(-16.027831,128.583758,-68.903113),Base.Rotation(0.240181,-0.955788,0.000000,0.169651))
App.ActiveDocument.addObject("Part::Cylinder","C1796")
App.ActiveDocument.C1796.Radius=0.695601
App.ActiveDocument.C1796.Height=20.00
App.ActiveDocument.C1796.Angle=360.00 
App.ActiveDocument.C1796.Placement=Base.Placement(Base.Vector(-15.797489,125.348600,-68.558292),Base.Rotation(0.545696,-0.811398,0.000000,0.209401))
App.ActiveDocument.addObject("Part::Cylinder","C1797")
App.ActiveDocument.C1797.Radius=0.691854
App.ActiveDocument.C1797.Height=20.00
App.ActiveDocument.C1797.Angle=360.00 
App.ActiveDocument.C1797.Placement=Base.Placement(Base.Vector(-15.993023,121.943053,-67.372805),Base.Rotation(0.693743,-0.674611,0.000000,0.252229))
App.ActiveDocument.addObject("Part::Cylinder","C1798")
App.ActiveDocument.C1798.Radius=0.688265
App.ActiveDocument.C1798.Height=20.00
App.ActiveDocument.C1798.Angle=360.00 
App.ActiveDocument.C1798.Placement=Base.Placement(Base.Vector(-15.811674,118.253982,-65.794434),Base.Rotation(0.742670,-0.611981,0.000000,0.271882))
App.ActiveDocument.addObject("Part::Cylinder","C1799")
App.ActiveDocument.C1799.Radius=0.683796
App.ActiveDocument.C1799.Height=20.00
App.ActiveDocument.C1799.Angle=360.00 
App.ActiveDocument.C1799.Placement=Base.Placement(Base.Vector(-15.895485,114.783365,-63.982063),Base.Rotation(0.782747,-0.549245,0.000000,0.292637))
App.ActiveDocument.addObject("Part::Cylinder","C1800")
App.ActiveDocument.C1800.Radius=0.678601
App.ActiveDocument.C1800.Height=20.00
App.ActiveDocument.C1800.Angle=360.00 
App.ActiveDocument.C1800.Placement=Base.Placement(Base.Vector(-15.797178,111.290519,-61.928231),Base.Rotation(0.802777,-0.502133,0.000000,0.321576))
App.ActiveDocument.addObject("Part::Cylinder","C1801")
App.ActiveDocument.C1801.Radius=0.672837
App.ActiveDocument.C1801.Height=20.00
App.ActiveDocument.C1801.Angle=360.00 
App.ActiveDocument.C1801.Placement=Base.Placement(Base.Vector(-15.912263,108.276605,-59.721338),Base.Rotation(0.833553,-0.421999,0.000000,0.356520))
App.ActiveDocument.addObject("Part::Cylinder","C1802")
App.ActiveDocument.C1802.Radius=0.528303
App.ActiveDocument.C1802.Height=20.00
App.ActiveDocument.C1802.Angle=360.00 
App.ActiveDocument.C1802.Placement=Base.Placement(Base.Vector(-19.951001,202.606272,-4.193281),Base.Rotation(-0.663206,-0.267788,0.000000,0.698890))
App.ActiveDocument.addObject("Part::Cylinder","C1803")
App.ActiveDocument.C1803.Radius=0.538647
App.ActiveDocument.C1803.Height=20.00
App.ActiveDocument.C1803.Angle=360.00 
App.ActiveDocument.C1803.Placement=Base.Placement(Base.Vector(-20.335589,202.258135,-8.778963),Base.Rotation(-0.674142,-0.272108,0.000000,0.686651))
App.ActiveDocument.addObject("Part::Cylinder","C1804")
App.ActiveDocument.C1804.Radius=0.549479
App.ActiveDocument.C1804.Height=20.00
App.ActiveDocument.C1804.Angle=360.00 
App.ActiveDocument.C1804.Placement=Base.Placement(Base.Vector(-20.323393,201.899944,-13.312769),Base.Rotation(-0.686268,-0.273995,0.000000,0.673768))
App.ActiveDocument.addObject("Part::Cylinder","C1805")
App.ActiveDocument.C1805.Radius=0.559775
App.ActiveDocument.C1805.Height=20.00
App.ActiveDocument.C1805.Angle=360.00 
App.ActiveDocument.C1805.Placement=Base.Placement(Base.Vector(-20.407744,201.352038,-17.579450),Base.Rotation(-0.700896,-0.274780,0.000000,0.658210))
App.ActiveDocument.addObject("Part::Cylinder","C1806")
App.ActiveDocument.C1806.Radius=0.569689
App.ActiveDocument.C1806.Height=20.00
App.ActiveDocument.C1806.Angle=360.00 
App.ActiveDocument.C1806.Placement=Base.Placement(Base.Vector(-20.895024,200.428742,-21.952488),Base.Rotation(-0.712334,-0.286501,0.000000,0.640701))
App.ActiveDocument.addObject("Part::Cylinder","C1807")
App.ActiveDocument.C1807.Radius=0.581036
App.ActiveDocument.C1807.Height=20.00
App.ActiveDocument.C1807.Angle=360.00 
App.ActiveDocument.C1807.Placement=Base.Placement(Base.Vector(-20.299934,199.736321,-26.234357),Base.Rotation(-0.728359,-0.284198,0.000000,0.623478))
App.ActiveDocument.addObject("Part::Cylinder","C1808")
App.ActiveDocument.C1808.Radius=0.590833
App.ActiveDocument.C1808.Height=20.00
App.ActiveDocument.C1808.Angle=360.00 
App.ActiveDocument.C1808.Placement=Base.Placement(Base.Vector(-20.601016,198.483833,-30.417450),Base.Rotation(-0.739807,-0.294961,0.000000,0.604718))
App.ActiveDocument.addObject("Part::Cylinder","C1809")
App.ActiveDocument.C1809.Radius=0.600023
App.ActiveDocument.C1809.Height=20.00
App.ActiveDocument.C1809.Angle=360.00 
App.ActiveDocument.C1809.Placement=Base.Placement(Base.Vector(-20.885546,197.077554,-34.287452),Base.Rotation(-0.751512,-0.305819,0.000000,0.584555))
App.ActiveDocument.addObject("Part::Cylinder","C1810")
App.ActiveDocument.C1810.Radius=0.609998
App.ActiveDocument.C1810.Height=20.00
App.ActiveDocument.C1810.Angle=360.00 
App.ActiveDocument.C1810.Placement=Base.Placement(Base.Vector(-20.926595,195.524509,-38.043621),Base.Rotation(-0.772040,-0.314948,0.000000,0.552053))
App.ActiveDocument.addObject("Part::Cylinder","C1811")
App.ActiveDocument.C1811.Radius=0.620350
App.ActiveDocument.C1811.Height=20.00
App.ActiveDocument.C1811.Angle=360.00 
App.ActiveDocument.C1811.Placement=Base.Placement(Base.Vector(-20.772477,193.698112,-41.719652),Base.Rotation(-0.794244,-0.327447,0.000000,0.511815))
App.ActiveDocument.addObject("Part::Cylinder","C1812")
App.ActiveDocument.C1812.Radius=0.628493
App.ActiveDocument.C1812.Height=20.00
App.ActiveDocument.C1812.Angle=360.00 
App.ActiveDocument.C1812.Placement=Base.Placement(Base.Vector(-21.245572,191.440441,-44.868441),Base.Rotation(-0.808506,-0.354058,0.000000,0.470064))
App.ActiveDocument.addObject("Part::Cylinder","C1813")
App.ActiveDocument.C1813.Radius=0.637168
App.ActiveDocument.C1813.Height=20.00
App.ActiveDocument.C1813.Angle=360.00 
App.ActiveDocument.C1813.Placement=Base.Placement(Base.Vector(-20.990723,189.173761,-47.813242),Base.Rotation(-0.825408,-0.366499,0.000000,0.429395))
App.ActiveDocument.addObject("Part::Cylinder","C1814")
App.ActiveDocument.C1814.Radius=0.643687
App.ActiveDocument.C1814.Height=20.00
App.ActiveDocument.C1814.Angle=360.00 
App.ActiveDocument.C1814.Placement=Base.Placement(Base.Vector(-21.539257,186.294352,-50.500476),Base.Rotation(-0.826334,-0.404538,0.000000,0.391817))
App.ActiveDocument.addObject("Part::Cylinder","C1815")
App.ActiveDocument.C1815.Radius=0.650442
App.ActiveDocument.C1815.Height=20.00
App.ActiveDocument.C1815.Angle=360.00 
App.ActiveDocument.C1815.Placement=Base.Placement(Base.Vector(-21.523468,183.411363,-52.983533),Base.Rotation(-0.824067,-0.441640,0.000000,0.354779))
App.ActiveDocument.addObject("Part::Cylinder","C1816")
App.ActiveDocument.C1816.Radius=0.656337
App.ActiveDocument.C1816.Height=20.00
App.ActiveDocument.C1816.Angle=360.00 
App.ActiveDocument.C1816.Placement=Base.Placement(Base.Vector(-21.656433,180.203953,-55.208537),Base.Rotation(-0.810962,-0.492362,0.000000,0.316101))
App.ActiveDocument.addObject("Part::Cylinder","C1817")
App.ActiveDocument.C1817.Radius=0.662144
App.ActiveDocument.C1817.Height=20.00
App.ActiveDocument.C1817.Angle=360.00 
App.ActiveDocument.C1817.Placement=Base.Placement(Base.Vector(-21.431040,176.930673,-57.187164),Base.Rotation(-0.798483,-0.533432,0.000000,0.279062))
App.ActiveDocument.addObject("Part::Cylinder","C1818")
App.ActiveDocument.C1818.Radius=0.667428
App.ActiveDocument.C1818.Height=20.00
App.ActiveDocument.C1818.Angle=360.00 
App.ActiveDocument.C1818.Placement=Base.Placement(Base.Vector(-21.175050,173.279266,-59.012233),Base.Rotation(-0.775887,-0.580962,0.000000,0.245934))
App.ActiveDocument.addObject("Part::Cylinder","C1819")
App.ActiveDocument.C1819.Radius=0.671611
App.ActiveDocument.C1819.Height=20.00
App.ActiveDocument.C1819.Angle=360.00 
App.ActiveDocument.C1819.Placement=Base.Placement(Base.Vector(-20.869234,169.589535,-60.592136),Base.Rotation(-0.734890,-0.638676,0.000000,0.228102))
App.ActiveDocument.addObject("Part::Cylinder","C1820")
App.ActiveDocument.C1820.Radius=0.673997
App.ActiveDocument.C1820.Height=20.00
App.ActiveDocument.C1820.Angle=360.00 
App.ActiveDocument.C1820.Placement=Base.Placement(Base.Vector(-20.969792,165.742366,-61.901833),Base.Rotation(-0.647292,-0.728742,0.000000,0.223491))
App.ActiveDocument.addObject("Part::Cylinder","C1821")
App.ActiveDocument.C1821.Radius=0.677050
App.ActiveDocument.C1821.Height=20.00
App.ActiveDocument.C1821.Angle=360.00 
App.ActiveDocument.C1821.Placement=Base.Placement(Base.Vector(-20.670226,161.573894,-63.261231),Base.Rotation(-0.557315,-0.800241,0.000000,0.221393))
App.ActiveDocument.addObject("Part::Cylinder","C1822")
App.ActiveDocument.C1822.Radius=0.679754
App.ActiveDocument.C1822.Height=20.00
App.ActiveDocument.C1822.Angle=360.00 
App.ActiveDocument.C1822.Placement=Base.Placement(Base.Vector(-20.355477,157.305255,-64.461041),Base.Rotation(-0.463683,-0.857785,0.000000,0.221818))
App.ActiveDocument.addObject("Part::Cylinder","C1823")
App.ActiveDocument.C1823.Radius=0.681777
App.ActiveDocument.C1823.Height=20.00
App.ActiveDocument.C1823.Angle=360.00 
App.ActiveDocument.C1823.Placement=Base.Placement(Base.Vector(-20.222911,153.080271,-65.400365),Base.Rotation(-0.383646,-0.896484,0.000000,0.221657))
App.ActiveDocument.addObject("Part::Cylinder","C1824")
App.ActiveDocument.C1824.Radius=0.683403
App.ActiveDocument.C1824.Height=20.00
App.ActiveDocument.C1824.Angle=360.00 
App.ActiveDocument.C1824.Placement=Base.Placement(Base.Vector(-20.071046,148.833571,-66.194399),Base.Rotation(-0.300119,-0.927005,0.000000,0.224925))
App.ActiveDocument.addObject("Part::Cylinder","C1825")
App.ActiveDocument.C1825.Radius=0.684349
App.ActiveDocument.C1825.Height=20.00
App.ActiveDocument.C1825.Angle=360.00 
App.ActiveDocument.C1825.Placement=Base.Placement(Base.Vector(-20.144322,144.560329,-66.733167),Base.Rotation(-0.229664,-0.946788,0.000000,0.225495))
App.ActiveDocument.addObject("Part::Cylinder","C1826")
App.ActiveDocument.C1826.Radius=0.685654
App.ActiveDocument.C1826.Height=20.00
App.ActiveDocument.C1826.Angle=360.00 
App.ActiveDocument.C1826.Placement=Base.Placement(Base.Vector(-19.899857,140.425033,-67.248498),Base.Rotation(-0.157633,-0.961049,0.000000,0.227017))
App.ActiveDocument.addObject("Part::Cylinder","C1827")
App.ActiveDocument.C1827.Radius=0.686453
App.ActiveDocument.C1827.Height=20.00
App.ActiveDocument.C1827.Angle=360.00 
App.ActiveDocument.C1827.Placement=Base.Placement(Base.Vector(-19.817109,136.159735,-67.508190),Base.Rotation(-0.048752,-0.973647,0.000000,0.222787))
App.ActiveDocument.addObject("Part::Cylinder","C1828")
App.ActiveDocument.C1828.Radius=0.686939
App.ActiveDocument.C1828.Height=20.00
App.ActiveDocument.C1828.Angle=360.00 
App.ActiveDocument.C1828.Placement=Base.Placement(Base.Vector(-19.513424,132.061228,-67.648662),Base.Rotation(0.042889,-0.972753,0.000000,0.227843))
App.ActiveDocument.addObject("Part::Cylinder","C1829")
App.ActiveDocument.C1829.Radius=0.686260
App.ActiveDocument.C1829.Height=20.00
App.ActiveDocument.C1829.Angle=360.00 
App.ActiveDocument.C1829.Placement=Base.Placement(Base.Vector(-19.332240,128.099486,-67.481300),Base.Rotation(0.242319,-0.938915,0.000000,0.244378))
App.ActiveDocument.addObject("Part::Cylinder","C1830")
App.ActiveDocument.C1830.Radius=0.684644
App.ActiveDocument.C1830.Height=20.00
App.ActiveDocument.C1830.Angle=360.00 
App.ActiveDocument.C1830.Placement=Base.Placement(Base.Vector(-19.328136,124.799556,-66.867392),Base.Rotation(0.463350,-0.845990,0.000000,0.263833))
App.ActiveDocument.addObject("Part::Cylinder","C1831")
App.ActiveDocument.C1831.Radius=0.681091
App.ActiveDocument.C1831.Height=20.00
App.ActiveDocument.C1831.Angle=360.00 
App.ActiveDocument.C1831.Placement=Base.Placement(Base.Vector(-19.503266,121.431430,-65.557618),Base.Rotation(0.593776,-0.751055,0.000000,0.288699))
App.ActiveDocument.addObject("Part::Cylinder","C1832")
App.ActiveDocument.C1832.Radius=0.677223
App.ActiveDocument.C1832.Height=20.00
App.ActiveDocument.C1832.Angle=360.00 
App.ActiveDocument.C1832.Placement=Base.Placement(Base.Vector(-19.397833,117.936504,-63.977870),Base.Rotation(0.654871,-0.688687,0.000000,0.311213))
App.ActiveDocument.addObject("Part::Cylinder","C1833")
App.ActiveDocument.C1833.Radius=0.672144
App.ActiveDocument.C1833.Height=20.00
App.ActiveDocument.C1833.Angle=360.00 
App.ActiveDocument.C1833.Placement=Base.Placement(Base.Vector(-19.200906,114.218019,-62.064654),Base.Rotation(0.673228,-0.655850,0.000000,0.341503))
App.ActiveDocument.addObject("Part::Cylinder","C1834")
App.ActiveDocument.C1834.Radius=0.666845
App.ActiveDocument.C1834.Height=20.00
App.ActiveDocument.C1834.Angle=360.00 
App.ActiveDocument.C1834.Placement=Base.Placement(Base.Vector(-19.135821,110.784626,-59.912638),Base.Rotation(0.691488,-0.625820,0.000000,0.360824))
App.ActiveDocument.addObject("Part::Cylinder","C1835")
App.ActiveDocument.C1835.Radius=0.662238
App.ActiveDocument.C1835.Height=20.00
App.ActiveDocument.C1835.Angle=360.00 
App.ActiveDocument.C1835.Placement=Base.Placement(Base.Vector(-19.605542,108.956884,-58.803954),Base.Rotation(0.811854,-0.375185,0.000000,0.447357))
App.ActiveDocument.addObject("Part::Cylinder","C1836")
App.ActiveDocument.C1836.Radius=0.522033
App.ActiveDocument.C1836.Height=20.00
App.ActiveDocument.C1836.Angle=360.00 
App.ActiveDocument.C1836.Placement=Base.Placement(Base.Vector(-23.883029,200.838371,-4.165528),Base.Rotation(-0.640805,-0.312561,0.000000,0.701195))
App.ActiveDocument.addObject("Part::Cylinder","C1837")
App.ActiveDocument.C1837.Radius=0.532648
App.ActiveDocument.C1837.Height=20.00
App.ActiveDocument.C1837.Angle=360.00 
App.ActiveDocument.C1837.Placement=Base.Placement(Base.Vector(-24.148653,200.547392,-8.819351),Base.Rotation(-0.651073,-0.316788,0.000000,0.689746))
App.ActiveDocument.addObject("Part::Cylinder","C1838")
App.ActiveDocument.C1838.Radius=0.543400
App.ActiveDocument.C1838.Height=20.00
App.ActiveDocument.C1838.Angle=360.00 
App.ActiveDocument.C1838.Placement=Base.Placement(Base.Vector(-24.247178,200.163876,-13.370391),Base.Rotation(-0.663537,-0.319479,0.000000,0.676500))
App.ActiveDocument.addObject("Part::Cylinder","C1839")
App.ActiveDocument.C1839.Radius=0.553651
App.ActiveDocument.C1839.Height=20.00
App.ActiveDocument.C1839.Angle=360.00 
App.ActiveDocument.C1839.Placement=Base.Placement(Base.Vector(-24.374030,199.600128,-17.665145),Base.Rotation(-0.676640,-0.324597,0.000000,0.660905))
App.ActiveDocument.addObject("Part::Cylinder","C1840")
App.ActiveDocument.C1840.Radius=0.563652
App.ActiveDocument.C1840.Height=20.00
App.ActiveDocument.C1840.Angle=360.00 
App.ActiveDocument.C1840.Placement=Base.Placement(Base.Vector(-24.795980,198.676751,-22.030842),Base.Rotation(-0.688146,-0.333905,0.000000,0.644176))
App.ActiveDocument.addObject("Part::Cylinder","C1841")
App.ActiveDocument.C1841.Radius=0.574703
App.ActiveDocument.C1841.Height=20.00
App.ActiveDocument.C1841.Angle=360.00 
App.ActiveDocument.C1841.Placement=Base.Placement(Base.Vector(-24.225976,198.052560,-26.143392),Base.Rotation(-0.705835,-0.332769,0.000000,0.625350))
App.ActiveDocument.addObject("Part::Cylinder","C1842")
App.ActiveDocument.C1842.Radius=0.583852
App.ActiveDocument.C1842.Height=20.00
App.ActiveDocument.C1842.Angle=360.00 
App.ActiveDocument.C1842.Placement=Base.Placement(Base.Vector(-24.658300,196.753871,-30.143503),Base.Rotation(-0.714473,-0.347971,0.000000,0.606997))
App.ActiveDocument.addObject("Part::Cylinder","C1843")
App.ActiveDocument.C1843.Radius=0.593318
App.ActiveDocument.C1843.Height=20.00
App.ActiveDocument.C1843.Angle=360.00 
App.ActiveDocument.C1843.Placement=Base.Placement(Base.Vector(-24.837281,195.338552,-34.085510),Base.Rotation(-0.723385,-0.364769,0.000000,0.586224))
App.ActiveDocument.addObject("Part::Cylinder","C1844")
App.ActiveDocument.C1844.Radius=0.603503
App.ActiveDocument.C1844.Height=20.00
App.ActiveDocument.C1844.Angle=360.00 
App.ActiveDocument.C1844.Placement=Base.Placement(Base.Vector(-24.673814,193.840266,-37.903543),Base.Rotation(-0.738396,-0.381451,0.000000,0.556117))
App.ActiveDocument.addObject("Part::Cylinder","C1845")
App.ActiveDocument.C1845.Radius=0.613325
App.ActiveDocument.C1845.Height=20.00
App.ActiveDocument.C1845.Angle=360.00 
App.ActiveDocument.C1845.Placement=Base.Placement(Base.Vector(-24.590588,192.011522,-41.502822),Base.Rotation(-0.753385,-0.402439,0.000000,0.520052))
App.ActiveDocument.addObject("Part::Cylinder","C1846")
App.ActiveDocument.C1846.Radius=0.621176
App.ActiveDocument.C1846.Height=20.00
App.ActiveDocument.C1846.Angle=360.00 
App.ActiveDocument.C1846.Placement=Base.Placement(Base.Vector(-24.926341,189.862137,-44.504772),Base.Rotation(-0.759153,-0.438761,0.000000,0.480807))
App.ActiveDocument.addObject("Part::Cylinder","C1847")
App.ActiveDocument.C1847.Radius=0.629743
App.ActiveDocument.C1847.Height=20.00
App.ActiveDocument.C1847.Angle=360.00 
App.ActiveDocument.C1847.Placement=Base.Placement(Base.Vector(-24.791680,187.553404,-47.442715),Base.Rotation(-0.770759,-0.461879,0.000000,0.438859))
App.ActiveDocument.addObject("Part::Cylinder","C1848")
App.ActiveDocument.C1848.Radius=0.636008
App.ActiveDocument.C1848.Height=20.00
App.ActiveDocument.C1848.Angle=360.00 
App.ActiveDocument.C1848.Placement=Base.Placement(Base.Vector(-25.263821,184.695464,-50.019689),Base.Rotation(-0.758765,-0.511334,0.000000,0.403502))
App.ActiveDocument.addObject("Part::Cylinder","C1849")
App.ActiveDocument.C1849.Radius=0.642290
App.ActiveDocument.C1849.Height=20.00
App.ActiveDocument.C1849.Angle=360.00 
App.ActiveDocument.C1849.Placement=Base.Placement(Base.Vector(-25.328246,181.788180,-52.392127),Base.Rotation(-0.741746,-0.559690,0.000000,0.369541))
App.ActiveDocument.addObject("Part::Cylinder","C1850")
App.ActiveDocument.C1850.Radius=0.648225
App.ActiveDocument.C1850.Height=20.00
App.ActiveDocument.C1850.Angle=360.00 
App.ActiveDocument.C1850.Placement=Base.Placement(Base.Vector(-25.330172,178.626298,-54.553112),Base.Rotation(-0.719827,-0.608288,0.000000,0.334418))
App.ActiveDocument.addObject("Part::Cylinder","C1851")
App.ActiveDocument.C1851.Radius=0.653915
App.ActiveDocument.C1851.Height=20.00
App.ActiveDocument.C1851.Angle=360.00 
App.ActiveDocument.C1851.Placement=Base.Placement(Base.Vector(-25.090897,175.317538,-56.517811),Base.Rotation(-0.685284,-0.663263,0.000000,0.300778))
App.ActiveDocument.addObject("Part::Cylinder","C1852")
App.ActiveDocument.C1852.Radius=0.658597
App.ActiveDocument.C1852.Height=20.00
App.ActiveDocument.C1852.Angle=360.00 
App.ActiveDocument.C1852.Placement=Base.Placement(Base.Vector(-24.893612,171.876489,-58.165892),Base.Rotation(-0.637924,-0.720192,0.000000,0.272719))
App.ActiveDocument.addObject("Part::Cylinder","C1853")
App.ActiveDocument.C1853.Radius=0.662643
App.ActiveDocument.C1853.Height=20.00
App.ActiveDocument.C1853.Angle=360.00 
App.ActiveDocument.C1853.Placement=Base.Placement(Base.Vector(-24.640056,168.100890,-59.659056),Base.Rotation(-0.569655,-0.781997,0.000000,0.252932))
App.ActiveDocument.addObject("Part::Cylinder","C1854")
App.ActiveDocument.C1854.Radius=0.665128
App.ActiveDocument.C1854.Height=20.00
App.ActiveDocument.C1854.Angle=360.00 
App.ActiveDocument.C1854.Placement=Base.Placement(Base.Vector(-24.648913,164.179454,-60.830900),Base.Rotation(-0.488967,-0.836742,0.000000,0.246522))
App.ActiveDocument.addObject("Part::Cylinder","C1855")
App.ActiveDocument.C1855.Radius=0.667786
App.ActiveDocument.C1855.Height=20.00
App.ActiveDocument.C1855.Angle=360.00 
App.ActiveDocument.C1855.Placement=Base.Placement(Base.Vector(-24.403744,160.076489,-61.969700),Base.Rotation(-0.410872,-0.878333,0.000000,0.244366))
App.ActiveDocument.addObject("Part::Cylinder","C1856")
App.ActiveDocument.C1856.Radius=0.669634
App.ActiveDocument.C1856.Height=20.00
App.ActiveDocument.C1856.Angle=360.00 
App.ActiveDocument.C1856.Placement=Base.Placement(Base.Vector(-24.287556,155.817530,-62.909022),Base.Rotation(-0.331869,-0.910132,0.000000,0.248036))
App.ActiveDocument.addObject("Part::Cylinder","C1857")
App.ActiveDocument.C1857.Radius=0.671547
App.ActiveDocument.C1857.Height=20.00
App.ActiveDocument.C1857.Angle=360.00 
App.ActiveDocument.C1857.Placement=Base.Placement(Base.Vector(-24.007863,151.504501,-63.780396),Base.Rotation(-0.254898,-0.933327,0.000000,0.252840))
App.ActiveDocument.addObject("Part::Cylinder","C1858")
App.ActiveDocument.C1858.Radius=0.672574
App.ActiveDocument.C1858.Height=20.00
App.ActiveDocument.C1858.Angle=360.00 
App.ActiveDocument.C1858.Placement=Base.Placement(Base.Vector(-23.949029,147.290450,-64.367275),Base.Rotation(-0.199497,-0.945225,0.000000,0.258363))
App.ActiveDocument.addObject("Part::Cylinder","C1859")
App.ActiveDocument.C1859.Radius=0.673536
App.ActiveDocument.C1859.Height=20.00
App.ActiveDocument.C1859.Angle=360.00 
App.ActiveDocument.C1859.Placement=Base.Placement(Base.Vector(-23.664663,143.062865,-64.932275),Base.Rotation(-0.113176,-0.956072,0.000000,0.270402))
App.ActiveDocument.addObject("Part::Cylinder","C1860")
App.ActiveDocument.C1860.Radius=0.674245
App.ActiveDocument.C1860.Height=20.00
App.ActiveDocument.C1860.Angle=360.00 
App.ActiveDocument.C1860.Placement=Base.Placement(Base.Vector(-23.439839,138.840217,-65.306054),Base.Rotation(-0.065093,-0.958259,0.000000,0.278393))
App.ActiveDocument.addObject("Part::Cylinder","C1861")
App.ActiveDocument.C1861.Radius=0.675253
App.ActiveDocument.C1861.Height=20.00
App.ActiveDocument.C1861.Angle=360.00 
App.ActiveDocument.C1861.Placement=Base.Placement(Base.Vector(-22.942526,134.783990,-65.671340),Base.Rotation(0.015663,-0.957638,0.000000,0.287549))
App.ActiveDocument.addObject("Part::Cylinder","C1862")
App.ActiveDocument.C1862.Radius=0.675161
App.ActiveDocument.C1862.Height=20.00
App.ActiveDocument.C1862.Angle=360.00 
App.ActiveDocument.C1862.Placement=Base.Placement(Base.Vector(-22.656961,130.928803,-65.709339),Base.Rotation(0.103197,-0.948405,0.000000,0.299797))
App.ActiveDocument.addObject("Part::Cylinder","C1863")
App.ActiveDocument.C1863.Radius=0.674289
App.ActiveDocument.C1863.Height=20.00
App.ActiveDocument.C1863.Angle=360.00 
App.ActiveDocument.C1863.Placement=Base.Placement(Base.Vector(-22.286734,127.150958,-65.529473),Base.Rotation(0.243805,-0.914186,0.000000,0.323765))
App.ActiveDocument.addObject("Part::Cylinder","C1864")
App.ActiveDocument.C1864.Radius=0.672404
App.ActiveDocument.C1864.Height=20.00
App.ActiveDocument.C1864.Angle=360.00 
App.ActiveDocument.C1864.Placement=Base.Placement(Base.Vector(-22.234169,123.801950,-64.744882),Base.Rotation(0.354544,-0.873013,0.000000,0.334884))
App.ActiveDocument.addObject("Part::Cylinder","C1865")
App.ActiveDocument.C1865.Radius=0.668362
App.ActiveDocument.C1865.Height=20.00
App.ActiveDocument.C1865.Angle=360.00 
App.ActiveDocument.C1865.Placement=Base.Placement(Base.Vector(-22.557131,120.751653,-63.304031),Base.Rotation(0.459271,-0.815018,0.000000,0.353293))
App.ActiveDocument.addObject("Part::Cylinder","C1866")
App.ActiveDocument.C1866.Radius=0.664806
App.ActiveDocument.C1866.Height=20.00
App.ActiveDocument.C1866.Angle=360.00 
App.ActiveDocument.C1866.Placement=Base.Placement(Base.Vector(-22.435991,117.243573,-61.634604),Base.Rotation(0.547995,-0.752435,0.000000,0.365435))
App.ActiveDocument.addObject("Part::Cylinder","C1867")
App.ActiveDocument.C1867.Radius=0.659647
App.ActiveDocument.C1867.Height=20.00
App.ActiveDocument.C1867.Angle=360.00 
App.ActiveDocument.C1867.Placement=Base.Placement(Base.Vector(-22.793481,114.254648,-59.606293),Base.Rotation(0.593233,-0.711071,0.000000,0.377429))
App.ActiveDocument.addObject("Part::Cylinder","C1868")
App.ActiveDocument.C1868.Radius=0.655075
App.ActiveDocument.C1868.Height=20.00
App.ActiveDocument.C1868.Angle=360.00 
App.ActiveDocument.C1868.Placement=Base.Placement(Base.Vector(-22.547455,110.704518,-57.447617),Base.Rotation(0.619741,-0.683569,0.000000,0.385557))
App.ActiveDocument.addObject("Part::Cylinder","C1869")
App.ActiveDocument.C1869.Radius=0.651063
App.ActiveDocument.C1869.Height=20.00
App.ActiveDocument.C1869.Angle=360.00 
App.ActiveDocument.C1869.Placement=Base.Placement(Base.Vector(-23.432374,109.665880,-57.305749),Base.Rotation(0.786934,-0.351132,0.000000,0.507387))
App.ActiveDocument.addObject("Part::Cylinder","C1870")
App.ActiveDocument.C1870.Radius=0.516239
App.ActiveDocument.C1870.Height=20.00
App.ActiveDocument.C1870.Angle=360.00 
App.ActiveDocument.C1870.Placement=Base.Placement(Base.Vector(-27.812029,198.804066,-4.197257),Base.Rotation(-0.624001,-0.341869,0.000000,0.702672))
App.ActiveDocument.addObject("Part::Cylinder","C1871")
App.ActiveDocument.C1871.Radius=0.526600
App.ActiveDocument.C1871.Height=20.00
App.ActiveDocument.C1871.Angle=360.00 
App.ActiveDocument.C1871.Placement=Base.Placement(Base.Vector(-28.046392,198.539283,-8.728459),Base.Rotation(-0.633548,-0.347100,0.000000,0.691476))
App.ActiveDocument.addObject("Part::Cylinder","C1872")
App.ActiveDocument.C1872.Radius=0.537415
App.ActiveDocument.C1872.Height=20.00
App.ActiveDocument.C1872.Angle=360.00 
App.ActiveDocument.C1872.Placement=Base.Placement(Base.Vector(-28.198041,198.138085,-13.371914),Base.Rotation(-0.643968,-0.353642,0.000000,0.678412))
App.ActiveDocument.addObject("Part::Cylinder","C1873")
App.ActiveDocument.C1873.Radius=0.547679
App.ActiveDocument.C1873.Height=20.00
App.ActiveDocument.C1873.Angle=360.00 
App.ActiveDocument.C1873.Placement=Base.Placement(Base.Vector(-28.309704,197.583646,-17.703468),Base.Rotation(-0.654831,-0.361717,0.000000,0.663594))
App.ActiveDocument.addObject("Part::Cylinder","C1874")
App.ActiveDocument.C1874.Radius=0.557760
App.ActiveDocument.C1874.Height=20.00
App.ActiveDocument.C1874.Angle=360.00 
App.ActiveDocument.C1874.Placement=Base.Placement(Base.Vector(-28.624935,196.692604,-22.024777),Base.Rotation(-0.666513,-0.370993,0.000000,0.646625))
App.ActiveDocument.addObject("Part::Cylinder","C1875")
App.ActiveDocument.C1875.Radius=0.568404
App.ActiveDocument.C1875.Height=20.00
App.ActiveDocument.C1875.Angle=360.00 
App.ActiveDocument.C1875.Placement=Base.Placement(Base.Vector(-28.205001,196.034486,-26.046533),Base.Rotation(-0.682832,-0.375079,0.000000,0.626943))
App.ActiveDocument.addObject("Part::Cylinder","C1876")
App.ActiveDocument.C1876.Radius=0.577451
App.ActiveDocument.C1876.Height=20.00
App.ActiveDocument.C1876.Angle=360.00 
App.ActiveDocument.C1876.Placement=Base.Placement(Base.Vector(-28.615300,194.700420,-29.983031),Base.Rotation(-0.689026,-0.395062,0.000000,0.607592))
App.ActiveDocument.addObject("Part::Cylinder","C1877")
App.ActiveDocument.C1877.Radius=0.587176
App.ActiveDocument.C1877.Height=20.00
App.ActiveDocument.C1877.Angle=360.00 
App.ActiveDocument.C1877.Placement=Base.Placement(Base.Vector(-28.626215,193.323087,-33.912427),Base.Rotation(-0.694913,-0.418886,0.000000,0.584491))
App.ActiveDocument.addObject("Part::Cylinder","C1878")
App.ActiveDocument.C1878.Radius=0.597158
App.ActiveDocument.C1878.Height=20.00
App.ActiveDocument.C1878.Angle=360.00 
App.ActiveDocument.C1878.Placement=Base.Placement(Base.Vector(-28.528701,191.709369,-37.770720),Base.Rotation(-0.702340,-0.444071,0.000000,0.556346))
App.ActiveDocument.addObject("Part::Cylinder","C1879")
App.ActiveDocument.C1879.Radius=0.606522
App.ActiveDocument.C1879.Height=20.00
App.ActiveDocument.C1879.Angle=360.00 
App.ActiveDocument.C1879.Placement=Base.Placement(Base.Vector(-28.437287,189.891906,-41.197100),Base.Rotation(-0.709781,-0.474581,0.000000,0.520561))
App.ActiveDocument.addObject("Part::Cylinder","C1880")
App.ActiveDocument.C1880.Radius=0.614644
App.ActiveDocument.C1880.Height=20.00
App.ActiveDocument.C1880.Angle=360.00 
App.ActiveDocument.C1880.Placement=Base.Placement(Base.Vector(-28.661242,187.568898,-44.335789),Base.Rotation(-0.706519,-0.515552,0.000000,0.484806))
App.ActiveDocument.addObject("Part::Cylinder","C1881")
App.ActiveDocument.C1881.Radius=0.622308
App.ActiveDocument.C1881.Height=20.00
App.ActiveDocument.C1881.Angle=360.00 
App.ActiveDocument.C1881.Placement=Base.Placement(Base.Vector(-28.580642,185.316664,-47.039854),Base.Rotation(-0.703602,-0.551855,0.000000,0.447662))
App.ActiveDocument.addObject("Part::Cylinder","C1882")
App.ActiveDocument.C1882.Radius=0.628316
App.ActiveDocument.C1882.Height=20.00
App.ActiveDocument.C1882.Angle=360.00 
App.ActiveDocument.C1882.Placement=Base.Placement(Base.Vector(-28.951052,182.511298,-49.431262),Base.Rotation(-0.682125,-0.603079,0.000000,0.413523))
App.ActiveDocument.addObject("Part::Cylinder","C1883")
App.ActiveDocument.C1883.Radius=0.634636
App.ActiveDocument.C1883.Height=20.00
App.ActiveDocument.C1883.Angle=360.00 
App.ActiveDocument.C1883.Placement=Base.Placement(Base.Vector(-28.954556,179.470708,-51.808586),Base.Rotation(-0.650868,-0.656320,0.000000,0.381594))
App.ActiveDocument.addObject("Part::Cylinder","C1884")
App.ActiveDocument.C1884.Radius=0.640604
App.ActiveDocument.C1884.Height=20.00
App.ActiveDocument.C1884.Angle=360.00 
App.ActiveDocument.C1884.Placement=Base.Placement(Base.Vector(-28.809313,176.294886,-53.907671),Base.Rotation(-0.616368,-0.705838,0.000000,0.349117))
App.ActiveDocument.addObject("Part::Cylinder","C1885")
App.ActiveDocument.C1885.Radius=0.645608
App.ActiveDocument.C1885.Height=20.00
App.ActiveDocument.C1885.Angle=360.00 
App.ActiveDocument.C1885.Placement=Base.Placement(Base.Vector(-28.583188,173.084355,-55.690232),Base.Rotation(-0.562042,-0.761365,0.000000,0.323160))
App.ActiveDocument.addObject("Part::Cylinder","C1886")
App.ActiveDocument.C1886.Radius=0.650125
App.ActiveDocument.C1886.Height=20.00
App.ActiveDocument.C1886.Angle=360.00 
App.ActiveDocument.C1886.Placement=Base.Placement(Base.Vector(-28.323193,169.676566,-57.240400),Base.Rotation(-0.501594,-0.811858,0.000000,0.298816))
App.ActiveDocument.addObject("Part::Cylinder","C1887")
App.ActiveDocument.C1887.Radius=0.652859
App.ActiveDocument.C1887.Height=20.00
App.ActiveDocument.C1887.Angle=360.00 
App.ActiveDocument.C1887.Placement=Base.Placement(Base.Vector(-28.348246,166.000723,-58.426524),Base.Rotation(-0.420951,-0.860235,0.000000,0.287742))
App.ActiveDocument.addObject("Part::Cylinder","C1888")
App.ActiveDocument.C1888.Radius=0.655373
App.ActiveDocument.C1888.Height=20.00
App.ActiveDocument.C1888.Angle=360.00 
App.ActiveDocument.C1888.Placement=Base.Placement(Base.Vector(-28.293291,162.056682,-59.478563),Base.Rotation(-0.348151,-0.894710,0.000000,0.279795))
App.ActiveDocument.addObject("Part::Cylinder","C1889")
App.ActiveDocument.C1889.Radius=0.657741
App.ActiveDocument.C1889.Height=20.00
App.ActiveDocument.C1889.Angle=360.00 
App.ActiveDocument.C1889.Placement=Base.Placement(Base.Vector(-28.058495,157.987134,-60.447744),Base.Rotation(-0.277799,-0.919655,0.000000,0.277602))
App.ActiveDocument.addObject("Part::Cylinder","C1890")
App.ActiveDocument.C1890.Radius=0.659287
App.ActiveDocument.C1890.Height=20.00
App.ActiveDocument.C1890.Angle=360.00 
App.ActiveDocument.C1890.Placement=Base.Placement(Base.Vector(-27.862956,153.978812,-61.197675),Base.Rotation(-0.204872,-0.937171,0.000000,0.282380))
App.ActiveDocument.addObject("Part::Cylinder","C1891")
App.ActiveDocument.C1891.Radius=0.660564
App.ActiveDocument.C1891.Height=20.00
App.ActiveDocument.C1891.Angle=360.00 
App.ActiveDocument.C1891.Placement=Base.Placement(Base.Vector(-27.616631,149.854029,-61.838580),Base.Rotation(-0.142973,-0.946226,0.000000,0.290200))
App.ActiveDocument.addObject("Part::Cylinder","C1892")
App.ActiveDocument.C1892.Radius=0.661516
App.ActiveDocument.C1892.Height=20.00
App.ActiveDocument.C1892.Angle=360.00 
App.ActiveDocument.C1892.Placement=Base.Placement(Base.Vector(-27.313584,145.779586,-62.355373),Base.Rotation(-0.080040,-0.950237,0.000000,0.301070))
App.ActiveDocument.addObject("Part::Cylinder","C1893")
App.ActiveDocument.C1893.Radius=0.662059
App.ActiveDocument.C1893.Height=20.00
App.ActiveDocument.C1893.Angle=360.00 
App.ActiveDocument.C1893.Placement=Base.Placement(Base.Vector(-26.963427,141.796561,-62.744258),Base.Rotation(-0.022187,-0.948433,0.000000,0.316201))
App.ActiveDocument.addObject("Part::Cylinder","C1894")
App.ActiveDocument.C1894.Radius=0.662757
App.ActiveDocument.C1894.Height=20.00
App.ActiveDocument.C1894.Angle=360.00 
App.ActiveDocument.C1894.Placement=Base.Placement(Base.Vector(-26.351027,137.451773,-63.179027),Base.Rotation(0.042269,-0.940410,0.000000,0.337406))
App.ActiveDocument.addObject("Part::Cylinder","C1895")
App.ActiveDocument.C1895.Radius=0.663161
App.ActiveDocument.C1895.Height=20.00
App.ActiveDocument.C1895.Angle=360.00 
App.ActiveDocument.C1895.Placement=Base.Placement(Base.Vector(-25.840705,133.378462,-63.374497),Base.Rotation(0.089064,-0.931920,0.000000,0.351559))
App.ActiveDocument.addObject("Part::Cylinder","C1896")
App.ActiveDocument.C1896.Radius=0.662085
App.ActiveDocument.C1896.Height=20.00
App.ActiveDocument.C1896.Angle=360.00 
App.ActiveDocument.C1896.Placement=Base.Placement(Base.Vector(-25.553606,129.323892,-63.166683),Base.Rotation(0.164519,-0.913352,0.000000,0.372453))
App.ActiveDocument.addObject("Part::Cylinder","C1897")
App.ActiveDocument.C1897.Radius=0.660805
App.ActiveDocument.C1897.Height=20.00
App.ActiveDocument.C1897.Angle=360.00 
App.ActiveDocument.C1897.Placement=Base.Placement(Base.Vector(-25.420291,125.534780,-62.534180),Base.Rotation(0.237394,-0.895402,0.000000,0.376694))
App.ActiveDocument.addObject("Part::Cylinder","C1898")
App.ActiveDocument.C1898.Radius=0.657452
App.ActiveDocument.C1898.Height=20.00
App.ActiveDocument.C1898.Angle=360.00 
App.ActiveDocument.C1898.Placement=Base.Placement(Base.Vector(-25.653124,122.527964,-61.348955),Base.Rotation(0.345543,-0.852629,0.000000,0.391950))
App.ActiveDocument.addObject("Part::Cylinder","C1899")
App.ActiveDocument.C1899.Radius=0.654965
App.ActiveDocument.C1899.Height=20.00
App.ActiveDocument.C1899.Angle=360.00 
App.ActiveDocument.C1899.Placement=Base.Placement(Base.Vector(-25.408800,119.417379,-60.190649),Base.Rotation(0.395496,-0.826122,0.000000,0.401381))
App.ActiveDocument.addObject("Part::Cylinder","C1900")
App.ActiveDocument.C1900.Radius=0.649996
App.ActiveDocument.C1900.Height=20.00
App.ActiveDocument.C1900.Angle=360.00 
App.ActiveDocument.C1900.Placement=Base.Placement(Base.Vector(-25.749539,116.594182,-58.381391),Base.Rotation(0.434305,-0.799097,0.000000,0.415719))
App.ActiveDocument.addObject("Part::Cylinder","C1901")
App.ActiveDocument.C1901.Radius=0.646208
App.ActiveDocument.C1901.Height=20.00
App.ActiveDocument.C1901.Angle=360.00 
App.ActiveDocument.C1901.Placement=Base.Placement(Base.Vector(-25.674009,113.133306,-56.459621),Base.Rotation(0.492942,-0.763899,0.000000,0.416493))
App.ActiveDocument.addObject("Part::Cylinder","C1902")
App.ActiveDocument.C1902.Radius=0.641777
App.ActiveDocument.C1902.Height=20.00
App.ActiveDocument.C1902.Angle=360.00 
App.ActiveDocument.C1902.Placement=Base.Placement(Base.Vector(-25.649314,109.551284,-54.119031),Base.Rotation(0.534597,-0.739568,0.000000,0.408957))
App.ActiveDocument.addObject("Part::Cylinder","C1903")
App.ActiveDocument.C1903.Radius=0.638953
App.ActiveDocument.C1903.Height=20.00
App.ActiveDocument.C1903.Angle=360.00 
App.ActiveDocument.C1903.Placement=Base.Placement(Base.Vector(-27.502628,109.736380,-55.243754),Base.Rotation(0.782375,-0.236765,0.000000,0.576048))
App.ActiveDocument.addObject("Part::Cylinder","C1904")
App.ActiveDocument.C1904.Radius=0.511138
App.ActiveDocument.C1904.Height=20.00
App.ActiveDocument.C1904.Angle=360.00 
App.ActiveDocument.C1904.Placement=Base.Placement(Base.Vector(-31.627140,196.610103,-4.417293),Base.Rotation(-0.607380,-0.371243,0.000000,0.702330))
App.ActiveDocument.addObject("Part::Cylinder","C1905")
App.ActiveDocument.C1905.Radius=0.521487
App.ActiveDocument.C1905.Height=20.00
App.ActiveDocument.C1905.Angle=360.00 
App.ActiveDocument.C1905.Placement=Base.Placement(Base.Vector(-31.821484,196.354393,-8.966582),Base.Rotation(-0.613905,-0.380271,0.000000,0.691748))
App.ActiveDocument.addObject("Part::Cylinder","C1906")
App.ActiveDocument.C1906.Radius=0.531703
App.ActiveDocument.C1906.Height=20.00
App.ActiveDocument.C1906.Angle=360.00 
App.ActiveDocument.C1906.Placement=Base.Placement(Base.Vector(-31.886159,196.005395,-13.310642),Base.Rotation(-0.621577,-0.391683,0.000000,0.678400))
App.ActiveDocument.addObject("Part::Cylinder","C1907")
App.ActiveDocument.C1907.Radius=0.541908
App.ActiveDocument.C1907.Height=20.00
App.ActiveDocument.C1907.Angle=360.00 
App.ActiveDocument.C1907.Placement=Base.Placement(Base.Vector(-32.096275,195.346200,-17.712672),Base.Rotation(-0.629699,-0.402904,0.000000,0.664189))
App.ActiveDocument.addObject("Part::Cylinder","C1908")
App.ActiveDocument.C1908.Radius=0.551858
App.ActiveDocument.C1908.Height=20.00
App.ActiveDocument.C1908.Angle=360.00 
App.ActiveDocument.C1908.Placement=Base.Placement(Base.Vector(-32.237078,194.517350,-21.929100),Base.Rotation(-0.633924,-0.424859,0.000000,0.646247))
App.ActiveDocument.addObject("Part::Cylinder","C1909")
App.ActiveDocument.C1909.Radius=0.562777
App.ActiveDocument.C1909.Height=20.00
App.ActiveDocument.C1909.Angle=360.00 
App.ActiveDocument.C1909.Placement=Base.Placement(Base.Vector(-31.823386,193.822698,-26.099946),Base.Rotation(-0.647205,-0.434716,0.000000,0.626217))
App.ActiveDocument.addObject("Part::Cylinder","C1910")
App.ActiveDocument.C1910.Radius=0.571758
App.ActiveDocument.C1910.Height=20.00
App.ActiveDocument.C1910.Angle=360.00 
App.ActiveDocument.C1910.Placement=Base.Placement(Base.Vector(-32.175275,192.432235,-29.973889),Base.Rotation(-0.650007,-0.457623,0.000000,0.606690))
App.ActiveDocument.addObject("Part::Cylinder","C1911")
App.ActiveDocument.C1911.Radius=0.581643
App.ActiveDocument.C1911.Height=20.00
App.ActiveDocument.C1911.Angle=360.00 
App.ActiveDocument.C1911.Placement=Base.Placement(Base.Vector(-32.096023,191.041474,-33.879134),Base.Rotation(-0.656252,-0.478495,0.000000,0.583417))
App.ActiveDocument.addObject("Part::Cylinder","C1912")
App.ActiveDocument.C1912.Radius=0.591188
App.ActiveDocument.C1912.Height=20.00
App.ActiveDocument.C1912.Angle=360.00 
App.ActiveDocument.C1912.Placement=Base.Placement(Base.Vector(-32.004677,189.408018,-37.550092),Base.Rotation(-0.660214,-0.505094,0.000000,0.555875))
App.ActiveDocument.addObject("Part::Cylinder","C1913")
App.ActiveDocument.C1913.Radius=0.599837
App.ActiveDocument.C1913.Height=20.00
App.ActiveDocument.C1913.Angle=360.00 
App.ActiveDocument.C1913.Placement=Base.Placement(Base.Vector(-31.936758,187.596434,-40.743377),Base.Rotation(-0.661046,-0.537660,0.000000,0.523393))
App.ActiveDocument.addObject("Part::Cylinder","C1914")
App.ActiveDocument.C1914.Radius=0.607324
App.ActiveDocument.C1914.Height=20.00
App.ActiveDocument.C1914.Angle=360.00 
App.ActiveDocument.C1914.Placement=Base.Placement(Base.Vector(-32.132557,185.310783,-43.651969),Base.Rotation(-0.649582,-0.580298,0.000000,0.491221))
App.ActiveDocument.addObject("Part::Cylinder","C1915")
App.ActiveDocument.C1915.Radius=0.614645
App.ActiveDocument.C1915.Height=20.00
App.ActiveDocument.C1915.Angle=360.00 
App.ActiveDocument.C1915.Placement=Base.Placement(Base.Vector(-32.153353,182.912237,-46.291740),Base.Rotation(-0.635864,-0.623241,0.000000,0.455244))
App.ActiveDocument.addObject("Part::Cylinder","C1916")
App.ActiveDocument.C1916.Radius=0.620334
App.ActiveDocument.C1916.Height=20.00
App.ActiveDocument.C1916.Angle=360.00 
App.ActiveDocument.C1916.Placement=Base.Placement(Base.Vector(-32.392871,180.189166,-48.509378),Base.Rotation(-0.604428,-0.674102,0.000000,0.424562))
App.ActiveDocument.addObject("Part::Cylinder","C1917")
App.ActiveDocument.C1917.Radius=0.626290
App.ActiveDocument.C1917.Height=20.00
App.ActiveDocument.C1917.Angle=360.00 
App.ActiveDocument.C1917.Placement=Base.Placement(Base.Vector(-32.296204,177.276096,-50.707638),Base.Rotation(-0.558274,-0.729281,0.000000,0.395575))
App.ActiveDocument.addObject("Part::Cylinder","C1918")
App.ActiveDocument.C1918.Radius=0.631873
App.ActiveDocument.C1918.Height=20.00
App.ActiveDocument.C1918.Angle=360.00 
App.ActiveDocument.C1918.Placement=Base.Placement(Base.Vector(-32.028613,173.977211,-52.806495),Base.Rotation(-0.483711,-0.791992,0.000000,0.372522))
App.ActiveDocument.addObject("Part::Cylinder","C1919")
App.ActiveDocument.C1919.Radius=0.636383
App.ActiveDocument.C1919.Height=20.00
App.ActiveDocument.C1919.Angle=360.00 
App.ActiveDocument.C1919.Placement=Base.Placement(Base.Vector(-31.745327,170.687550,-54.505540),Base.Rotation(-0.416359,-0.836060,0.000000,0.357281))
App.ActiveDocument.addObject("Part::Cylinder","C1920")
App.ActiveDocument.C1920.Radius=0.640404
App.ActiveDocument.C1920.Height=20.00
App.ActiveDocument.C1920.Angle=360.00 
App.ActiveDocument.C1920.Placement=Base.Placement(Base.Vector(-31.510924,167.345726,-55.886139),Base.Rotation(-0.364044,-0.867385,0.000000,0.339286))
App.ActiveDocument.addObject("Part::Cylinder","C1921")
App.ActiveDocument.C1921.Radius=0.642770
App.ActiveDocument.C1921.Height=20.00
App.ActiveDocument.C1921.Angle=360.00 
App.ActiveDocument.C1921.Placement=Base.Placement(Base.Vector(-31.545513,163.752513,-56.878562),Base.Rotation(-0.297590,-0.895763,0.000000,0.330226))
App.ActiveDocument.addObject("Part::Cylinder","C1922")
App.ActiveDocument.C1922.Radius=0.645167
App.ActiveDocument.C1922.Height=20.00
App.ActiveDocument.C1922.Angle=360.00 
App.ActiveDocument.C1922.Placement=Base.Placement(Base.Vector(-31.441049,159.753385,-57.837441),Base.Rotation(-0.230969,-0.917466,0.000000,0.323897))
App.ActiveDocument.addObject("Part::Cylinder","C1923")
App.ActiveDocument.C1923.Radius=0.646343
App.ActiveDocument.C1923.Height=20.00
App.ActiveDocument.C1923.Angle=360.00 
App.ActiveDocument.C1923.Placement=Base.Placement(Base.Vector(-31.379896,156.055033,-58.491167),Base.Rotation(-0.158052,-0.931319,0.000000,0.328124))
App.ActiveDocument.addObject("Part::Cylinder","C1924")
App.ActiveDocument.C1924.Radius=0.648218
App.ActiveDocument.C1924.Height=20.00
App.ActiveDocument.C1924.Angle=360.00 
App.ActiveDocument.C1924.Placement=Base.Placement(Base.Vector(-30.912972,152.128223,-59.288854),Base.Rotation(-0.088532,-0.937556,0.000000,0.336380))
App.ActiveDocument.addObject("Part::Cylinder","C1925")
App.ActiveDocument.C1925.Radius=0.648402
App.ActiveDocument.C1925.Height=20.00
App.ActiveDocument.C1925.Angle=360.00 
App.ActiveDocument.C1925.Placement=Base.Placement(Base.Vector(-30.705309,148.139728,-59.685598),Base.Rotation(-0.020145,-0.934925,0.000000,0.354274))
App.ActiveDocument.addObject("Part::Cylinder","C1926")
App.ActiveDocument.C1926.Radius=0.648697
App.ActiveDocument.C1926.Height=20.00
App.ActiveDocument.C1926.Angle=360.00 
App.ActiveDocument.C1926.Placement=Base.Placement(Base.Vector(-30.421491,144.354413,-59.901164),Base.Rotation(0.034145,-0.930418,0.000000,0.364906))
App.ActiveDocument.addObject("Part::Cylinder","C1927")
App.ActiveDocument.C1927.Radius=0.649995
App.ActiveDocument.C1927.Height=20.00
App.ActiveDocument.C1927.Angle=360.00 
App.ActiveDocument.C1927.Placement=Base.Placement(Base.Vector(-29.706880,140.118191,-60.334689),Base.Rotation(0.073996,-0.923388,0.000000,0.376670))
App.ActiveDocument.addObject("Part::Cylinder","C1928")
App.ActiveDocument.C1928.Radius=0.650517
App.ActiveDocument.C1928.Height=20.00
App.ActiveDocument.C1928.Angle=360.00 
App.ActiveDocument.C1928.Placement=Base.Placement(Base.Vector(-29.120145,136.034603,-60.511995),Base.Rotation(0.102740,-0.915406,0.000000,0.389199))
App.ActiveDocument.addObject("Part::Cylinder","C1929")
App.ActiveDocument.C1929.Radius=0.650189
App.ActiveDocument.C1929.Height=20.00
App.ActiveDocument.C1929.Angle=360.00 
App.ActiveDocument.C1929.Placement=Base.Placement(Base.Vector(-28.683730,131.678190,-60.382548),Base.Rotation(0.133418,-0.906141,0.000000,0.401383))
App.ActiveDocument.addObject("Part::Cylinder","C1930")
App.ActiveDocument.C1930.Radius=0.648672
App.ActiveDocument.C1930.Height=20.00
App.ActiveDocument.C1930.Angle=360.00 
App.ActiveDocument.C1930.Placement=Base.Placement(Base.Vector(-28.513724,127.622843,-59.832658),Base.Rotation(0.178779,-0.893182,0.000000,0.412630))
App.ActiveDocument.addObject("Part::Cylinder","C1931")
App.ActiveDocument.C1931.Radius=0.645904
App.ActiveDocument.C1931.Height=20.00
App.ActiveDocument.C1931.Angle=360.00 
App.ActiveDocument.C1931.Placement=Base.Placement(Base.Vector(-28.632799,124.216212,-58.816073),Base.Rotation(0.234351,-0.875789,0.000000,0.421987))
App.ActiveDocument.addObject("Part::Cylinder","C1932")
App.ActiveDocument.C1932.Radius=0.642979
App.ActiveDocument.C1932.Height=20.00
App.ActiveDocument.C1932.Angle=360.00 
App.ActiveDocument.C1932.Placement=Base.Placement(Base.Vector(-28.566784,120.815985,-57.487496),Base.Rotation(0.346572,-0.832889,0.000000,0.431490))
App.ActiveDocument.addObject("Part::Cylinder","C1933")
App.ActiveDocument.C1933.Radius=0.636879
App.ActiveDocument.C1933.Height=20.00
App.ActiveDocument.C1933.Angle=360.00 
App.ActiveDocument.C1933.Placement=Base.Placement(Base.Vector(-28.955865,117.101813,-55.056205),Base.Rotation(0.376562,-0.816019,0.000000,0.438536))
App.ActiveDocument.addObject("Part::Cylinder","C1934")
App.ActiveDocument.C1934.Radius=0.633476
App.ActiveDocument.C1934.Height=20.00
App.ActiveDocument.C1934.Angle=360.00 
App.ActiveDocument.C1934.Placement=Base.Placement(Base.Vector(-28.723982,112.751569,-52.994286),Base.Rotation(0.406857,-0.807993,0.000000,0.426162))
App.ActiveDocument.addObject("Part::Cylinder","C1935")
App.ActiveDocument.C1935.Radius=0.629389
App.ActiveDocument.C1935.Height=20.00
App.ActiveDocument.C1935.Angle=360.00 
App.ActiveDocument.C1935.Placement=Base.Placement(Base.Vector(-28.822118,108.707949,-50.663508),Base.Rotation(0.450766,-0.793614,0.000000,0.408640))
App.ActiveDocument.addObject("Part::Cylinder","C1936")
App.ActiveDocument.C1936.Radius=0.626663
App.ActiveDocument.C1936.Height=20.00
App.ActiveDocument.C1936.Angle=360.00 
App.ActiveDocument.C1936.Placement=Base.Placement(Base.Vector(-30.480480,108.928342,-51.180098),Base.Rotation(0.775908,-0.320583,0.000000,0.543317))
App.ActiveDocument.addObject("Part::Cylinder","C1937")
App.ActiveDocument.C1937.Radius=0.505473
App.ActiveDocument.C1937.Height=20.00
App.ActiveDocument.C1937.Angle=360.00 
App.ActiveDocument.C1937.Placement=Base.Placement(Base.Vector(-34.835698,194.469071,-4.241529),Base.Rotation(-0.572549,-0.420788,0.000000,0.703651))
App.ActiveDocument.addObject("Part::Cylinder","C1938")
App.ActiveDocument.C1938.Radius=0.515451
App.ActiveDocument.C1938.Height=20.00
App.ActiveDocument.C1938.Angle=360.00 
App.ActiveDocument.C1938.Placement=Base.Placement(Base.Vector(-35.172224,194.087766,-8.642685),Base.Rotation(-0.580710,-0.430123,0.000000,0.691209))
App.ActiveDocument.addObject("Part::Cylinder","C1939")
App.ActiveDocument.C1939.Radius=0.525665
App.ActiveDocument.C1939.Height=20.00
App.ActiveDocument.C1939.Angle=360.00 
App.ActiveDocument.C1939.Placement=Base.Placement(Base.Vector(-35.222323,193.724078,-13.022760),Base.Rotation(-0.585125,-0.443259,0.000000,0.679081))
App.ActiveDocument.addObject("Part::Cylinder","C1940")
App.ActiveDocument.C1940.Radius=0.535675
App.ActiveDocument.C1940.Height=20.00
App.ActiveDocument.C1940.Angle=360.00 
App.ActiveDocument.C1940.Placement=Base.Placement(Base.Vector(-35.454037,192.985977,-17.407307),Base.Rotation(-0.584466,-0.466369,0.000000,0.664002))
App.ActiveDocument.addObject("Part::Cylinder","C1941")
App.ActiveDocument.C1941.Radius=0.546077
App.ActiveDocument.C1941.Height=20.00
App.ActiveDocument.C1941.Angle=360.00 
App.ActiveDocument.C1941.Placement=Base.Placement(Base.Vector(-35.524166,192.129091,-21.729446),Base.Rotation(-0.591262,-0.482704,0.000000,0.646070))
App.ActiveDocument.addObject("Part::Cylinder","C1942")
App.ActiveDocument.C1942.Radius=0.557128
App.ActiveDocument.C1942.Height=20.00
App.ActiveDocument.C1942.Angle=360.00 
App.ActiveDocument.C1942.Placement=Base.Placement(Base.Vector(-35.176216,191.347774,-26.063356),Base.Rotation(-0.601681,-0.493022,0.000000,0.628418))
App.ActiveDocument.addObject("Part::Cylinder","C1943")
App.ActiveDocument.C1943.Radius=0.566183
App.ActiveDocument.C1943.Height=20.00
App.ActiveDocument.C1943.Angle=360.00 
App.ActiveDocument.C1943.Placement=Base.Placement(Base.Vector(-35.592024,189.778536,-29.974226),Base.Rotation(-0.604034,-0.514613,0.000000,0.608536))
App.ActiveDocument.addObject("Part::Cylinder","C1944")
App.ActiveDocument.C1944.Radius=0.576172
App.ActiveDocument.C1944.Height=20.00
App.ActiveDocument.C1944.Angle=360.00 
App.ActiveDocument.C1944.Placement=Base.Placement(Base.Vector(-35.473086,188.363247,-33.831282),Base.Rotation(-0.611570,-0.534007,0.000000,0.583797))
App.ActiveDocument.addObject("Part::Cylinder","C1945")
App.ActiveDocument.C1945.Radius=0.585480
App.ActiveDocument.C1945.Height=20.00
App.ActiveDocument.C1945.Angle=360.00 
App.ActiveDocument.C1945.Placement=Base.Placement(Base.Vector(-35.458317,186.611702,-37.365103),Base.Rotation(-0.614314,-0.561886,0.000000,0.553988))
App.ActiveDocument.addObject("Part::Cylinder","C1946")
App.ActiveDocument.C1946.Radius=0.593586
App.ActiveDocument.C1946.Height=20.00
App.ActiveDocument.C1946.Angle=360.00 
App.ActiveDocument.C1946.Placement=Base.Placement(Base.Vector(-35.500668,184.632690,-40.409140),Base.Rotation(-0.605767,-0.600459,0.000000,0.522011))
App.ActiveDocument.addObject("Part::Cylinder","C1947")
App.ActiveDocument.C1947.Radius=0.600743
App.ActiveDocument.C1947.Height=20.00
App.ActiveDocument.C1947.Angle=360.00 
App.ActiveDocument.C1947.Placement=Base.Placement(Base.Vector(-35.678332,182.208617,-43.165223),Base.Rotation(-0.589664,-0.640919,0.000000,0.491446))
App.ActiveDocument.addObject("Part::Cylinder","C1948")
App.ActiveDocument.C1948.Radius=0.606844
App.ActiveDocument.C1948.Height=20.00
App.ActiveDocument.C1948.Angle=360.00 
App.ActiveDocument.C1948.Placement=Base.Placement(Base.Vector(-35.758640,179.802008,-45.439144),Base.Rotation(-0.551842,-0.695793,0.000000,0.459719))
App.ActiveDocument.addObject("Part::Cylinder","C1949")
App.ActiveDocument.C1949.Radius=0.612888
App.ActiveDocument.C1949.Height=20.00
App.ActiveDocument.C1949.Angle=360.00 
App.ActiveDocument.C1949.Placement=Base.Placement(Base.Vector(-35.614529,177.192334,-47.629303),Base.Rotation(-0.501592,-0.750034,0.000000,0.431108))
App.ActiveDocument.addObject("Part::Cylinder","C1950")
App.ActiveDocument.C1950.Radius=0.618426
App.ActiveDocument.C1950.Height=20.00
App.ActiveDocument.C1950.Angle=360.00 
App.ActiveDocument.C1950.Placement=Base.Placement(Base.Vector(-35.407764,174.296427,-49.619222),Base.Rotation(-0.447522,-0.796391,0.000000,0.406799))
App.ActiveDocument.addObject("Part::Cylinder","C1951")
App.ActiveDocument.C1951.Radius=0.622680
App.ActiveDocument.C1951.Height=20.00
App.ActiveDocument.C1951.Angle=360.00 
App.ActiveDocument.C1951.Placement=Base.Placement(Base.Vector(-35.287978,171.201386,-51.212558),Base.Rotation(-0.377970,-0.840472,0.000000,0.388260))
App.ActiveDocument.addObject("Part::Cylinder","C1952")
App.ActiveDocument.C1952.Radius=0.626551
App.ActiveDocument.C1952.Height=20.00
App.ActiveDocument.C1952.Angle=360.00 
App.ActiveDocument.C1952.Placement=Base.Placement(Base.Vector(-35.107339,167.500817,-52.777817),Base.Rotation(-0.314555,-0.869996,0.000000,0.379687))
App.ActiveDocument.addObject("Part::Cylinder","C1953")
App.ActiveDocument.C1953.Radius=0.629860
App.ActiveDocument.C1953.Height=20.00
App.ActiveDocument.C1953.Angle=360.00 
App.ActiveDocument.C1953.Placement=Base.Placement(Base.Vector(-34.838618,164.097426,-54.047639),Base.Rotation(-0.253167,-0.892660,0.000000,0.372914))
App.ActiveDocument.addObject("Part::Cylinder","C1954")
App.ActiveDocument.C1954.Radius=0.631788
App.ActiveDocument.C1954.Height=20.00
App.ActiveDocument.C1954.Angle=360.00 
App.ActiveDocument.C1954.Placement=Base.Placement(Base.Vector(-34.670722,160.738465,-54.962130),Base.Rotation(-0.174867,-0.910271,0.000000,0.375271))
App.ActiveDocument.addObject("Part::Cylinder","C1955")
App.ActiveDocument.C1955.Radius=0.633032
App.ActiveDocument.C1955.Height=20.00
App.ActiveDocument.C1955.Angle=360.00 
App.ActiveDocument.C1955.Placement=Base.Placement(Base.Vector(-34.455871,157.186393,-55.697938),Base.Rotation(-0.092361,-0.918139,0.000000,0.385345))
App.ActiveDocument.addObject("Part::Cylinder","C1956")
App.ActiveDocument.C1956.Radius=0.634847
App.ActiveDocument.C1956.Height=20.00
App.ActiveDocument.C1956.Angle=360.00 
App.ActiveDocument.C1956.Placement=Base.Placement(Base.Vector(-34.014561,153.528002,-56.402649),Base.Rotation(-0.039235,-0.919730,0.000000,0.390585))
App.ActiveDocument.addObject("Part::Cylinder","C1957")
App.ActiveDocument.C1957.Radius=0.635685
App.ActiveDocument.C1957.Height=20.00
App.ActiveDocument.C1957.Angle=360.00 
App.ActiveDocument.C1957.Placement=Base.Placement(Base.Vector(-33.646172,149.507489,-56.813253),Base.Rotation(0.014355,-0.916148,0.000000,0.400582))
App.ActiveDocument.addObject("Part::Cylinder","C1958")
App.ActiveDocument.C1958.Radius=0.635536
App.ActiveDocument.C1958.Height=20.00
App.ActiveDocument.C1958.Angle=360.00 
App.ActiveDocument.C1958.Placement=Base.Placement(Base.Vector(-33.359242,145.576748,-56.921984),Base.Rotation(0.058479,-0.908008,0.000000,0.414851))
App.ActiveDocument.addObject("Part::Cylinder","C1959")
App.ActiveDocument.C1959.Radius=0.636233
App.ActiveDocument.C1959.Height=20.00
App.ActiveDocument.C1959.Angle=360.00 
App.ActiveDocument.C1959.Placement=Base.Placement(Base.Vector(-32.854515,141.940823,-57.122613),Base.Rotation(0.097382,-0.900906,0.000000,0.422949))
App.ActiveDocument.addObject("Part::Cylinder","C1960")
App.ActiveDocument.C1960.Radius=0.637736
App.ActiveDocument.C1960.Height=20.00
App.ActiveDocument.C1960.Angle=360.00 
App.ActiveDocument.C1960.Placement=Base.Placement(Base.Vector(-32.059522,138.160187,-57.497539),Base.Rotation(0.123449,-0.894189,0.000000,0.430333))
App.ActiveDocument.addObject("Part::Cylinder","C1961")
App.ActiveDocument.C1961.Radius=0.636978
App.ActiveDocument.C1961.Height=20.00
App.ActiveDocument.C1961.Angle=360.00 
App.ActiveDocument.C1961.Placement=Base.Placement(Base.Vector(-31.698314,134.217629,-57.218302),Base.Rotation(0.141440,-0.885828,0.000000,0.441931))
App.ActiveDocument.addObject("Part::Cylinder","C1962")
App.ActiveDocument.C1962.Radius=0.636219
App.ActiveDocument.C1962.Height=20.00
App.ActiveDocument.C1962.Angle=360.00 
App.ActiveDocument.C1962.Placement=Base.Placement(Base.Vector(-31.249156,129.918431,-56.874999),Base.Rotation(0.153326,-0.878287,0.000000,0.452883))
App.ActiveDocument.addObject("Part::Cylinder","C1963")
App.ActiveDocument.C1963.Radius=0.633318
App.ActiveDocument.C1963.Height=20.00
App.ActiveDocument.C1963.Angle=360.00 
App.ActiveDocument.C1963.Placement=Base.Placement(Base.Vector(-31.336462,126.166187,-55.808481),Base.Rotation(0.174708,-0.869833,0.000000,0.461376))
App.ActiveDocument.addObject("Part::Cylinder","C1964")
App.ActiveDocument.C1964.Radius=0.631007
App.ActiveDocument.C1964.Height=20.00
App.ActiveDocument.C1964.Angle=360.00 
App.ActiveDocument.C1964.Placement=Base.Placement(Base.Vector(-31.269042,122.559518,-54.761725),Base.Rotation(0.226561,-0.855480,0.000000,0.465644))
App.ActiveDocument.addObject("Part::Cylinder","C1965")
App.ActiveDocument.C1965.Radius=0.628203
App.ActiveDocument.C1965.Height=20.00
App.ActiveDocument.C1965.Angle=360.00 
App.ActiveDocument.C1965.Placement=Base.Placement(Base.Vector(-31.381201,119.635044,-53.388861),Base.Rotation(0.281959,-0.840450,0.000000,0.462757))
App.ActiveDocument.addObject("Part::Cylinder","C1966")
App.ActiveDocument.C1966.Radius=0.622911
App.ActiveDocument.C1966.Height=20.00
App.ActiveDocument.C1966.Angle=360.00 
App.ActiveDocument.C1966.Placement=Base.Placement(Base.Vector(-31.737269,115.744054,-50.985835),Base.Rotation(0.316856,-0.831089,0.000000,0.457049))
App.ActiveDocument.addObject("Part::Cylinder","C1967")
App.ActiveDocument.C1967.Radius=0.619806
App.ActiveDocument.C1967.Height=20.00
App.ActiveDocument.C1967.Angle=360.00 
App.ActiveDocument.C1967.Placement=Base.Placement(Base.Vector(-31.470023,111.637986,-49.198908),Base.Rotation(0.339840,-0.825606,0.000000,0.450427))
App.ActiveDocument.addObject("Part::Cylinder","C1968")
App.ActiveDocument.C1968.Radius=0.616730
App.ActiveDocument.C1968.Height=20.00
App.ActiveDocument.C1968.Angle=360.00 
App.ActiveDocument.C1968.Placement=Base.Placement(Base.Vector(-31.177931,107.290085,-47.390444),Base.Rotation(0.342149,-0.829639,0.000000,0.441173))
App.ActiveDocument.addObject("Part::Cylinder","C1969")
App.ActiveDocument.C1969.Radius=0.614166
App.ActiveDocument.C1969.Height=20.00
App.ActiveDocument.C1969.Angle=360.00 
App.ActiveDocument.C1969.Placement=Base.Placement(Base.Vector(-34.186113,109.486698,-49.007012),Base.Rotation(0.755028,-0.218304,0.000000,0.618285))
App.ActiveDocument.addObject("Part::Cylinder","C1970")
App.ActiveDocument.C1970.Radius=0.500509
App.ActiveDocument.C1970.Height=20.00
App.ActiveDocument.C1970.Angle=360.00 
App.ActiveDocument.C1970.Placement=Base.Placement(Base.Vector(-37.768022,191.995622,-4.381814),Base.Rotation(-0.516047,-0.484833,0.000000,0.706139))
App.ActiveDocument.addObject("Part::Cylinder","C1971")
App.ActiveDocument.C1971.Radius=0.510519
App.ActiveDocument.C1971.Height=20.00
App.ActiveDocument.C1971.Angle=360.00 
App.ActiveDocument.C1971.Placement=Base.Placement(Base.Vector(-38.007850,191.659530,-8.743425),Base.Rotation(-0.523151,-0.494631,0.000000,0.694013))
App.ActiveDocument.addObject("Part::Cylinder","C1972")
App.ActiveDocument.C1972.Radius=0.520706
App.ActiveDocument.C1972.Height=20.00
App.ActiveDocument.C1972.Angle=360.00 
App.ActiveDocument.C1972.Placement=Base.Placement(Base.Vector(-38.195107,191.160786,-13.077924),Base.Rotation(-0.534485,-0.501612,0.000000,0.680229))
App.ActiveDocument.addObject("Part::Cylinder","C1973")
App.ActiveDocument.C1973.Radius=0.530237
App.ActiveDocument.C1973.Height=20.00
App.ActiveDocument.C1973.Angle=360.00 
App.ActiveDocument.C1973.Placement=Base.Placement(Base.Vector(-38.547107,190.284515,-17.307291),Base.Rotation(-0.533399,-0.521531,0.000000,0.665951))
App.ActiveDocument.addObject("Part::Cylinder","C1974")
App.ActiveDocument.C1974.Radius=0.541198
App.ActiveDocument.C1974.Height=20.00
App.ActiveDocument.C1974.Angle=360.00 
App.ActiveDocument.C1974.Placement=Base.Placement(Base.Vector(-38.437116,189.549230,-21.758558),Base.Rotation(-0.544575,-0.530360,0.000000,0.649736))
App.ActiveDocument.addObject("Part::Cylinder","C1975")
App.ActiveDocument.C1975.Radius=0.551241
App.ActiveDocument.C1975.Height=20.00
App.ActiveDocument.C1975.Angle=360.00 
App.ActiveDocument.C1975.Placement=Base.Placement(Base.Vector(-38.432873,188.502900,-25.917400),Base.Rotation(-0.546911,-0.547743,0.000000,0.633140))
App.ActiveDocument.addObject("Part::Cylinder","C1976")
App.ActiveDocument.C1976.Radius=0.560996
App.ActiveDocument.C1976.Height=20.00
App.ActiveDocument.C1976.Angle=360.00 
App.ActiveDocument.C1976.Placement=Base.Placement(Base.Vector(-38.577381,187.042665,-29.961294),Base.Rotation(-0.544380,-0.573586,0.000000,0.612087))
App.ActiveDocument.addObject("Part::Cylinder","C1977")
App.ActiveDocument.C1977.Radius=0.571031
App.ActiveDocument.C1977.Height=20.00
App.ActiveDocument.C1977.Angle=360.00 
App.ActiveDocument.C1977.Placement=Base.Placement(Base.Vector(-38.435129,185.588087,-33.801954),Base.Rotation(-0.549746,-0.594397,0.000000,0.586918))
App.ActiveDocument.addObject("Part::Cylinder","C1978")
App.ActiveDocument.C1978.Radius=0.579437
App.ActiveDocument.C1978.Height=20.00
App.ActiveDocument.C1978.Angle=360.00 
App.ActiveDocument.C1978.Placement=Base.Placement(Base.Vector(-38.612985,183.620333,-37.072238),Base.Rotation(-0.542576,-0.628253,0.000000,0.557593))
App.ActiveDocument.addObject("Part::Cylinder","C1979")
App.ActiveDocument.C1979.Radius=0.587000
App.ActiveDocument.C1979.Height=20.00
App.ActiveDocument.C1979.Angle=360.00 
App.ActiveDocument.C1979.Placement=Base.Placement(Base.Vector(-38.753831,181.353009,-40.021101),Base.Rotation(-0.526687,-0.664394,0.000000,0.530266))
App.ActiveDocument.addObject("Part::Cylinder","C1980")
App.ActiveDocument.C1980.Radius=0.593316
App.ActiveDocument.C1980.Height=20.00
App.ActiveDocument.C1980.Angle=360.00 
App.ActiveDocument.C1980.Placement=Base.Placement(Base.Vector(-38.866446,179.185510,-42.209714),Base.Rotation(-0.498619,-0.712242,0.000000,0.494054))
App.ActiveDocument.addObject("Part::Cylinder","C1981")
App.ActiveDocument.C1981.Radius=0.599155
App.ActiveDocument.C1981.Height=20.00
App.ActiveDocument.C1981.Angle=360.00 
App.ActiveDocument.C1981.Placement=Base.Placement(Base.Vector(-38.951910,176.407685,-44.428537),Base.Rotation(-0.449029,-0.762030,0.000000,0.466566))
App.ActiveDocument.addObject("Part::Cylinder","C1982")
App.ActiveDocument.C1982.Radius=0.604702
App.ActiveDocument.C1982.Height=20.00
App.ActiveDocument.C1982.Angle=360.00 
App.ActiveDocument.C1982.Placement=Base.Placement(Base.Vector(-38.790403,173.775246,-46.331790),Base.Rotation(-0.397321,-0.805810,0.000000,0.439098))
App.ActiveDocument.addObject("Part::Cylinder","C1983")
App.ActiveDocument.C1983.Radius=0.609584
App.ActiveDocument.C1983.Height=20.00
App.ActiveDocument.C1983.Angle=360.00 
App.ActiveDocument.C1983.Placement=Base.Placement(Base.Vector(-38.556052,170.806306,-48.081518),Base.Rotation(-0.328884,-0.846140,0.000000,0.419383))
App.ActiveDocument.addObject("Part::Cylinder","C1984")
App.ActiveDocument.C1984.Radius=0.613625
App.ActiveDocument.C1984.Height=20.00
App.ActiveDocument.C1984.Angle=360.00 
App.ActiveDocument.C1984.Placement=Base.Placement(Base.Vector(-38.343590,167.422644,-49.589861),Base.Rotation(-0.272371,-0.871758,0.000000,0.407249))
App.ActiveDocument.addObject("Part::Cylinder","C1985")
App.ActiveDocument.C1985.Radius=0.616384
App.ActiveDocument.C1985.Height=20.00
App.ActiveDocument.C1985.Angle=360.00 
App.ActiveDocument.C1985.Placement=Base.Placement(Base.Vector(-38.054449,164.051970,-50.812936),Base.Rotation(-0.181127,-0.894633,0.000000,0.408442))
App.ActiveDocument.addObject("Part::Cylinder","C1986")
App.ActiveDocument.C1986.Radius=0.618197
App.ActiveDocument.C1986.Height=20.00
App.ActiveDocument.C1986.Angle=360.00 
App.ActiveDocument.C1986.Placement=Base.Placement(Base.Vector(-37.826669,160.856668,-51.623280),Base.Rotation(-0.112670,-0.904556,0.000000,0.411197))
App.ActiveDocument.addObject("Part::Cylinder","C1987")
App.ActiveDocument.C1987.Radius=0.620630
App.ActiveDocument.C1987.Height=20.00
App.ActiveDocument.C1987.Angle=360.00 
App.ActiveDocument.C1987.Placement=Base.Placement(Base.Vector(-37.281357,157.370680,-52.557235),Base.Rotation(-0.042813,-0.908232,0.000000,0.416271))
App.ActiveDocument.addObject("Part::Cylinder","C1988")
App.ActiveDocument.C1988.Radius=0.621453
App.ActiveDocument.C1988.Height=20.00
App.ActiveDocument.C1988.Angle=360.00 
App.ActiveDocument.C1988.Placement=Base.Placement(Base.Vector(-37.014939,154.238106,-52.941721),Base.Rotation(-0.002302,-0.906210,0.000000,0.422821))
App.ActiveDocument.addObject("Part::Cylinder","C1989")
App.ActiveDocument.C1989.Radius=0.621486
App.ActiveDocument.C1989.Height=20.00
App.ActiveDocument.C1989.Angle=360.00 
App.ActiveDocument.C1989.Placement=Base.Placement(Base.Vector(-36.826034,150.609370,-53.061421),Base.Rotation(0.037209,-0.901328,0.000000,0.431536))
App.ActiveDocument.addObject("Part::Cylinder","C1990")
App.ActiveDocument.C1990.Radius=0.622097
App.ActiveDocument.C1990.Height=20.00
App.ActiveDocument.C1990.Angle=360.00 
App.ActiveDocument.C1990.Placement=Base.Placement(Base.Vector(-36.436361,147.091970,-53.271458),Base.Rotation(0.067411,-0.896243,0.000000,0.438410))
App.ActiveDocument.addObject("Part::Cylinder","C1991")
App.ActiveDocument.C1991.Radius=0.622657
App.ActiveDocument.C1991.Height=20.00
App.ActiveDocument.C1991.Angle=360.00 
App.ActiveDocument.C1991.Placement=Base.Placement(Base.Vector(-35.897747,142.916846,-53.424674),Base.Rotation(0.106329,-0.887763,0.000000,0.447851))
App.ActiveDocument.addObject("Part::Cylinder","C1992")
App.ActiveDocument.C1992.Radius=0.624136
App.ActiveDocument.C1992.Height=20.00
App.ActiveDocument.C1992.Angle=360.00 
App.ActiveDocument.C1992.Placement=Base.Placement(Base.Vector(-35.141684,138.959658,-53.704360),Base.Rotation(0.134529,-0.882272,0.000000,0.451109))
App.ActiveDocument.addObject("Part::Cylinder","C1993")
App.ActiveDocument.C1993.Radius=0.624140
App.ActiveDocument.C1993.Height=20.00
App.ActiveDocument.C1993.Angle=360.00 
App.ActiveDocument.C1993.Placement=Base.Placement(Base.Vector(-34.686135,135.370856,-53.516783),Base.Rotation(0.151561,-0.877510,0.000000,0.454978))
App.ActiveDocument.addObject("Part::Cylinder","C1994")
App.ActiveDocument.C1994.Radius=0.623434
App.ActiveDocument.C1994.Height=20.00
App.ActiveDocument.C1994.Angle=360.00 
App.ActiveDocument.C1994.Placement=Base.Placement(Base.Vector(-34.341765,131.706128,-53.074628),Base.Rotation(0.163196,-0.873461,0.000000,0.458729))
App.ActiveDocument.addObject("Part::Cylinder","C1995")
App.ActiveDocument.C1995.Radius=0.621701
App.ActiveDocument.C1995.Height=20.00
App.ActiveDocument.C1995.Angle=360.00 
App.ActiveDocument.C1995.Placement=Base.Placement(Base.Vector(-34.224416,128.278057,-52.314110),Base.Rotation(0.176597,-0.868576,0.000000,0.463023))
App.ActiveDocument.addObject("Part::Cylinder","C1996")
App.ActiveDocument.C1996.Radius=0.618247
App.ActiveDocument.C1996.Height=20.00
App.ActiveDocument.C1996.Angle=360.00 
App.ActiveDocument.C1996.Placement=Base.Placement(Base.Vector(-34.352079,124.486541,-50.954263),Base.Rotation(0.201184,-0.859846,0.000000,0.469243))
App.ActiveDocument.addObject("Part::Cylinder","C1997")
App.ActiveDocument.C1997.Radius=0.615623
App.ActiveDocument.C1997.Height=20.00
App.ActiveDocument.C1997.Angle=360.00 
App.ActiveDocument.C1997.Placement=Base.Placement(Base.Vector(-34.094009,120.300377,-49.753743),Base.Rotation(0.235968,-0.846734,0.000000,0.476823))
App.ActiveDocument.addObject("Part::Cylinder","C1998")
App.ActiveDocument.C1998.Radius=0.610192
App.ActiveDocument.C1998.Height=20.00
App.ActiveDocument.C1998.Angle=360.00 
App.ActiveDocument.C1998.Placement=Base.Placement(Base.Vector(-34.479204,116.317192,-47.490517),Base.Rotation(0.253368,-0.841699,0.000000,0.476809))
App.ActiveDocument.addObject("Part::Cylinder","C1999")
App.ActiveDocument.C1999.Radius=0.607484
App.ActiveDocument.C1999.Height=20.00
App.ActiveDocument.C1999.Angle=360.00 
App.ActiveDocument.C1999.Placement=Base.Placement(Base.Vector(-34.231835,112.239659,-45.858923),Base.Rotation(0.304404,-0.828077,0.000000,0.470773))
App.ActiveDocument.addObject("Part::Cylinder","C2000")
App.ActiveDocument.C2000.Radius=0.604256
App.ActiveDocument.C2000.Height=20.00
App.ActiveDocument.C2000.Angle=360.00 
App.ActiveDocument.C2000.Placement=Base.Placement(Base.Vector(-33.844386,107.657579,-44.018678),Base.Rotation(0.304155,-0.831291,0.000000,0.465237))
App.ActiveDocument.addObject("Part::Cylinder","C2001")
App.ActiveDocument.C2001.Radius=0.602277
App.ActiveDocument.C2001.Height=20.00
App.ActiveDocument.C2001.Angle=360.00 
App.ActiveDocument.C2001.Placement=Base.Placement(Base.Vector(-35.142875,108.193981,-44.415594),Base.Rotation(0.689497,-0.451084,0.000000,0.566673))
App.ActiveDocument.addObject("Part::Cylinder","C2002")
App.ActiveDocument.C2002.Radius=0.495804
App.ActiveDocument.C2002.Height=20.00
App.ActiveDocument.C2002.Angle=360.00 
App.ActiveDocument.C2002.Placement=Base.Placement(Base.Vector(-40.510914,189.178943,-4.373905),Base.Rotation(-0.465976,-0.529448,0.000000,0.708908))
App.ActiveDocument.addObject("Part::Cylinder","C2003")
App.ActiveDocument.C2003.Radius=0.506231
App.ActiveDocument.C2003.Height=20.00
App.ActiveDocument.C2003.Angle=360.00 
App.ActiveDocument.C2003.Placement=Base.Placement(Base.Vector(-40.924784,188.633361,-9.027479),Base.Rotation(-0.472596,-0.539421,0.000000,0.696906))
App.ActiveDocument.addObject("Part::Cylinder","C2004")
App.ActiveDocument.C2004.Radius=0.516591
App.ActiveDocument.C2004.Height=20.00
App.ActiveDocument.C2004.Angle=360.00 
App.ActiveDocument.C2004.Placement=Base.Placement(Base.Vector(-41.071729,188.156781,-13.397472),Base.Rotation(-0.484720,-0.546725,0.000000,0.682743))
App.ActiveDocument.addObject("Part::Cylinder","C2005")
App.ActiveDocument.C2005.Radius=0.526563
App.ActiveDocument.C2005.Height=20.00
App.ActiveDocument.C2005.Angle=360.00 
App.ActiveDocument.C2005.Placement=Base.Placement(Base.Vector(-41.400980,187.206535,-17.713425),Base.Rotation(-0.486505,-0.565439,0.000000,0.666027))
App.ActiveDocument.addObject("Part::Cylinder","C2006")
App.ActiveDocument.C2006.Radius=0.536593
App.ActiveDocument.C2006.Height=20.00
App.ActiveDocument.C2006.Angle=360.00 
App.ActiveDocument.C2006.Placement=Base.Placement(Base.Vector(-41.281191,186.515856,-21.813198),Base.Rotation(-0.489736,-0.579876,0.000000,0.651078))
App.ActiveDocument.addObject("Part::Cylinder","C2007")
App.ActiveDocument.C2007.Radius=0.546290
App.ActiveDocument.C2007.Height=20.00
App.ActiveDocument.C2007.Angle=360.00 
App.ActiveDocument.C2007.Placement=Base.Placement(Base.Vector(-41.314978,185.386302,-25.834686),Base.Rotation(-0.492473,-0.594888,0.000000,0.635278))
App.ActiveDocument.addObject("Part::Cylinder","C2008")
App.ActiveDocument.C2008.Radius=0.556339
App.ActiveDocument.C2008.Height=20.00
App.ActiveDocument.C2008.Angle=360.00 
App.ActiveDocument.C2008.Placement=Base.Placement(Base.Vector(-41.294564,183.965869,-29.921476),Base.Rotation(-0.487248,-0.619874,0.000000,0.615099))
App.ActiveDocument.addObject("Part::Cylinder","C2009")
App.ActiveDocument.C2009.Radius=0.565429
App.ActiveDocument.C2009.Height=20.00
App.ActiveDocument.C2009.Angle=360.00 
App.ActiveDocument.C2009.Placement=Base.Placement(Base.Vector(-41.208254,182.450382,-33.471152),Base.Rotation(-0.478563,-0.648463,0.000000,0.592008))
App.ActiveDocument.addObject("Part::Cylinder","C2010")
App.ActiveDocument.C2010.Radius=0.573105
App.ActiveDocument.C2010.Height=20.00
App.ActiveDocument.C2010.Angle=360.00 
App.ActiveDocument.C2010.Placement=Base.Placement(Base.Vector(-41.389177,180.363346,-36.535487),Base.Rotation(-0.457347,-0.685265,0.000000,0.566786))
App.ActiveDocument.addObject("Part::Cylinder","C2011")
App.ActiveDocument.C2011.Radius=0.579785
App.ActiveDocument.C2011.Height=20.00
App.ActiveDocument.C2011.Angle=360.00 
App.ActiveDocument.C2011.Placement=Base.Placement(Base.Vector(-41.514216,178.060372,-39.153627),Base.Rotation(-0.427014,-0.723454,0.000000,0.542470))
App.ActiveDocument.addObject("Part::Cylinder","C2012")
App.ActiveDocument.C2012.Radius=0.586045
App.ActiveDocument.C2012.Height=20.00
App.ActiveDocument.C2012.Angle=360.00 
App.ActiveDocument.C2012.Placement=Base.Placement(Base.Vector(-41.569989,175.616926,-41.325462),Base.Rotation(-0.381115,-0.771929,0.000000,0.508799))
App.ActiveDocument.addObject("Part::Cylinder","C2013")
App.ActiveDocument.C2013.Radius=0.591174
App.ActiveDocument.C2013.Height=20.00
App.ActiveDocument.C2013.Angle=360.00 
App.ActiveDocument.C2013.Placement=Base.Placement(Base.Vector(-41.571721,172.871754,-43.202025),Base.Rotation(-0.327510,-0.810563,0.000000,0.485514))
App.ActiveDocument.addObject("Part::Cylinder","C2014")
App.ActiveDocument.C2014.Radius=0.596187
App.ActiveDocument.C2014.Height=20.00
App.ActiveDocument.C2014.Angle=360.00 
App.ActiveDocument.C2014.Placement=Base.Placement(Base.Vector(-41.295511,170.378891,-44.891947),Base.Rotation(-0.273079,-0.842284,0.000000,0.464742))
App.ActiveDocument.addObject("Part::Cylinder","C2015")
App.ActiveDocument.C2015.Radius=0.600586
App.ActiveDocument.C2015.Height=20.00
App.ActiveDocument.C2015.Angle=360.00 
App.ActiveDocument.C2015.Placement=Base.Placement(Base.Vector(-41.036599,167.286956,-46.412027),Base.Rotation(-0.214482,-0.867601,0.000000,0.448627))
App.ActiveDocument.addObject("Part::Cylinder","C2016")
App.ActiveDocument.C2016.Radius=0.602791
App.ActiveDocument.C2016.Height=20.00
App.ActiveDocument.C2016.Angle=360.00 
App.ActiveDocument.C2016.Placement=Base.Placement(Base.Vector(-40.951855,164.245276,-47.309168),Base.Rotation(-0.141747,-0.885014,0.000000,0.443460))
App.ActiveDocument.addObject("Part::Cylinder","C2017")
App.ActiveDocument.C2017.Radius=0.604837
App.ActiveDocument.C2017.Height=20.00
App.ActiveDocument.C2017.Angle=360.00 
App.ActiveDocument.C2017.Placement=Base.Placement(Base.Vector(-40.726747,160.863547,-48.115527),Base.Rotation(-0.069051,-0.894264,0.000000,0.442181))
App.ActiveDocument.addObject("Part::Cylinder","C2018")
App.ActiveDocument.C2018.Radius=0.606639
App.ActiveDocument.C2018.Height=20.00
App.ActiveDocument.C2018.Angle=360.00 
App.ActiveDocument.C2018.Placement=Base.Placement(Base.Vector(-40.347783,157.443659,-48.791845),Base.Rotation(-0.008363,-0.895501,0.000000,0.444982))
App.ActiveDocument.addObject("Part::Cylinder","C2019")
App.ActiveDocument.C2019.Radius=0.608272
App.ActiveDocument.C2019.Height=20.00
App.ActiveDocument.C2019.Angle=360.00 
App.ActiveDocument.C2019.Placement=Base.Placement(Base.Vector(-39.883776,153.956652,-49.309621),Base.Rotation(0.031678,-0.893860,0.000000,0.447225))
App.ActiveDocument.addObject("Part::Cylinder","C2020")
App.ActiveDocument.C2020.Radius=0.608407
App.ActiveDocument.C2020.Height=20.00
App.ActiveDocument.C2020.Angle=360.00 
App.ActiveDocument.C2020.Placement=Base.Placement(Base.Vector(-39.436133,149.696562,-49.490740),Base.Rotation(0.079931,-0.882852,0.000000,0.462800))
App.ActiveDocument.addObject("Part::Cylinder","C2021")
App.ActiveDocument.C2021.Radius=0.609391
App.ActiveDocument.C2021.Height=20.00
App.ActiveDocument.C2021.Angle=360.00 
App.ActiveDocument.C2021.Placement=Base.Placement(Base.Vector(-38.850198,145.712027,-49.740277),Base.Rotation(0.100492,-0.877368,0.000000,0.469176))
App.ActiveDocument.addObject("Part::Cylinder","C2022")
App.ActiveDocument.C2022.Radius=0.609674
App.ActiveDocument.C2022.Height=20.00
App.ActiveDocument.C2022.Angle=360.00 
App.ActiveDocument.C2022.Placement=Base.Placement(Base.Vector(-38.333143,141.360431,-49.667862),Base.Rotation(0.122986,-0.871897,0.000000,0.473993))
App.ActiveDocument.addObject("Part::Cylinder","C2023")
App.ActiveDocument.C2023.Radius=0.610679
App.ActiveDocument.C2023.Height=20.00
App.ActiveDocument.C2023.Angle=360.00 
App.ActiveDocument.C2023.Placement=Base.Placement(Base.Vector(-37.712123,137.438675,-49.721547),Base.Rotation(0.138221,-0.869932,0.000000,0.473406))
App.ActiveDocument.addObject("Part::Cylinder","C2024")
App.ActiveDocument.C2024.Radius=0.610103
App.ActiveDocument.C2024.Height=20.00
App.ActiveDocument.C2024.Angle=360.00 
App.ActiveDocument.C2024.Placement=Base.Placement(Base.Vector(-37.345955,133.126669,-49.202650),Base.Rotation(0.151647,-0.868191,0.000000,0.472491))
App.ActiveDocument.addObject("Part::Cylinder","C2025")
App.ActiveDocument.C2025.Radius=0.608549
App.ActiveDocument.C2025.Height=20.00
App.ActiveDocument.C2025.Angle=360.00 
App.ActiveDocument.C2025.Placement=Base.Placement(Base.Vector(-37.226776,129.504310,-48.406809),Base.Rotation(0.169721,-0.864818,0.000000,0.472530))
App.ActiveDocument.addObject("Part::Cylinder","C2026")
App.ActiveDocument.C2026.Radius=0.605702
App.ActiveDocument.C2026.Height=20.00
App.ActiveDocument.C2026.Angle=360.00 
App.ActiveDocument.C2026.Placement=Base.Placement(Base.Vector(-37.154168,125.231220,-47.131611),Base.Rotation(0.203259,-0.855382,0.000000,0.476453))
App.ActiveDocument.addObject("Part::Cylinder","C2027")
App.ActiveDocument.C2027.Radius=0.602283
App.ActiveDocument.C2027.Height=20.00
App.ActiveDocument.C2027.Angle=360.00 
App.ActiveDocument.C2027.Placement=Base.Placement(Base.Vector(-37.118330,121.074503,-45.548501),Base.Rotation(0.231956,-0.847334,0.000000,0.477726))
App.ActiveDocument.addObject("Part::Cylinder","C2028")
App.ActiveDocument.C2028.Radius=0.597195
App.ActiveDocument.C2028.Height=20.00
App.ActiveDocument.C2028.Angle=360.00 
App.ActiveDocument.C2028.Placement=Base.Placement(Base.Vector(-37.575319,116.738421,-43.123737),Base.Rotation(0.238623,-0.853580,0.000000,0.463098))
App.ActiveDocument.addObject("Part::Cylinder","C2029")
App.ActiveDocument.C2029.Radius=0.595210
App.ActiveDocument.C2029.Height=20.00
App.ActiveDocument.C2029.Angle=360.00 
App.ActiveDocument.C2029.Placement=Base.Placement(Base.Vector(-37.342929,112.562413,-41.751915),Base.Rotation(0.282381,-0.845562,0.000000,0.453085))
App.ActiveDocument.addObject("Part::Cylinder","C2030")
App.ActiveDocument.C2030.Radius=0.591720
App.ActiveDocument.C2030.Height=20.00
App.ActiveDocument.C2030.Angle=360.00 
App.ActiveDocument.C2030.Placement=Base.Placement(Base.Vector(-37.017212,108.613494,-40.249186),Base.Rotation(0.338490,-0.815972,0.000000,0.468631))
App.ActiveDocument.addObject("Part::Cylinder","C2031")
App.ActiveDocument.C2031.Radius=0.590277
App.ActiveDocument.C2031.Height=20.00
App.ActiveDocument.C2031.Angle=360.00 
App.ActiveDocument.C2031.Placement=Base.Placement(Base.Vector(-38.253683,109.005958,-41.409258),Base.Rotation(0.686314,-0.418935,0.000000,0.594531))
App.ActiveDocument.addObject("Part::Cylinder","C2032")
App.ActiveDocument.C2032.Radius=0.491659
App.ActiveDocument.C2032.Height=20.00
App.ActiveDocument.C2032.Angle=360.00 
App.ActiveDocument.C2032.Placement=Base.Placement(Base.Vector(-42.983057,186.093341,-4.373060),Base.Rotation(-0.418293,-0.564615,0.000000,0.711506))
App.ActiveDocument.addObject("Part::Cylinder","C2033")
App.ActiveDocument.C2033.Radius=0.501884
App.ActiveDocument.C2033.Height=20.00
App.ActiveDocument.C2033.Angle=360.00 
App.ActiveDocument.C2033.Placement=Base.Placement(Base.Vector(-43.406048,185.505686,-8.984015),Base.Rotation(-0.423238,-0.573880,0.000000,0.701093))
App.ActiveDocument.addObject("Part::Cylinder","C2034")
App.ActiveDocument.C2034.Radius=0.512143
App.ActiveDocument.C2034.Height=20.00
App.ActiveDocument.C2034.Angle=360.00 
App.ActiveDocument.C2034.Placement=Base.Placement(Base.Vector(-43.583259,185.002863,-13.353333),Base.Rotation(-0.428142,-0.587932,0.000000,0.686317))
App.ActiveDocument.addObject("Part::Cylinder","C2035")
App.ActiveDocument.C2035.Radius=0.522198
App.ActiveDocument.C2035.Height=20.00
App.ActiveDocument.C2035.Angle=360.00 
App.ActiveDocument.C2035.Placement=Base.Placement(Base.Vector(-43.920674,183.959871,-17.649661),Base.Rotation(-0.431772,-0.605790,0.000000,0.668275))
App.ActiveDocument.addObject("Part::Cylinder","C2036")
App.ActiveDocument.C2036.Radius=0.532352
App.ActiveDocument.C2036.Height=20.00
App.ActiveDocument.C2036.Angle=360.00 
App.ActiveDocument.C2036.Placement=Base.Placement(Base.Vector(-43.804737,183.217855,-21.798754),Base.Rotation(-0.434346,-0.620104,0.000000,0.653310))
App.ActiveDocument.addObject("Part::Cylinder","C2037")
App.ActiveDocument.C2037.Radius=0.541839
App.ActiveDocument.C2037.Height=20.00
App.ActiveDocument.C2037.Angle=360.00 
App.ActiveDocument.C2037.Placement=Base.Placement(Base.Vector(-43.851433,181.942296,-25.745288),Base.Rotation(-0.423733,-0.645091,0.000000,0.635853))
App.ActiveDocument.addObject("Part::Cylinder","C2038")
App.ActiveDocument.C2038.Radius=0.551068
App.ActiveDocument.C2038.Height=20.00
App.ActiveDocument.C2038.Angle=360.00 
App.ActiveDocument.C2038.Placement=Base.Placement(Base.Vector(-43.712548,180.655596,-29.501047),Base.Rotation(-0.412777,-0.667091,0.000000,0.620166))
App.ActiveDocument.addObject("Part::Cylinder","C2039")
App.ActiveDocument.C2039.Radius=0.559361
App.ActiveDocument.C2039.Height=20.00
App.ActiveDocument.C2039.Angle=360.00 
App.ActiveDocument.C2039.Placement=Base.Placement(Base.Vector(-43.676127,179.053209,-32.733135),Base.Rotation(-0.400145,-0.694154,0.000000,0.598359))
App.ActiveDocument.addObject("Part::Cylinder","C2040")
App.ActiveDocument.C2040.Radius=0.565877
App.ActiveDocument.C2040.Height=20.00
App.ActiveDocument.C2040.Angle=360.00 
App.ActiveDocument.C2040.Placement=Base.Placement(Base.Vector(-43.921697,176.747204,-35.441835),Base.Rotation(-0.359890,-0.732845,0.000000,0.577423))
App.ActiveDocument.addObject("Part::Cylinder","C2041")
App.ActiveDocument.C2041.Radius=0.572791
App.ActiveDocument.C2041.Height=20.00
App.ActiveDocument.C2041.Angle=360.00 
App.ActiveDocument.C2041.Placement=Base.Placement(Base.Vector(-43.903969,174.340983,-38.017125),Base.Rotation(-0.320853,-0.769628,0.000000,0.552020))
App.ActiveDocument.addObject("Part::Cylinder","C2042")
App.ActiveDocument.C2042.Radius=0.578309
App.ActiveDocument.C2042.Height=20.00
App.ActiveDocument.C2042.Angle=360.00 
App.ActiveDocument.C2042.Placement=Base.Placement(Base.Vector(-43.960111,171.458895,-40.029088),Base.Rotation(-0.262003,-0.808525,0.000000,0.526918))
App.ActiveDocument.addObject("Part::Cylinder","C2043")
App.ActiveDocument.C2043.Radius=0.584768
App.ActiveDocument.C2043.Height=20.00
App.ActiveDocument.C2043.Angle=360.00 
App.ActiveDocument.C2043.Placement=Base.Placement(Base.Vector(-43.570385,168.600818,-42.163156),Base.Rotation(-0.203930,-0.840520,0.000000,0.501935))
App.ActiveDocument.addObject("Part::Cylinder","C2044")
App.ActiveDocument.C2044.Radius=0.588174
App.ActiveDocument.C2044.Height=20.00
App.ActiveDocument.C2044.Angle=360.00 
App.ActiveDocument.C2044.Placement=Base.Placement(Base.Vector(-43.433843,165.824600,-43.355025),Base.Rotation(-0.148860,-0.859419,0.000000,0.489122))
App.ActiveDocument.addObject("Part::Cylinder","C2045")
App.ActiveDocument.C2045.Radius=0.590517
App.ActiveDocument.C2045.Height=20.00
App.ActiveDocument.C2045.Angle=360.00 
App.ActiveDocument.C2045.Placement=Base.Placement(Base.Vector(-43.295697,162.336443,-44.268279),Base.Rotation(-0.067590,-0.872261,0.000000,0.484348))
App.ActiveDocument.addObject("Part::Cylinder","C2046")
App.ActiveDocument.C2046.Radius=0.591986
App.ActiveDocument.C2046.Height=20.00
App.ActiveDocument.C2046.Angle=360.00 
App.ActiveDocument.C2046.Placement=Base.Placement(Base.Vector(-43.059355,158.539299,-44.859866),Base.Rotation(0.006571,-0.873780,0.000000,0.486277))
App.ActiveDocument.addObject("Part::Cylinder","C2047")
App.ActiveDocument.C2047.Radius=0.594176
App.ActiveDocument.C2047.Height=20.00
App.ActiveDocument.C2047.Angle=360.00 
App.ActiveDocument.C2047.Placement=Base.Placement(Base.Vector(-42.518069,154.937535,-45.497815),Base.Rotation(0.050459,-0.872801,0.000000,0.485461))
App.ActiveDocument.addObject("Part::Cylinder","C2048")
App.ActiveDocument.C2048.Radius=0.594873
App.ActiveDocument.C2048.Height=20.00
App.ActiveDocument.C2048.Angle=360.00 
App.ActiveDocument.C2048.Placement=Base.Placement(Base.Vector(-42.093505,151.588516,-45.723359),Base.Rotation(0.087832,-0.865987,0.000000,0.492292))
App.ActiveDocument.addObject("Part::Cylinder","C2049")
App.ActiveDocument.C2049.Radius=0.595324
App.ActiveDocument.C2049.Height=20.00
App.ActiveDocument.C2049.Angle=360.00 
App.ActiveDocument.C2049.Placement=Base.Placement(Base.Vector(-41.560920,147.037210,-45.716758),Base.Rotation(0.109085,-0.860919,0.000000,0.496909))
App.ActiveDocument.addObject("Part::Cylinder","C2050")
App.ActiveDocument.C2050.Radius=0.596256
App.ActiveDocument.C2050.Height=20.00
App.ActiveDocument.C2050.Angle=360.00 
App.ActiveDocument.C2050.Placement=Base.Placement(Base.Vector(-40.947268,142.768317,-45.796885),Base.Rotation(0.117361,-0.859112,0.000000,0.498150))
App.ActiveDocument.addObject("Part::Cylinder","C2051")
App.ActiveDocument.C2051.Radius=0.596778
App.ActiveDocument.C2051.Height=20.00
App.ActiveDocument.C2051.Angle=360.00 
App.ActiveDocument.C2051.Placement=Base.Placement(Base.Vector(-40.358323,137.897140,-45.636363),Base.Rotation(0.123375,-0.859077,0.000000,0.496755))
App.ActiveDocument.addObject("Part::Cylinder","C2052")
App.ActiveDocument.C2052.Radius=0.597160
App.ActiveDocument.C2052.Height=20.00
App.ActiveDocument.C2052.Angle=360.00 
App.ActiveDocument.C2052.Placement=Base.Placement(Base.Vector(-39.906813,133.956868,-45.430809),Base.Rotation(0.132067,-0.859929,0.000000,0.493032))
App.ActiveDocument.addObject("Part::Cylinder","C2053")
App.ActiveDocument.C2053.Radius=0.594899
App.ActiveDocument.C2053.Height=20.00
App.ActiveDocument.C2053.Angle=360.00 
App.ActiveDocument.C2053.Placement=Base.Placement(Base.Vector(-39.933041,130.429475,-44.459508),Base.Rotation(0.146230,-0.856478,0.000000,0.495037))
App.ActiveDocument.addObject("Part::Cylinder","C2054")
App.ActiveDocument.C2054.Radius=0.593882
App.ActiveDocument.C2054.Height=20.00
App.ActiveDocument.C2054.Angle=360.00 
App.ActiveDocument.C2054.Placement=Base.Placement(Base.Vector(-39.586694,126.169562,-43.689932),Base.Rotation(0.173699,-0.852826,0.000000,0.492460))
App.ActiveDocument.addObject("Part::Cylinder","C2055")
App.ActiveDocument.C2055.Radius=0.590107
App.ActiveDocument.C2055.Height=20.00
App.ActiveDocument.C2055.Angle=360.00 
App.ActiveDocument.C2055.Placement=Base.Placement(Base.Vector(-39.880030,121.869975,-41.738540),Base.Rotation(0.195685,-0.856388,0.000000,0.477815))
App.ActiveDocument.addObject("Part::Cylinder","C2056")
App.ActiveDocument.C2056.Radius=0.584964
App.ActiveDocument.C2056.Height=20.00
App.ActiveDocument.C2056.Angle=360.00 
App.ActiveDocument.C2056.Placement=Base.Placement(Base.Vector(-40.163522,117.469983,-39.832752),Base.Rotation(0.189251,-0.852466,0.000000,0.487325))
App.ActiveDocument.addObject("Part::Cylinder","C2057")
App.ActiveDocument.C2057.Radius=0.583130
App.ActiveDocument.C2057.Height=20.00
App.ActiveDocument.C2057.Angle=360.00 
App.ActiveDocument.C2057.Placement=Base.Placement(Base.Vector(-39.605995,113.190333,-39.220095),Base.Rotation(0.207260,-0.835300,0.000000,0.509231))
App.ActiveDocument.addObject("Part::Cylinder","C2058")
App.ActiveDocument.C2058.Radius=0.579232
App.ActiveDocument.C2058.Height=20.00
App.ActiveDocument.C2058.Angle=360.00 
App.ActiveDocument.C2058.Placement=Base.Placement(Base.Vector(-39.773198,110.060385,-37.018500),Base.Rotation(0.352340,-0.790789,0.000000,0.500509))
App.ActiveDocument.addObject("Part::Cylinder","C2059")
App.ActiveDocument.C2059.Radius=0.577595
App.ActiveDocument.C2059.Height=20.00
App.ActiveDocument.C2059.Angle=360.00 
App.ActiveDocument.C2059.Placement=Base.Placement(Base.Vector(-39.122050,107.560025,-35.841639),Base.Rotation(0.513763,-0.680658,0.000000,0.522256))
App.ActiveDocument.addObject("Part::Cylinder","C2060")
App.ActiveDocument.C2060.Radius=0.488082
App.ActiveDocument.C2060.Height=20.00
App.ActiveDocument.C2060.Angle=360.00 
App.ActiveDocument.C2060.Placement=Base.Placement(Base.Vector(-45.375073,182.622740,-4.414482),Base.Rotation(-0.382673,-0.588734,0.000000,0.712006))
App.ActiveDocument.addObject("Part::Cylinder","C2061")
App.ActiveDocument.C2061.Radius=0.498277
App.ActiveDocument.C2061.Height=20.00
App.ActiveDocument.C2061.Angle=360.00 
App.ActiveDocument.C2061.Placement=Base.Placement(Base.Vector(-45.706626,182.113460,-8.975671),Base.Rotation(-0.383968,-0.600167,0.000000,0.701689))
App.ActiveDocument.addObject("Part::Cylinder","C2062")
App.ActiveDocument.C2062.Radius=0.508506
App.ActiveDocument.C2062.Height=20.00
App.ActiveDocument.C2062.Angle=360.00 
App.ActiveDocument.C2062.Placement=Base.Placement(Base.Vector(-45.918297,181.496405,-13.380285),Base.Rotation(-0.384913,-0.615790,0.000000,0.687492))
App.ActiveDocument.addObject("Part::Cylinder","C2063")
App.ActiveDocument.C2063.Radius=0.518128
App.ActiveDocument.C2063.Height=20.00
App.ActiveDocument.C2063.Angle=360.00 
App.ActiveDocument.C2063.Placement=Base.Placement(Base.Vector(-46.200738,180.419059,-17.472625),Base.Rotation(-0.377423,-0.640540,0.000000,0.668775))
App.ActiveDocument.addObject("Part::Cylinder","C2064")
App.ActiveDocument.C2064.Radius=0.527993
App.ActiveDocument.C2064.Height=20.00
App.ActiveDocument.C2064.Angle=360.00 
App.ActiveDocument.C2064.Placement=Base.Placement(Base.Vector(-46.009470,179.751430,-21.462402),Base.Rotation(-0.372615,-0.658745,0.000000,0.653615))
App.ActiveDocument.addObject("Part::Cylinder","C2065")
App.ActiveDocument.C2065.Radius=0.537366
App.ActiveDocument.C2065.Height=20.00
App.ActiveDocument.C2065.Angle=360.00 
App.ActiveDocument.C2065.Placement=Base.Placement(Base.Vector(-46.041364,178.317585,-25.348646),Base.Rotation(-0.356604,-0.684039,0.000000,0.636337))
App.ActiveDocument.addObject("Part::Cylinder","C2066")
App.ActiveDocument.C2066.Radius=0.546894
App.ActiveDocument.C2066.Height=20.00
App.ActiveDocument.C2066.Angle=360.00 
App.ActiveDocument.C2066.Placement=Base.Placement(Base.Vector(-45.923690,176.691080,-29.224699),Base.Rotation(-0.335807,-0.709817,0.000000,0.619188))
App.ActiveDocument.addObject("Part::Cylinder","C2067")
App.ActiveDocument.C2067.Radius=0.553672
App.ActiveDocument.C2067.Height=20.00
App.ActiveDocument.C2067.Angle=360.00 
App.ActiveDocument.C2067.Placement=Base.Placement(Base.Vector(-45.980980,174.805345,-31.996109),Base.Rotation(-0.300319,-0.739627,0.000000,0.602296))
App.ActiveDocument.addObject("Part::Cylinder","C2068")
App.ActiveDocument.C2068.Radius=0.560235
App.ActiveDocument.C2068.Height=20.00
App.ActiveDocument.C2068.Angle=360.00 
App.ActiveDocument.C2068.Placement=Base.Placement(Base.Vector(-45.953025,172.595476,-34.603779),Base.Rotation(-0.262314,-0.767070,0.000000,0.585487))
App.ActiveDocument.addObject("Part::Cylinder","C2069")
App.ActiveDocument.C2069.Radius=0.566430
App.ActiveDocument.C2069.Height=20.00
App.ActiveDocument.C2069.Angle=360.00 
App.ActiveDocument.C2069.Placement=Base.Placement(Base.Vector(-45.918723,169.792006,-36.900644),Base.Rotation(-0.206651,-0.800104,0.000000,0.563142))
App.ActiveDocument.addObject("Part::Cylinder","C2070")
App.ActiveDocument.C2070.Radius=0.572005
App.ActiveDocument.C2070.Height=20.00
App.ActiveDocument.C2070.Angle=360.00 
App.ActiveDocument.C2070.Placement=Base.Placement(Base.Vector(-45.710765,167.051698,-38.752703),Base.Rotation(-0.157106,-0.826745,0.000000,0.540194))
App.ActiveDocument.addObject("Part::Cylinder","C2071")
App.ActiveDocument.C2071.Radius=0.576546
App.ActiveDocument.C2071.Height=20.00
App.ActiveDocument.C2071.Angle=360.00 
App.ActiveDocument.C2071.Placement=Base.Placement(Base.Vector(-45.398030,163.772468,-40.299206),Base.Rotation(-0.084690,-0.846408,0.000000,0.525758))
App.ActiveDocument.addObject("Part::Cylinder","C2072")
App.ActiveDocument.C2072.Radius=0.578106
App.ActiveDocument.C2072.Height=20.00
App.ActiveDocument.C2072.Angle=360.00 
App.ActiveDocument.C2072.Placement=Base.Placement(Base.Vector(-45.242148,160.252102,-40.950984),Base.Rotation(-0.007880,-0.850357,0.000000,0.526147))
App.ActiveDocument.addObject("Part::Cylinder","C2073")
App.ActiveDocument.C2073.Radius=0.580470
App.ActiveDocument.C2073.Height=20.00
App.ActiveDocument.C2073.Angle=360.00 
App.ActiveDocument.C2073.Placement=Base.Placement(Base.Vector(-44.790358,156.340436,-41.602861),Base.Rotation(0.047203,-0.852259,0.000000,0.520985))
App.ActiveDocument.addObject("Part::Cylinder","C2074")
App.ActiveDocument.C2074.Radius=0.580295
App.ActiveDocument.C2074.Height=20.00
App.ActiveDocument.C2074.Angle=360.00 
App.ActiveDocument.C2074.Placement=Base.Placement(Base.Vector(-44.561857,152.346710,-41.423593),Base.Rotation(0.081873,-0.848408,0.000000,0.522973))
App.ActiveDocument.addObject("Part::Cylinder","C2075")
App.ActiveDocument.C2075.Radius=0.581951
App.ActiveDocument.C2075.Height=20.00
App.ActiveDocument.C2075.Angle=360.00 
App.ActiveDocument.C2075.Placement=Base.Placement(Base.Vector(-43.987064,148.434868,-41.691540),Base.Rotation(0.102715,-0.848923,0.000000,0.518440))
App.ActiveDocument.addObject("Part::Cylinder","C2076")
App.ActiveDocument.C2076.Radius=0.582553
App.ActiveDocument.C2076.Height=20.00
App.ActiveDocument.C2076.Angle=360.00 
App.ActiveDocument.C2076.Placement=Base.Placement(Base.Vector(-43.451925,144.118350,-41.622138),Base.Rotation(0.116823,-0.847299,0.000000,0.518108))
App.ActiveDocument.addObject("Part::Cylinder","C2077")
App.ActiveDocument.C2077.Radius=0.583512
App.ActiveDocument.C2077.Height=20.00
App.ActiveDocument.C2077.Angle=360.00 
App.ActiveDocument.C2077.Placement=Base.Placement(Base.Vector(-42.802770,139.810796,-41.716648),Base.Rotation(0.116186,-0.846263,0.000000,0.519942))
App.ActiveDocument.addObject("Part::Cylinder","C2078")
App.ActiveDocument.C2078.Radius=0.583937
App.ActiveDocument.C2078.Height=20.00
App.ActiveDocument.C2078.Angle=360.00 
App.ActiveDocument.C2078.Placement=Base.Placement(Base.Vector(-42.254853,135.175107,-41.581004),Base.Rotation(0.112771,-0.846757,0.000000,0.519889))
App.ActiveDocument.addObject("Part::Cylinder","C2079")
App.ActiveDocument.C2079.Radius=0.582071
App.ActiveDocument.C2079.Height=20.00
App.ActiveDocument.C2079.Angle=360.00 
App.ActiveDocument.C2079.Placement=Base.Placement(Base.Vector(-42.200519,131.340559,-40.701344),Base.Rotation(0.119987,-0.845618,0.000000,0.520129))
App.ActiveDocument.addObject("Part::Cylinder","C2080")
App.ActiveDocument.C2080.Radius=0.581358
App.ActiveDocument.C2080.Height=20.00
App.ActiveDocument.C2080.Angle=360.00 
App.ActiveDocument.C2080.Placement=Base.Placement(Base.Vector(-41.986323,127.581310,-40.031147),Base.Rotation(0.135712,-0.847805,0.000000,0.512649))
App.ActiveDocument.addObject("Part::Cylinder","C2081")
App.ActiveDocument.C2081.Radius=0.578908
App.ActiveDocument.C2081.Height=20.00
App.ActiveDocument.C2081.Angle=360.00 
App.ActiveDocument.C2081.Placement=Base.Placement(Base.Vector(-42.062224,124.165462,-38.907161),Base.Rotation(0.139762,-0.848340,0.000000,0.510673))
App.ActiveDocument.addObject("Part::Cylinder","C2082")
App.ActiveDocument.C2082.Radius=0.574477
App.ActiveDocument.C2082.Height=20.00
App.ActiveDocument.C2082.Angle=360.00 
App.ActiveDocument.C2082.Placement=Base.Placement(Base.Vector(-42.125601,121.345571,-37.877874),Base.Rotation(0.198036,-0.812500,0.000000,0.548294))
App.ActiveDocument.addObject("Part::Cylinder","C2083")
App.ActiveDocument.C2083.Radius=0.571242
App.ActiveDocument.C2083.Height=20.00
App.ActiveDocument.C2083.Angle=360.00 
App.ActiveDocument.C2083.Placement=Base.Placement(Base.Vector(-42.502879,115.777687,-34.745198),Base.Rotation(0.100791,-0.874739,0.000000,0.473997))
App.ActiveDocument.addObject("Part::Cylinder","C2084")
App.ActiveDocument.C2084.Radius=0.568959
App.ActiveDocument.C2084.Height=20.00
App.ActiveDocument.C2084.Angle=360.00 
App.ActiveDocument.C2084.Placement=Base.Placement(Base.Vector(-43.520271,111.690862,-32.745869),Base.Rotation(0.162438,-0.895333,0.000000,0.414721))
App.ActiveDocument.addObject("Part::Cylinder","C2085")
App.ActiveDocument.C2085.Radius=0.566024
App.ActiveDocument.C2085.Height=20.00
App.ActiveDocument.C2085.Angle=360.00 
App.ActiveDocument.C2085.Placement=Base.Placement(Base.Vector(-44.596292,108.758176,-30.701721),Base.Rotation(0.383810,-0.845201,0.000000,0.371921))
App.ActiveDocument.addObject("Part::Cylinder","C2086")
App.ActiveDocument.C2086.Radius=0.564992
App.ActiveDocument.C2086.Height=20.00
App.ActiveDocument.C2086.Angle=360.00 
App.ActiveDocument.C2086.Placement=Base.Placement(Base.Vector(-44.353087,107.439289,-30.141818),Base.Rotation(0.699669,-0.572246,0.000000,0.427781))
App.ActiveDocument.addObject("Part::Cylinder","C2087")
App.ActiveDocument.C2087.Radius=0.484184
App.ActiveDocument.C2087.Height=20.00
App.ActiveDocument.C2087.Angle=360.00 
App.ActiveDocument.C2087.Placement=Base.Placement(Base.Vector(-47.572126,178.989525,-4.234387),Base.Rotation(-0.335443,-0.615785,0.000000,0.712942))
App.ActiveDocument.addObject("Part::Cylinder","C2088")
App.ActiveDocument.C2088.Radius=0.494726
App.ActiveDocument.C2088.Height=20.00
App.ActiveDocument.C2088.Angle=360.00 
App.ActiveDocument.C2088.Placement=Base.Placement(Base.Vector(-47.785631,178.607532,-8.870823),Base.Rotation(-0.332223,-0.630264,0.000000,0.701709))
App.ActiveDocument.addObject("Part::Cylinder","C2089")
App.ActiveDocument.C2089.Radius=0.504460
App.ActiveDocument.C2089.Height=20.00
App.ActiveDocument.C2089.Angle=360.00 
App.ActiveDocument.C2089.Placement=Base.Placement(Base.Vector(-47.994950,177.898134,-13.057860),Base.Rotation(-0.328352,-0.647766,0.000000,0.687448))
App.ActiveDocument.addObject("Part::Cylinder","C2090")
App.ActiveDocument.C2090.Radius=0.513884
App.ActiveDocument.C2090.Height=20.00
App.ActiveDocument.C2090.Angle=360.00 
App.ActiveDocument.C2090.Placement=Base.Placement(Base.Vector(-48.175474,176.831258,-17.043967),Base.Rotation(-0.311499,-0.673938,0.000000,0.669907))
App.ActiveDocument.addObject("Part::Cylinder","C2091")
App.ActiveDocument.C2091.Radius=0.524074
App.ActiveDocument.C2091.Height=20.00
App.ActiveDocument.C2091.Angle=360.00 
App.ActiveDocument.C2091.Placement=Base.Placement(Base.Vector(-47.986469,176.009853,-21.068130),Base.Rotation(-0.308113,-0.693426,0.000000,0.651327))
App.ActiveDocument.addObject("Part::Cylinder","C2092")
App.ActiveDocument.C2092.Radius=0.533546
App.ActiveDocument.C2092.Height=20.00
App.ActiveDocument.C2092.Angle=360.00 
App.ActiveDocument.C2092.Placement=Base.Placement(Base.Vector(-47.842810,174.623139,-24.949556),Base.Rotation(-0.280490,-0.719101,0.000000,0.635783))
App.ActiveDocument.addObject("Part::Cylinder","C2093")
App.ActiveDocument.C2093.Radius=0.541595
App.ActiveDocument.C2093.Height=20.00
App.ActiveDocument.C2093.Angle=360.00 
App.ActiveDocument.C2093.Placement=Base.Placement(Base.Vector(-47.783619,172.732826,-28.278150),Base.Rotation(-0.241387,-0.745421,0.000000,0.621353))
App.ActiveDocument.addObject("Part::Cylinder","C2094")
App.ActiveDocument.C2094.Radius=0.549420
App.ActiveDocument.C2094.Height=20.00
App.ActiveDocument.C2094.Angle=360.00 
App.ActiveDocument.C2094.Placement=Base.Placement(Base.Vector(-47.685713,170.277081,-31.442246),Base.Rotation(-0.200614,-0.769546,0.000000,0.606262))
App.ActiveDocument.addObject("Part::Cylinder","C2095")
App.ActiveDocument.C2095.Radius=0.554697
App.ActiveDocument.C2095.Height=20.00
App.ActiveDocument.C2095.Angle=360.00 
App.ActiveDocument.C2095.Placement=Base.Placement(Base.Vector(-47.608765,167.833507,-33.509450),Base.Rotation(-0.145476,-0.791997,0.000000,0.592939))
App.ActiveDocument.addObject("Part::Cylinder","C2096")
App.ActiveDocument.C2096.Radius=0.560391
App.ActiveDocument.C2096.Height=20.00
App.ActiveDocument.C2096.Angle=360.00 
App.ActiveDocument.C2096.Placement=Base.Placement(Base.Vector(-47.287463,165.234408,-35.586623),Base.Rotation(-0.100325,-0.808485,0.000000,0.579902))
App.ActiveDocument.addObject("Part::Cylinder","C2097")
App.ActiveDocument.C2097.Radius=0.564428
App.ActiveDocument.C2097.Height=20.00
App.ActiveDocument.C2097.Angle=360.00 
App.ActiveDocument.C2097.Placement=Base.Placement(Base.Vector(-46.984793,161.822058,-36.970273),Base.Rotation(-0.023682,-0.822072,0.000000,0.568891))
App.ActiveDocument.addObject("Part::Cylinder","C2098")
App.ActiveDocument.C2098.Radius=0.566464
App.ActiveDocument.C2098.Height=20.00
App.ActiveDocument.C2098.Angle=360.00 
App.ActiveDocument.C2098.Placement=Base.Placement(Base.Vector(-46.747315,158.130733,-37.498206),Base.Rotation(0.026429,-0.828197,0.000000,0.559814))
App.ActiveDocument.addObject("Part::Cylinder","C2099")
App.ActiveDocument.C2099.Radius=0.567296
App.ActiveDocument.C2099.Height=20.00
App.ActiveDocument.C2099.Angle=360.00 
App.ActiveDocument.C2099.Placement=Base.Placement(Base.Vector(-46.470315,154.061211,-37.632695),Base.Rotation(0.057510,-0.828213,0.000000,0.557455))
App.ActiveDocument.addObject("Part::Cylinder","C2100")
App.ActiveDocument.C2100.Radius=0.567076
App.ActiveDocument.C2100.Height=20.00
App.ActiveDocument.C2100.Angle=360.00 
App.ActiveDocument.C2100.Placement=Base.Placement(Base.Vector(-46.250991,149.679342,-37.300111),Base.Rotation(0.074353,-0.829088,0.000000,0.554152))
App.ActiveDocument.addObject("Part::Cylinder","C2101")
App.ActiveDocument.C2101.Radius=0.570455
App.ActiveDocument.C2101.Height=20.00
App.ActiveDocument.C2101.Angle=360.00 
App.ActiveDocument.C2101.Placement=Base.Placement(Base.Vector(-45.572902,146.243370,-37.984908),Base.Rotation(0.102423,-0.836144,0.000000,0.538863))
App.ActiveDocument.addObject("Part::Cylinder","C2102")
App.ActiveDocument.C2102.Radius=0.569561
App.ActiveDocument.C2102.Height=20.00
App.ActiveDocument.C2102.Angle=360.00 
App.ActiveDocument.C2102.Placement=Base.Placement(Base.Vector(-45.249380,141.845602,-37.377325),Base.Rotation(0.122892,-0.833110,0.000000,0.539283))
App.ActiveDocument.addObject("Part::Cylinder","C2103")
App.ActiveDocument.C2103.Radius=0.570854
App.ActiveDocument.C2103.Height=20.00
App.ActiveDocument.C2103.Angle=360.00 
App.ActiveDocument.C2103.Placement=Base.Placement(Base.Vector(-44.495755,137.534486,-37.604052),Base.Rotation(0.116113,-0.832013,0.000000,0.542469))
App.ActiveDocument.addObject("Part::Cylinder","C2104")
App.ActiveDocument.C2104.Radius=0.569254
App.ActiveDocument.C2104.Height=20.00
App.ActiveDocument.C2104.Angle=360.00 
App.ActiveDocument.C2104.Placement=Base.Placement(Base.Vector(-44.274826,133.162332,-36.838491),Base.Rotation(0.101290,-0.832024,0.000000,0.545414))
App.ActiveDocument.addObject("Part::Cylinder","C2105")
App.ActiveDocument.C2105.Radius=0.568002
App.ActiveDocument.C2105.Height=20.00
App.ActiveDocument.C2105.Angle=360.00 
App.ActiveDocument.C2105.Placement=Base.Placement(Base.Vector(-44.134856,129.363767,-36.150916),Base.Rotation(0.098895,-0.833176,0.000000,0.544093))
App.ActiveDocument.addObject("Part::Cylinder","C2106")
App.ActiveDocument.C2106.Radius=0.566475
App.ActiveDocument.C2106.Height=20.00
App.ActiveDocument.C2106.Angle=360.00 
App.ActiveDocument.C2106.Placement=Base.Placement(Base.Vector(-44.075603,125.643003,-35.319250),Base.Rotation(0.116920,-0.832906,0.000000,0.540922))
App.ActiveDocument.addObject("Part::Cylinder","C2107")
App.ActiveDocument.C2107.Radius=0.561677
App.ActiveDocument.C2107.Height=20.00
App.ActiveDocument.C2107.Angle=360.00 
App.ActiveDocument.C2107.Placement=Base.Placement(Base.Vector(-44.645018,120.663410,-32.236962),Base.Rotation(0.071734,-0.866593,0.000000,0.493833))
App.ActiveDocument.addObject("Part::Cylinder","C2108")
App.ActiveDocument.C2108.Radius=0.558543
App.ActiveDocument.C2108.Height=20.00
App.ActiveDocument.C2108.Angle=360.00 
App.ActiveDocument.C2108.Placement=Base.Placement(Base.Vector(-45.122363,116.052728,-31.178598),Base.Rotation(0.072627,-0.864865,0.000000,0.496723))
App.ActiveDocument.addObject("Part::Cylinder","C2109")
App.ActiveDocument.C2109.Radius=0.556098
App.ActiveDocument.C2109.Height=20.00
App.ActiveDocument.C2109.Angle=360.00 
App.ActiveDocument.C2109.Placement=Base.Placement(Base.Vector(-45.216187,111.179926,-30.406504),Base.Rotation(0.043609,-0.861004,0.000000,0.506726))
App.ActiveDocument.addObject("Part::Cylinder","C2110")
App.ActiveDocument.C2110.Radius=0.554411
App.ActiveDocument.C2110.Height=20.00
App.ActiveDocument.C2110.Angle=360.00 
App.ActiveDocument.C2110.Placement=Base.Placement(Base.Vector(-46.277535,107.742470,-28.565186),Base.Rotation(0.219055,-0.867092,0.000000,0.447400))
App.ActiveDocument.addObject("Part::Cylinder","C2111")
App.ActiveDocument.C2111.Radius=0.553552
App.ActiveDocument.C2111.Height=20.00
App.ActiveDocument.C2111.Angle=360.00 
App.ActiveDocument.C2111.Placement=Base.Placement(Base.Vector(-47.568925,107.364517,-27.567603),Base.Rotation(0.671190,-0.587297,0.000000,0.452311))
App.ActiveDocument.addObject("Part::Cylinder","C2112")
App.ActiveDocument.C2112.Radius=0.481674
App.ActiveDocument.C2112.Height=20.00
App.ActiveDocument.C2112.Angle=360.00 
App.ActiveDocument.C2112.Placement=Base.Placement(Base.Vector(-49.048702,175.969913,-4.399108),Base.Rotation(-0.243187,-0.655501,0.000000,0.714968))
App.ActiveDocument.addObject("Part::Cylinder","C2113")
App.ActiveDocument.C2113.Radius=0.491968
App.ActiveDocument.C2113.Height=20.00
App.ActiveDocument.C2113.Angle=360.00 
App.ActiveDocument.C2113.Placement=Base.Placement(Base.Vector(-49.352280,175.241442,-8.940073),Base.Rotation(-0.235270,-0.671713,0.000000,0.702460))
App.ActiveDocument.addObject("Part::Cylinder","C2114")
App.ActiveDocument.C2114.Radius=0.501991
App.ActiveDocument.C2114.Height=20.00
App.ActiveDocument.C2114.Angle=360.00 
App.ActiveDocument.C2114.Placement=Base.Placement(Base.Vector(-49.430940,174.604392,-13.180849),Base.Rotation(-0.226020,-0.689162,0.000000,0.688455))
App.ActiveDocument.addObject("Part::Cylinder","C2115")
App.ActiveDocument.C2115.Radius=0.511424
App.ActiveDocument.C2115.Height=20.00
App.ActiveDocument.C2115.Angle=360.00 
App.ActiveDocument.C2115.Placement=Base.Placement(Base.Vector(-49.523435,173.382685,-17.107228),Base.Rotation(-0.210751,-0.709804,0.000000,0.672132))
App.ActiveDocument.addObject("Part::Cylinder","C2116")
App.ActiveDocument.C2116.Radius=0.521431
App.ActiveDocument.C2116.Height=20.00
App.ActiveDocument.C2116.Angle=360.00 
App.ActiveDocument.C2116.Placement=Base.Placement(Base.Vector(-49.299984,172.457979,-21.032572),Base.Rotation(-0.200072,-0.729676,0.000000,0.653868))
App.ActiveDocument.addObject("Part::Cylinder","C2117")
App.ActiveDocument.C2117.Radius=0.529484
App.ActiveDocument.C2117.Height=20.00
App.ActiveDocument.C2117.Angle=360.00 
App.ActiveDocument.C2117.Placement=Base.Placement(Base.Vector(-49.212595,170.647729,-24.370449),Base.Rotation(-0.170729,-0.747203,0.000000,0.642292))
App.ActiveDocument.addObject("Part::Cylinder","C2118")
App.ActiveDocument.C2118.Radius=0.537012
App.ActiveDocument.C2118.Height=20.00
App.ActiveDocument.C2118.Angle=360.00 
App.ActiveDocument.C2118.Placement=Base.Placement(Base.Vector(-49.059365,168.371278,-27.439935),Base.Rotation(-0.134517,-0.763891,0.000000,0.631170))
App.ActiveDocument.addObject("Part::Cylinder","C2119")
App.ActiveDocument.C2119.Radius=0.542709
App.ActiveDocument.C2119.Height=20.00
App.ActiveDocument.C2119.Angle=360.00 
App.ActiveDocument.C2119.Placement=Base.Placement(Base.Vector(-48.880655,165.958600,-29.728729),Base.Rotation(-0.087397,-0.777645,0.000000,0.622600))
App.ActiveDocument.addObject("Part::Cylinder","C2120")
App.ActiveDocument.C2120.Radius=0.548901
App.ActiveDocument.C2120.Height=20.00
App.ActiveDocument.C2120.Angle=360.00 
App.ActiveDocument.C2120.Placement=Base.Placement(Base.Vector(-48.505679,163.500707,-32.047274),Base.Rotation(-0.049340,-0.789108,0.000000,0.612270))
App.ActiveDocument.addObject("Part::Cylinder","C2121")
App.ActiveDocument.C2121.Radius=0.552619
App.ActiveDocument.C2121.Height=20.00
App.ActiveDocument.C2121.Angle=360.00 
App.ActiveDocument.C2121.Placement=Base.Placement(Base.Vector(-48.217824,159.598697,-33.297747),Base.Rotation(0.009576,-0.798037,0.000000,0.602532))
App.ActiveDocument.addObject("Part::Cylinder","C2122")
App.ActiveDocument.C2122.Radius=0.554242
App.ActiveDocument.C2122.Height=20.00
App.ActiveDocument.C2122.Angle=360.00 
App.ActiveDocument.C2122.Placement=Base.Placement(Base.Vector(-47.956312,155.480572,-33.712347),Base.Rotation(0.037860,-0.801421,0.000000,0.596901))
App.ActiveDocument.addObject("Part::Cylinder","C2123")
App.ActiveDocument.C2123.Radius=0.554056
App.ActiveDocument.C2123.Height=20.00
App.ActiveDocument.C2123.Angle=360.00 
App.ActiveDocument.C2123.Placement=Base.Placement(Base.Vector(-47.822936,151.323514,-33.406407),Base.Rotation(0.049333,-0.804383,0.000000,0.592060))
App.ActiveDocument.addObject("Part::Cylinder","C2124")
App.ActiveDocument.C2124.Radius=0.555207
App.ActiveDocument.C2124.Height=20.00
App.ActiveDocument.C2124.Angle=360.00 
App.ActiveDocument.C2124.Placement=Base.Placement(Base.Vector(-47.501048,147.006420,-33.465459),Base.Rotation(0.064936,-0.810072,0.000000,0.582723))
App.ActiveDocument.addObject("Part::Cylinder","C2125")
App.ActiveDocument.C2125.Radius=0.556565
App.ActiveDocument.C2125.Height=20.00
App.ActiveDocument.C2125.Angle=360.00 
App.ActiveDocument.C2125.Placement=Base.Placement(Base.Vector(-47.135110,143.230622,-33.469445),Base.Rotation(0.098930,-0.815988,0.000000,0.569540))
App.ActiveDocument.addObject("Part::Cylinder","C2126")
App.ActiveDocument.C2126.Radius=0.556844
App.ActiveDocument.C2126.Height=20.00
App.ActiveDocument.C2126.Angle=360.00 
App.ActiveDocument.C2126.Placement=Base.Placement(Base.Vector(-46.653233,139.068897,-33.184558),Base.Rotation(0.123027,-0.815187,0.000000,0.565981))
App.ActiveDocument.addObject("Part::Cylinder","C2127")
App.ActiveDocument.C2127.Radius=0.556778
App.ActiveDocument.C2127.Height=20.00
App.ActiveDocument.C2127.Angle=360.00 
App.ActiveDocument.C2127.Placement=Base.Placement(Base.Vector(-46.107875,134.731106,-32.906782),Base.Rotation(0.112902,-0.814879,0.000000,0.568530))
App.ActiveDocument.addObject("Part::Cylinder","C2128")
App.ActiveDocument.C2128.Radius=0.554610
App.ActiveDocument.C2128.Height=20.00
App.ActiveDocument.C2128.Angle=360.00 
App.ActiveDocument.C2128.Placement=Base.Placement(Base.Vector(-45.907558,130.673485,-32.110990),Base.Rotation(0.088460,-0.810600,0.000000,0.578880))
App.ActiveDocument.addObject("Part::Cylinder","C2129")
App.ActiveDocument.C2129.Radius=0.553017
App.ActiveDocument.C2129.Height=20.00
App.ActiveDocument.C2129.Angle=360.00 
App.ActiveDocument.C2129.Placement=Base.Placement(Base.Vector(-45.752803,127.324175,-31.653256),Base.Rotation(0.089153,-0.801207,0.000000,0.591708))
App.ActiveDocument.addObject("Part::Cylinder","C2130")
App.ActiveDocument.C2130.Radius=0.550960
App.ActiveDocument.C2130.Height=20.00
App.ActiveDocument.C2130.Angle=360.00 
App.ActiveDocument.C2130.Placement=Base.Placement(Base.Vector(-46.358817,121.588547,-28.858261),Base.Rotation(-0.112711,-0.851721,0.000000,0.511729))
App.ActiveDocument.addObject("Part::Cylinder","C2131")
App.ActiveDocument.C2131.Radius=0.547024
App.ActiveDocument.C2131.Height=20.00
App.ActiveDocument.C2131.Angle=360.00 
App.ActiveDocument.C2131.Placement=Base.Placement(Base.Vector(-46.854716,119.365840,-28.364003),Base.Rotation(0.067586,-0.834413,0.000000,0.546980))
App.ActiveDocument.addObject("Part::Cylinder","C2132")
App.ActiveDocument.C2132.Radius=0.544469
App.ActiveDocument.C2132.Height=20.00
App.ActiveDocument.C2132.Angle=360.00 
App.ActiveDocument.C2132.Placement=Base.Placement(Base.Vector(-46.688496,115.361411,-27.635885),Base.Rotation(0.096465,-0.818141,0.000000,0.566869))
App.ActiveDocument.addObject("Part::Cylinder","C2133")
App.ActiveDocument.C2133.Radius=0.542984
App.ActiveDocument.C2133.Height=20.00
App.ActiveDocument.C2133.Angle=360.00 
App.ActiveDocument.C2133.Placement=Base.Placement(Base.Vector(-46.289591,110.214024,-27.442933),Base.Rotation(0.033948,-0.805639,0.000000,0.591433))
App.ActiveDocument.addObject("Part::Cylinder","C2134")
App.ActiveDocument.C2134.Radius=0.541553
App.ActiveDocument.C2134.Height=20.00
App.ActiveDocument.C2134.Angle=360.00 
App.ActiveDocument.C2134.Placement=Base.Placement(Base.Vector(-46.340889,104.950865,-27.483639),Base.Rotation(-0.019669,-0.788538,0.000000,0.614671))
App.ActiveDocument.addObject("Part::Cylinder","C2135")
App.ActiveDocument.C2135.Radius=0.541444
App.ActiveDocument.C2135.Height=20.00
App.ActiveDocument.C2135.Angle=360.00 
App.ActiveDocument.C2135.Placement=Base.Placement(Base.Vector(-51.491096,109.643403,-27.446119),Base.Rotation(0.720975,-0.248434,0.000000,0.646896))
App.ActiveDocument.addObject("Part::Cylinder","C2136")
App.ActiveDocument.C2136.Radius=0.479844
App.ActiveDocument.C2136.Height=20.00
App.ActiveDocument.C2136.Angle=360.00 
App.ActiveDocument.C2136.Placement=Base.Placement(Base.Vector(-50.222047,172.214305,-4.464608),Base.Rotation(-0.170463,-0.678238,0.000000,0.714797))
App.ActiveDocument.addObject("Part::Cylinder","C2137")
App.ActiveDocument.C2137.Radius=0.489917
App.ActiveDocument.C2137.Height=20.00
App.ActiveDocument.C2137.Angle=360.00 
App.ActiveDocument.C2137.Placement=Base.Placement(Base.Vector(-50.393402,171.530422,-8.850997),Base.Rotation(-0.148059,-0.695862,0.000000,0.702748))
App.ActiveDocument.addObject("Part::Cylinder","C2138")
App.ActiveDocument.C2138.Radius=0.499820
App.ActiveDocument.C2138.Height=20.00
App.ActiveDocument.C2138.Angle=360.00 
App.ActiveDocument.C2138.Placement=Base.Placement(Base.Vector(-50.419640,170.746242,-13.039415),Base.Rotation(-0.127561,-0.712501,0.000000,0.689978))
App.ActiveDocument.addObject("Part::Cylinder","C2139")
App.ActiveDocument.C2139.Radius=0.509494
App.ActiveDocument.C2139.Height=20.00
App.ActiveDocument.C2139.Angle=360.00 
App.ActiveDocument.C2139.Placement=Base.Placement(Base.Vector(-50.305458,169.794055,-17.033272),Base.Rotation(-0.103765,-0.728483,0.000000,0.677160))
App.ActiveDocument.addObject("Part::Cylinder","C2140")
App.ActiveDocument.C2140.Radius=0.518692
App.ActiveDocument.C2140.Height=20.00
App.ActiveDocument.C2140.Angle=360.00 
App.ActiveDocument.C2140.Placement=Base.Placement(Base.Vector(-50.138985,168.178609,-20.730669),Base.Rotation(-0.088622,-0.743171,0.000000,0.663206))
App.ActiveDocument.addObject("Part::Cylinder","C2141")
App.ActiveDocument.C2141.Radius=0.526099
App.ActiveDocument.C2141.Height=20.00
App.ActiveDocument.C2141.Angle=360.00 
App.ActiveDocument.C2141.Placement=Base.Placement(Base.Vector(-49.918209,166.289832,-23.748645),Base.Rotation(-0.058934,-0.753407,0.000000,0.654909))
App.ActiveDocument.addObject("Part::Cylinder","C2142")
App.ActiveDocument.C2142.Radius=0.532956
App.ActiveDocument.C2142.Height=20.00
App.ActiveDocument.C2142.Angle=360.00 
App.ActiveDocument.C2142.Placement=Base.Placement(Base.Vector(-49.642899,163.577830,-26.468717),Base.Rotation(-0.027345,-0.762501,0.000000,0.646409))
App.ActiveDocument.addObject("Part::Cylinder","C2143")
App.ActiveDocument.C2143.Radius=0.538523
App.ActiveDocument.C2143.Height=20.00
App.ActiveDocument.C2143.Angle=360.00 
App.ActiveDocument.C2143.Placement=Base.Placement(Base.Vector(-49.317067,161.003284,-28.573242),Base.Rotation(-0.003083,-0.769787,0.000000,0.638294))
App.ActiveDocument.addObject("Part::Cylinder","C2144")
App.ActiveDocument.C2144.Radius=0.541226
App.ActiveDocument.C2144.Height=20.00
App.ActiveDocument.C2144.Angle=360.00 
App.ActiveDocument.C2144.Placement=Base.Placement(Base.Vector(-49.085835,157.096912,-29.446612),Base.Rotation(0.020448,-0.775668,0.000000,0.630810))
App.ActiveDocument.addObject("Part::Cylinder","C2145")
App.ActiveDocument.C2145.Radius=0.541109
App.ActiveDocument.C2145.Height=20.00
App.ActiveDocument.C2145.Angle=360.00 
App.ActiveDocument.C2145.Placement=Base.Placement(Base.Vector(-48.990773,152.983627,-29.247957),Base.Rotation(0.028014,-0.777899,0.000000,0.627765))
App.ActiveDocument.addObject("Part::Cylinder","C2146")
App.ActiveDocument.C2146.Radius=0.541919
App.ActiveDocument.C2146.Height=20.00
App.ActiveDocument.C2146.Angle=360.00 
App.ActiveDocument.C2146.Placement=Base.Placement(Base.Vector(-48.814479,148.549261,-29.229922),Base.Rotation(0.035081,-0.785419,0.000000,0.617970))
App.ActiveDocument.addObject("Part::Cylinder","C2147")
App.ActiveDocument.C2147.Radius=0.543013
App.ActiveDocument.C2147.Height=20.00
App.ActiveDocument.C2147.Angle=360.00 
App.ActiveDocument.C2147.Placement=Base.Placement(Base.Vector(-48.585792,144.559705,-29.277923),Base.Rotation(0.056152,-0.792486,0.000000,0.607299))
App.ActiveDocument.addObject("Part::Cylinder","C2148")
App.ActiveDocument.C2148.Radius=0.543591
App.ActiveDocument.C2148.Height=20.00
App.ActiveDocument.C2148.Angle=360.00 
App.ActiveDocument.C2148.Placement=Base.Placement(Base.Vector(-48.283332,140.925947,-29.157269),Base.Rotation(0.097519,-0.793118,0.000000,0.601210))
App.ActiveDocument.addObject("Part::Cylinder","C2149")
App.ActiveDocument.C2149.Radius=0.543829
App.ActiveDocument.C2149.Height=20.00
App.ActiveDocument.C2149.Angle=360.00 
App.ActiveDocument.C2149.Placement=Base.Placement(Base.Vector(-47.780463,137.048707,-28.997105),Base.Rotation(0.123578,-0.787820,0.000000,0.603380))
App.ActiveDocument.addObject("Part::Cylinder","C2150")
App.ActiveDocument.C2150.Radius=0.542398
App.ActiveDocument.C2150.Height=20.00
App.ActiveDocument.C2150.Angle=360.00 
App.ActiveDocument.C2150.Placement=Base.Placement(Base.Vector(-47.178924,132.730375,-28.670245),Base.Rotation(0.119823,-0.769272,0.000000,0.627586))
App.ActiveDocument.addObject("Part::Cylinder","C2151")
App.ActiveDocument.C2151.Radius=0.540710
App.ActiveDocument.C2151.Height=20.00
App.ActiveDocument.C2151.Angle=360.00 
App.ActiveDocument.C2151.Placement=Base.Placement(Base.Vector(-46.776379,129.416617,-28.478627),Base.Rotation(0.152201,-0.737293,0.000000,0.658204))
App.ActiveDocument.addObject("Part::Cylinder","C2152")
App.ActiveDocument.C2152.Radius=0.538501
App.ActiveDocument.C2152.Height=20.00
App.ActiveDocument.C2152.Angle=360.00 
App.ActiveDocument.C2152.Placement=Base.Placement(Base.Vector(-48.146086,122.912336,-25.661860),Base.Rotation(-0.076507,-0.824109,0.000000,0.561241))
App.ActiveDocument.addObject("Part::Cylinder","C2153")
App.ActiveDocument.C2153.Radius=0.534348
App.ActiveDocument.C2153.Height=20.00
App.ActiveDocument.C2153.Angle=360.00 
App.ActiveDocument.C2153.Placement=Base.Placement(Base.Vector(-48.187364,120.136779,-24.837007),Base.Rotation(0.086454,-0.796406,0.000000,0.598551))
App.ActiveDocument.addObject("Part::Cylinder","C2154")
App.ActiveDocument.C2154.Radius=0.532351
App.ActiveDocument.C2154.Height=20.00
App.ActiveDocument.C2154.Angle=360.00 
App.ActiveDocument.C2154.Placement=Base.Placement(Base.Vector(-47.749373,115.907562,-24.275594),Base.Rotation(0.112431,-0.775667,0.000000,0.621048))
App.ActiveDocument.addObject("Part::Cylinder","C2155")
App.ActiveDocument.C2155.Radius=0.530801
App.ActiveDocument.C2155.Height=20.00
App.ActiveDocument.C2155.Angle=360.00 
App.ActiveDocument.C2155.Placement=Base.Placement(Base.Vector(-47.317974,110.705713,-23.637701),Base.Rotation(0.060748,-0.773375,0.000000,0.631031))
App.ActiveDocument.addObject("Part::Cylinder","C2156")
App.ActiveDocument.C2156.Radius=0.529822
App.ActiveDocument.C2156.Height=20.00
App.ActiveDocument.C2156.Angle=360.00 
App.ActiveDocument.C2156.Placement=Base.Placement(Base.Vector(-47.156691,104.807042,-23.525831),Base.Rotation(-0.022011,-0.763365,0.000000,0.645592))
App.ActiveDocument.addObject("Part::Cylinder","C2157")
App.ActiveDocument.C2157.Radius=0.530086
App.ActiveDocument.C2157.Height=20.00
App.ActiveDocument.C2157.Angle=360.00 
App.ActiveDocument.C2157.Placement=Base.Placement(Base.Vector(-49.513245,108.147221,-23.604784),Base.Rotation(0.577124,-0.462344,0.000000,0.673176))
App.ActiveDocument.addObject("Part::Cylinder","C2158")
App.ActiveDocument.C2158.Radius=0.478817
App.ActiveDocument.C2158.Height=20.00
App.ActiveDocument.C2158.Angle=360.00 
App.ActiveDocument.C2158.Placement=Base.Placement(Base.Vector(-50.974895,168.150009,-4.393815),Base.Rotation(-0.103864,-0.697902,0.000000,0.708622))
App.ActiveDocument.addObject("Part::Cylinder","C2159")
App.ActiveDocument.C2159.Radius=0.488930
App.ActiveDocument.C2159.Height=20.00
App.ActiveDocument.C2159.Angle=360.00 
App.ActiveDocument.C2159.Placement=Base.Placement(Base.Vector(-51.028074,167.440362,-8.753632),Base.Rotation(-0.082698,-0.710927,0.000000,0.698386))
App.ActiveDocument.addObject("Part::Cylinder","C2160")
App.ActiveDocument.C2160.Radius=0.498835
App.ActiveDocument.C2160.Height=20.00
App.ActiveDocument.C2160.Angle=360.00 
App.ActiveDocument.C2160.Placement=Base.Placement(Base.Vector(-50.964572,166.411511,-12.893760),Base.Rotation(-0.061860,-0.724504,0.000000,0.686489))
App.ActiveDocument.addObject("Part::Cylinder","C2161")
App.ActiveDocument.C2161.Radius=0.508162
App.ActiveDocument.C2161.Height=20.00
App.ActiveDocument.C2161.Angle=360.00 
App.ActiveDocument.C2161.Placement=Base.Placement(Base.Vector(-50.762298,165.342239,-16.736026),Base.Rotation(-0.047083,-0.734822,0.000000,0.676623))
App.ActiveDocument.addObject("Part::Cylinder","C2162")
App.ActiveDocument.C2162.Radius=0.516628
App.ActiveDocument.C2162.Height=20.00
App.ActiveDocument.C2162.Angle=360.00 
App.ActiveDocument.C2162.Placement=Base.Placement(Base.Vector(-50.509097,163.323075,-20.143717),Base.Rotation(-0.024055,-0.745280,0.000000,0.666317))
App.ActiveDocument.addObject("Part::Cylinder","C2163")
App.ActiveDocument.C2163.Radius=0.522599
App.ActiveDocument.C2163.Height=20.00
App.ActiveDocument.C2163.Angle=360.00 
App.ActiveDocument.C2163.Placement=Base.Placement(Base.Vector(-50.259627,160.922759,-22.499249),Base.Rotation(-0.004027,-0.752136,0.000000,0.658995))
App.ActiveDocument.addObject("Part::Cylinder","C2164")
App.ActiveDocument.C2164.Radius=0.528542
App.ActiveDocument.C2164.Height=20.00
App.ActiveDocument.C2164.Angle=360.00 
App.ActiveDocument.C2164.Placement=Base.Placement(Base.Vector(-49.920925,158.172483,-24.786520),Base.Rotation(0.009787,-0.758389,0.000000,0.651729))
App.ActiveDocument.addObject("Part::Cylinder","C2165")
App.ActiveDocument.C2165.Radius=0.527921
App.ActiveDocument.C2165.Height=20.00
App.ActiveDocument.C2165.Angle=360.00 
App.ActiveDocument.C2165.Placement=Base.Placement(Base.Vector(-49.908323,154.224623,-24.415789),Base.Rotation(0.013301,-0.760770,0.000000,0.648885))
App.ActiveDocument.addObject("Part::Cylinder","C2166")
App.ActiveDocument.C2166.Radius=0.528504
App.ActiveDocument.C2166.Height=20.00
App.ActiveDocument.C2166.Angle=360.00 
App.ActiveDocument.C2166.Placement=Base.Placement(Base.Vector(-49.844163,150.100211,-24.449567),Base.Rotation(0.011221,-0.766523,0.000000,0.642119))
App.ActiveDocument.addObject("Part::Cylinder","C2167")
App.ActiveDocument.C2167.Radius=0.530211
App.ActiveDocument.C2167.Height=20.00
App.ActiveDocument.C2167.Angle=360.00 
App.ActiveDocument.C2167.Placement=Base.Placement(Base.Vector(-49.688479,145.805019,-24.862693),Base.Rotation(0.026528,-0.773878,0.000000,0.632778))
App.ActiveDocument.addObject("Part::Cylinder","C2168")
App.ActiveDocument.C2168.Radius=0.530367
App.ActiveDocument.C2168.Height=20.00
App.ActiveDocument.C2168.Angle=360.00 
App.ActiveDocument.C2168.Placement=Base.Placement(Base.Vector(-49.508279,142.240155,-24.738065),Base.Rotation(0.073191,-0.772711,0.000000,0.630524))
App.ActiveDocument.addObject("Part::Cylinder","C2169")
App.ActiveDocument.C2169.Radius=0.531430
App.ActiveDocument.C2169.Height=20.00
App.ActiveDocument.C2169.Angle=360.00 
App.ActiveDocument.C2169.Placement=Base.Placement(Base.Vector(-48.998598,138.733416,-25.005053),Base.Rotation(0.126715,-0.761509,0.000000,0.635648))
App.ActiveDocument.addObject("Part::Cylinder","C2170")
App.ActiveDocument.C2170.Radius=0.530965
App.ActiveDocument.C2170.Height=20.00
App.ActiveDocument.C2170.Angle=360.00 
App.ActiveDocument.C2170.Placement=Base.Placement(Base.Vector(-48.370928,135.592697,-24.982904),Base.Rotation(0.159101,-0.736478,0.000000,0.657485))
App.ActiveDocument.addObject("Part::Cylinder","C2171")
App.ActiveDocument.C2171.Radius=0.528961
App.ActiveDocument.C2171.Height=20.00
App.ActiveDocument.C2171.Angle=360.00 
App.ActiveDocument.C2171.Placement=Base.Placement(Base.Vector(-49.070915,134.744653,-26.170291),Base.Rotation(0.376521,-0.544273,0.000000,0.749666))
App.ActiveDocument.addObject("Part::Cylinder","C2172")
App.ActiveDocument.C2172.Radius=0.525435
App.ActiveDocument.C2172.Height=20.00
App.ActiveDocument.C2172.Angle=360.00 
App.ActiveDocument.C2172.Placement=Base.Placement(Base.Vector(-51.404765,132.267298,-25.771550),Base.Rotation(0.421583,-0.503375,0.000000,0.754242))
App.ActiveDocument.addObject("Part::Cylinder","C2173")
App.ActiveDocument.C2173.Radius=0.523634
App.ActiveDocument.C2173.Height=20.00
App.ActiveDocument.C2173.Angle=360.00 
App.ActiveDocument.C2173.Placement=Base.Placement(Base.Vector(-49.246439,122.696289,-21.654056),Base.Rotation(0.051680,-0.771045,0.000000,0.634680))
App.ActiveDocument.addObject("Part::Cylinder","C2174")
App.ActiveDocument.C2174.Radius=0.520872
App.ActiveDocument.C2174.Height=20.00
App.ActiveDocument.C2174.Angle=360.00 
App.ActiveDocument.C2174.Placement=Base.Placement(Base.Vector(-49.085595,119.320058,-20.757968),Base.Rotation(0.108802,-0.750033,0.000000,0.652390))
App.ActiveDocument.addObject("Part::Cylinder","C2175")
App.ActiveDocument.C2175.Radius=0.520180
App.ActiveDocument.C2175.Height=20.00
App.ActiveDocument.C2175.Angle=360.00 
App.ActiveDocument.C2175.Placement=Base.Placement(Base.Vector(-48.514443,115.519375,-19.932924),Base.Rotation(0.140113,-0.748711,0.000000,0.647920))
App.ActiveDocument.addObject("Part::Cylinder","C2176")
App.ActiveDocument.C2176.Radius=0.519130
App.ActiveDocument.C2176.Height=20.00
App.ActiveDocument.C2176.Angle=360.00 
App.ActiveDocument.C2176.Placement=Base.Placement(Base.Vector(-47.615071,110.235686,-20.025092),Base.Rotation(0.074701,-0.725164,0.000000,0.684512))
App.ActiveDocument.addObject("Part::Cylinder","C2177")
App.ActiveDocument.C2177.Radius=0.518159
App.ActiveDocument.C2177.Height=20.00
App.ActiveDocument.C2177.Angle=360.00 
App.ActiveDocument.C2177.Placement=Base.Placement(Base.Vector(-47.512526,104.145421,-20.460224),Base.Rotation(-0.024868,-0.697002,0.000000,0.716637))
App.ActiveDocument.addObject("Part::Cylinder","C2178")
App.ActiveDocument.C2178.Radius=0.519792
App.ActiveDocument.C2178.Height=20.00
App.ActiveDocument.C2178.Angle=360.00 
App.ActiveDocument.C2178.Placement=Base.Placement(Base.Vector(-48.750646,107.150723,-19.972764),Base.Rotation(0.496922,-0.501217,0.000000,0.708414))
App.ActiveDocument.addObject("Part::Cylinder","C2179")
App.ActiveDocument.C2179.Radius=0.477537
App.ActiveDocument.C2179.Height=20.00
App.ActiveDocument.C2179.Angle=360.00 
App.ActiveDocument.C2179.Placement=Base.Placement(Base.Vector(-51.485195,163.830656,-3.982291),Base.Rotation(-0.065068,-0.708871,0.000000,0.702330))
App.ActiveDocument.addObject("Part::Cylinder","C2180")
App.ActiveDocument.C2180.Radius=0.487715
App.ActiveDocument.C2180.Height=20.00
App.ActiveDocument.C2180.Angle=360.00 
App.ActiveDocument.C2180.Placement=Base.Placement(Base.Vector(-51.447039,162.802087,-8.319889),Base.Rotation(-0.047851,-0.719641,0.000000,0.692695))
App.ActiveDocument.addObject("Part::Cylinder","C2181")
App.ActiveDocument.C2181.Radius=0.497806
App.ActiveDocument.C2181.Height=20.00
App.ActiveDocument.C2181.Angle=360.00 
App.ActiveDocument.C2181.Placement=Base.Placement(Base.Vector(-51.266667,161.589366,-12.510610),Base.Rotation(-0.030228,-0.730296,0.000000,0.682462))
App.ActiveDocument.addObject("Part::Cylinder","C2182")
App.ActiveDocument.C2182.Radius=0.506248
App.ActiveDocument.C2182.Height=20.00
App.ActiveDocument.C2182.Angle=360.00 
App.ActiveDocument.C2182.Placement=Base.Placement(Base.Vector(-51.006309,160.462895,-15.914602),Base.Rotation(-0.013457,-0.739764,0.000000,0.672731))
App.ActiveDocument.addObject("Part::Cylinder","C2183")
App.ActiveDocument.C2183.Radius=0.512342
App.ActiveDocument.C2183.Height=20.00
App.ActiveDocument.C2183.Angle=360.00 
App.ActiveDocument.C2183.Placement=Base.Placement(Base.Vector(-50.766465,157.992280,-18.343474),Base.Rotation(0.000767,-0.746059,0.000000,0.665880))
App.ActiveDocument.addObject("Part::Cylinder","C2184")
App.ActiveDocument.C2184.Radius=0.517911
App.ActiveDocument.C2184.Height=20.00
App.ActiveDocument.C2184.Angle=360.00 
App.ActiveDocument.C2184.Placement=Base.Placement(Base.Vector(-50.475143,155.080462,-20.522976),Base.Rotation(0.006579,-0.751418,0.000000,0.659793))
App.ActiveDocument.addObject("Part::Cylinder","C2185")
App.ActiveDocument.C2185.Radius=0.516907
App.ActiveDocument.C2185.Height=20.00
App.ActiveDocument.C2185.Angle=360.00 
App.ActiveDocument.C2185.Placement=Base.Placement(Base.Vector(-50.520977,150.171528,-20.026640),Base.Rotation(-0.000431,-0.753556,0.000000,0.657384))
App.ActiveDocument.addObject("Part::Cylinder","C2186")
App.ActiveDocument.C2186.Radius=0.518690
App.ActiveDocument.C2186.Height=20.00
App.ActiveDocument.C2186.Angle=360.00 
App.ActiveDocument.C2186.Placement=Base.Placement(Base.Vector(-50.427775,145.875913,-20.659935),Base.Rotation(0.012919,-0.757082,0.000000,0.653193))
App.ActiveDocument.addObject("Part::Cylinder","C2187")
App.ActiveDocument.C2187.Radius=0.518319
App.ActiveDocument.C2187.Height=20.00
App.ActiveDocument.C2187.Angle=360.00 
App.ActiveDocument.C2187.Placement=Base.Placement(Base.Vector(-50.279127,142.022400,-20.403199),Base.Rotation(0.086633,-0.751002,0.000000,0.654592))
App.ActiveDocument.addObject("Part::Cylinder","C2188")
App.ActiveDocument.C2188.Radius=0.519020
App.ActiveDocument.C2188.Height=20.00
App.ActiveDocument.C2188.Angle=360.00 
App.ActiveDocument.C2188.Placement=Base.Placement(Base.Vector(-49.689423,138.918223,-20.617510),Base.Rotation(0.175027,-0.723336,0.000000,0.667945))
App.ActiveDocument.addObject("Part::Cylinder","C2189")
App.ActiveDocument.C2189.Radius=0.518913
App.ActiveDocument.C2189.Height=20.00
App.ActiveDocument.C2189.Angle=360.00 
App.ActiveDocument.C2189.Placement=Base.Placement(Base.Vector(-48.648357,132.195999,-18.533958),Base.Rotation(-0.037565,-0.789400,0.000000,0.612729))
App.ActiveDocument.addObject("Part::Cylinder","C2190")
App.ActiveDocument.C2190.Radius=0.514321
App.ActiveDocument.C2190.Height=20.00
App.ActiveDocument.C2190.Angle=360.00 
App.ActiveDocument.C2190.Placement=Base.Placement(Base.Vector(-51.087574,124.993165,-16.281489),Base.Rotation(-0.345273,-0.743228,0.000000,0.573060))
App.ActiveDocument.addObject("Part::Cylinder","C2191")
App.ActiveDocument.C2191.Radius=0.511762
App.ActiveDocument.C2191.Height=20.00
App.ActiveDocument.C2191.Angle=360.00 
App.ActiveDocument.C2191.Placement=Base.Placement(Base.Vector(-50.018781,125.454533,-17.691271),Base.Rotation(0.074469,-0.739418,0.000000,0.669115))
App.ActiveDocument.addObject("Part::Cylinder","C2192")
App.ActiveDocument.C2192.Radius=0.510083
App.ActiveDocument.C2192.Height=20.00
App.ActiveDocument.C2192.Angle=360.00 
App.ActiveDocument.C2192.Placement=Base.Placement(Base.Vector(-49.599911,121.545788,-17.281590),Base.Rotation(0.087283,-0.717684,0.000000,0.690877))
App.ActiveDocument.addObject("Part::Cylinder","C2193")
App.ActiveDocument.C2193.Radius=0.508251
App.ActiveDocument.C2193.Height=20.00
App.ActiveDocument.C2193.Angle=360.00 
App.ActiveDocument.C2193.Placement=Base.Placement(Base.Vector(-49.086442,117.343981,-16.640175),Base.Rotation(0.085696,-0.700444,0.000000,0.708544))
App.ActiveDocument.addObject("Part::Cylinder","C2194")
App.ActiveDocument.C2194.Radius=0.507678
App.ActiveDocument.C2194.Height=20.00
App.ActiveDocument.C2194.Angle=360.00 
App.ActiveDocument.C2194.Placement=Base.Placement(Base.Vector(-48.617880,113.880068,-16.022816),Base.Rotation(0.124182,-0.695579,0.000000,0.707636))
App.ActiveDocument.addObject("Part::Cylinder","C2195")
App.ActiveDocument.C2195.Radius=0.507860
App.ActiveDocument.C2195.Height=20.00
App.ActiveDocument.C2195.Angle=360.00 
App.ActiveDocument.C2195.Placement=Base.Placement(Base.Vector(-47.508912,109.250846,-16.112592),Base.Rotation(0.114909,-0.672260,0.000000,0.731343))
App.ActiveDocument.addObject("Part::Cylinder","C2196")
App.ActiveDocument.C2196.Radius=0.507741
App.ActiveDocument.C2196.Height=20.00
App.ActiveDocument.C2196.Angle=360.00 
App.ActiveDocument.C2196.Placement=Base.Placement(Base.Vector(-47.146724,102.999122,-17.299164),Base.Rotation(-0.002677,-0.624360,0.000000,0.781132))
App.ActiveDocument.addObject("Part::Cylinder","C2197")
App.ActiveDocument.C2197.Radius=0.513198
App.ActiveDocument.C2197.Height=20.00
App.ActiveDocument.C2197.Angle=360.00 
App.ActiveDocument.C2197.Placement=Base.Placement(Base.Vector(-53.754037,110.004171,-15.676215),Base.Rotation(0.707115,0.000135,0.000000,0.707099))
App.ActiveDocument.addObject("Part::Cylinder","C2198")
App.ActiveDocument.C2198.Radius=0.477144
App.ActiveDocument.C2198.Height=20.00
App.ActiveDocument.C2198.Angle=360.00 
App.ActiveDocument.C2198.Placement=Base.Placement(Base.Vector(-51.783496,159.421261,-3.846740),Base.Rotation(-0.029090,-0.716686,0.000000,0.696789))
App.ActiveDocument.addObject("Part::Cylinder","C2199")
App.ActiveDocument.C2199.Radius=0.488620
App.ActiveDocument.C2199.Height=20.00
App.ActiveDocument.C2199.Angle=360.00 
App.ActiveDocument.C2199.Placement=Base.Placement(Base.Vector(-51.598777,158.666702,-8.675245),Base.Rotation(-0.017777,-0.726332,0.000000,0.687114))
App.ActiveDocument.addObject("Part::Cylinder","C2200")
App.ActiveDocument.C2200.Radius=0.498535
App.ActiveDocument.C2200.Height=20.00
App.ActiveDocument.C2200.Angle=360.00 
App.ActiveDocument.C2200.Placement=Base.Placement(Base.Vector(-51.332882,156.812257,-12.713500),Base.Rotation(-0.003639,-0.736547,0.000000,0.676377))
App.ActiveDocument.addObject("Part::Cylinder","C2201")
App.ActiveDocument.C2201.Radius=0.504989
App.ActiveDocument.C2201.Height=20.00
App.ActiveDocument.C2201.Angle=360.00 
App.ActiveDocument.C2201.Placement=Base.Placement(Base.Vector(-51.087006,153.596949,-15.300689),Base.Rotation(0.001792,-0.742806,0.000000,0.669504))
App.ActiveDocument.addObject("Part::Cylinder","C2202")
App.ActiveDocument.C2202.Radius=0.505737
App.ActiveDocument.C2202.Height=20.00
App.ActiveDocument.C2202.Angle=360.00 
App.ActiveDocument.C2202.Placement=Base.Placement(Base.Vector(-51.040105,148.612588,-15.668813),Base.Rotation(0.003878,-0.740991,0.000000,0.671504))
App.ActiveDocument.addObject("Part::Cylinder","C2203")
App.ActiveDocument.C2203.Radius=0.506980
App.ActiveDocument.C2203.Height=20.00
App.ActiveDocument.C2203.Angle=360.00 
App.ActiveDocument.C2203.Placement=Base.Placement(Base.Vector(-50.924694,144.420251,-16.268344),Base.Rotation(0.035158,-0.736593,0.000000,0.675422))
App.ActiveDocument.addObject("Part::Cylinder","C2204")
App.ActiveDocument.C2204.Radius=0.506501
App.ActiveDocument.C2204.Height=20.00
App.ActiveDocument.C2204.Angle=360.00 
App.ActiveDocument.C2204.Placement=Base.Placement(Base.Vector(-50.689950,141.124718,-15.805564),Base.Rotation(0.118102,-0.729015,0.000000,0.674232))
App.ActiveDocument.addObject("Part::Cylinder","C2205")
App.ActiveDocument.C2205.Radius=0.506945
App.ActiveDocument.C2205.Height=20.00
App.ActiveDocument.C2205.Angle=360.00 
App.ActiveDocument.C2205.Placement=Base.Placement(Base.Vector(-50.401917,133.765534,-12.351214),Base.Rotation(-0.132592,-0.824149,0.000000,0.550634))
App.ActiveDocument.addObject("Part::Cylinder","C2206")
App.ActiveDocument.C2206.Radius=0.503881
App.ActiveDocument.C2206.Height=20.00
App.ActiveDocument.C2206.Angle=360.00 
App.ActiveDocument.C2206.Placement=Base.Placement(Base.Vector(-50.317975,130.871881,-13.357660),Base.Rotation(-0.031947,-0.771553,0.000000,0.635362))
App.ActiveDocument.addObject("Part::Cylinder","C2207")
App.ActiveDocument.C2207.Radius=0.500112
App.ActiveDocument.C2207.Height=20.00
App.ActiveDocument.C2207.Angle=360.00 
App.ActiveDocument.C2207.Placement=Base.Placement(Base.Vector(-50.843235,128.139970,-12.809842),Base.Rotation(0.066577,-0.743153,0.000000,0.665801))
App.ActiveDocument.addObject("Part::Cylinder","C2208")
App.ActiveDocument.C2208.Radius=0.498778
App.ActiveDocument.C2208.Height=20.00
App.ActiveDocument.C2208.Angle=360.00 
App.ActiveDocument.C2208.Placement=Base.Placement(Base.Vector(-50.314867,124.925879,-12.464191),Base.Rotation(0.137489,-0.711467,0.000000,0.689138))
App.ActiveDocument.addObject("Part::Cylinder","C2209")
App.ActiveDocument.C2209.Radius=0.497770
App.ActiveDocument.C2209.Height=20.00
App.ActiveDocument.C2209.Angle=360.00 
App.ActiveDocument.C2209.Placement=Base.Placement(Base.Vector(-49.533646,120.985177,-11.991729),Base.Rotation(0.132035,-0.696723,0.000000,0.705084))
App.ActiveDocument.addObject("Part::Cylinder","C2210")
App.ActiveDocument.C2210.Radius=0.496725
App.ActiveDocument.C2210.Height=20.00
App.ActiveDocument.C2210.Angle=360.00 
App.ActiveDocument.C2210.Placement=Base.Placement(Base.Vector(-48.703577,116.302773,-11.606732),Base.Rotation(0.109590,-0.680010,0.000000,0.724966))
App.ActiveDocument.addObject("Part::Cylinder","C2211")
App.ActiveDocument.C2211.Radius=0.496830
App.ActiveDocument.C2211.Height=20.00
App.ActiveDocument.C2211.Angle=360.00 
App.ActiveDocument.C2211.Placement=Base.Placement(Base.Vector(-48.045504,112.464842,-11.412854),Base.Rotation(0.143628,-0.665346,0.000000,0.732588))
App.ActiveDocument.addObject("Part::Cylinder","C2212")
App.ActiveDocument.C2212.Radius=0.497626
App.ActiveDocument.C2212.Height=20.00
App.ActiveDocument.C2212.Angle=360.00 
App.ActiveDocument.C2212.Placement=Base.Placement(Base.Vector(-47.388219,109.362503,-12.654116),Base.Rotation(0.207427,-0.581817,0.000000,0.786424))
App.ActiveDocument.addObject("Part::Cylinder","C2213")
App.ActiveDocument.C2213.Radius=0.499389
App.ActiveDocument.C2213.Height=20.00
App.ActiveDocument.C2213.Angle=360.00 
App.ActiveDocument.C2213.Placement=Base.Placement(Base.Vector(-45.939144,102.214254,-13.832809),Base.Rotation(0.046724,-0.567653,0.000000,0.821941))
App.ActiveDocument.addObject("Part::Cylinder","C2214")
App.ActiveDocument.C2214.Radius=0.477195
App.ActiveDocument.C2214.Height=20.00
App.ActiveDocument.C2214.Angle=360.00 
App.ActiveDocument.C2214.Placement=Base.Placement(Base.Vector(-51.857677,155.122518,-3.891772),Base.Rotation(0.005850,-0.718195,0.000000,0.695817))
App.ActiveDocument.addObject("Part::Cylinder","C2215")
App.ActiveDocument.C2215.Radius=0.487027
App.ActiveDocument.C2215.Height=20.00
App.ActiveDocument.C2215.Angle=360.00 
App.ActiveDocument.C2215.Placement=Base.Placement(Base.Vector(-51.667706,154.084101,-8.030474),Base.Rotation(0.006186,-0.725344,0.000000,0.688359))
App.ActiveDocument.addObject("Part::Cylinder","C2216")
App.ActiveDocument.C2216.Radius=0.493887
App.ActiveDocument.C2216.Height=20.00
App.ActiveDocument.C2216.Angle=360.00 
App.ActiveDocument.C2216.Placement=Base.Placement(Base.Vector(-51.461200,151.540853,-10.891738),Base.Rotation(0.012140,-0.729532,0.000000,0.683838))
App.ActiveDocument.addObject("Part::Cylinder","C2217")
App.ActiveDocument.C2217.Radius=0.496130
App.ActiveDocument.C2217.Height=20.00
App.ActiveDocument.C2217.Angle=360.00 
App.ActiveDocument.C2217.Placement=Base.Placement(Base.Vector(-51.267400,146.575032,-12.046448),Base.Rotation(0.032434,-0.720278,0.000000,0.692927))
App.ActiveDocument.addObject("Part::Cylinder","C2218")
App.ActiveDocument.C2218.Radius=0.495955
App.ActiveDocument.C2218.Height=20.00
App.ActiveDocument.C2218.Angle=360.00 
App.ActiveDocument.C2218.Placement=Base.Placement(Base.Vector(-51.002229,141.909360,-11.874817),Base.Rotation(0.052390,-0.716457,0.000000,0.695661))
App.ActiveDocument.addObject("Part::Cylinder","C2219")
App.ActiveDocument.C2219.Radius=0.494519
App.ActiveDocument.C2219.Height=20.00
App.ActiveDocument.C2219.Angle=360.00 
App.ActiveDocument.C2219.Placement=Base.Placement(Base.Vector(-50.694570,135.390600,-9.933831),Base.Rotation(-0.058609,-0.751673,0.000000,0.656927))
App.ActiveDocument.addObject("Part::Cylinder","C2220")
App.ActiveDocument.C2220.Radius=0.490994
App.ActiveDocument.C2220.Height=20.00
App.ActiveDocument.C2220.Angle=360.00 
App.ActiveDocument.C2220.Placement=Base.Placement(Base.Vector(-51.524188,131.233045,-8.955726),Base.Rotation(-0.035086,-0.749719,0.000000,0.660825))
App.ActiveDocument.addObject("Part::Cylinder","C2221")
App.ActiveDocument.C2221.Radius=0.488377
App.ActiveDocument.C2221.Height=20.00
App.ActiveDocument.C2221.Angle=360.00 
App.ActiveDocument.C2221.Placement=Base.Placement(Base.Vector(-51.362348,128.711660,-7.950741),Base.Rotation(0.100144,-0.733386,0.000000,0.672396))
App.ActiveDocument.addObject("Part::Cylinder","C2222")
App.ActiveDocument.C2222.Radius=0.487005
App.ActiveDocument.C2222.Height=20.00
App.ActiveDocument.C2222.Angle=360.00 
App.ActiveDocument.C2222.Placement=Base.Placement(Base.Vector(-50.702486,125.318602,-7.130498),Base.Rotation(0.161639,-0.712554,0.000000,0.682744))
App.ActiveDocument.addObject("Part::Cylinder","C2223")
App.ActiveDocument.C2223.Radius=0.485605
App.ActiveDocument.C2223.Height=20.00
App.ActiveDocument.C2223.Angle=360.00 
App.ActiveDocument.C2223.Placement=Base.Placement(Base.Vector(-49.703712,121.058349,-6.122826),Base.Rotation(0.177346,-0.699684,0.000000,0.692092))
App.ActiveDocument.addObject("Part::Cylinder","C2224")
App.ActiveDocument.C2224.Radius=0.485639
App.ActiveDocument.C2224.Height=20.00
App.ActiveDocument.C2224.Angle=360.00 
App.ActiveDocument.C2224.Placement=Base.Placement(Base.Vector(-48.506906,116.072372,-5.908559),Base.Rotation(0.143882,-0.692050,0.000000,0.707365))
App.ActiveDocument.addObject("Part::Cylinder","C2225")
App.ActiveDocument.C2225.Radius=0.485846
App.ActiveDocument.C2225.Height=20.00
App.ActiveDocument.C2225.Angle=360.00 
App.ActiveDocument.C2225.Placement=Base.Placement(Base.Vector(-48.847300,114.773975,-5.737963),Base.Rotation(0.366942,-0.591038,0.000000,0.718350))
App.ActiveDocument.addObject("Part::Cylinder","C2226")
App.ActiveDocument.C2226.Radius=0.490302
App.ActiveDocument.C2226.Height=20.00
App.ActiveDocument.C2226.Angle=360.00 
App.ActiveDocument.C2226.Placement=Base.Placement(Base.Vector(-51.497090,114.760835,-8.886540),Base.Rotation(0.555023,-0.186737,0.000000,0.810604))
App.ActiveDocument.addObject("Part::Cylinder","C2227")
App.ActiveDocument.C2227.Radius=0.498453
App.ActiveDocument.C2227.Height=20.00
App.ActiveDocument.C2227.Angle=360.00 
App.ActiveDocument.C2227.Placement=Base.Placement(Base.Vector(-46.515699,98.575908,0.261558),Base.Rotation(-0.584137,-0.741748,0.000000,0.329537))
App.ActiveDocument.addObject("Part::Cylinder","C2228")
App.ActiveDocument.C2228.Radius=0.477186
App.ActiveDocument.C2228.Height=20.00
App.ActiveDocument.C2228.Angle=360.00 
App.ActiveDocument.C2228.Placement=Base.Placement(Base.Vector(-51.693344,150.606712,-4.010293),Base.Rotation(0.050330,-0.708252,0.000000,0.704163))
App.ActiveDocument.addObject("Part::Cylinder","C2229")
App.ActiveDocument.C2229.Radius=0.477927
App.ActiveDocument.C2229.Height=20.00
App.ActiveDocument.C2229.Angle=360.00 
App.ActiveDocument.C2229.Placement=Base.Placement(Base.Vector(-51.281390,146.041535,-4.409047),Base.Rotation(0.070117,-0.694883,0.000000,0.715697))
App.ActiveDocument.addObject("Part::Cylinder","C2230")
App.ActiveDocument.C2230.Radius=0.478512
App.ActiveDocument.C2230.Height=20.00
App.ActiveDocument.C2230.Angle=360.00 
App.ActiveDocument.C2230.Placement=Base.Placement(Base.Vector(-50.801558,139.744275,-4.177809),Base.Rotation(-0.018874,-0.706636,0.000000,0.707326))
App.ActiveDocument.addObject("Part::Cylinder","C2231")
App.ActiveDocument.C2231.Radius=0.477552
App.ActiveDocument.C2231.Height=20.00
App.ActiveDocument.C2231.Angle=360.00 
App.ActiveDocument.C2231.Placement=Base.Placement(Base.Vector(-51.829051,133.166997,-3.297406),Base.Rotation(-0.134742,-0.726969,0.000000,0.673321))
App.ActiveDocument.addObject("Part::Cylinder","C2232")
App.ActiveDocument.C2232.Radius=0.476804
App.ActiveDocument.C2232.Height=20.00
App.ActiveDocument.C2232.Angle=360.00 
App.ActiveDocument.C2232.Placement=Base.Placement(Base.Vector(-51.975187,130.845324,-3.519471),Base.Rotation(0.060480,-0.723963,0.000000,0.687182))
App.ActiveDocument.addObject("Part::Cylinder","C2233")
App.ActiveDocument.C2233.Radius=0.477552
App.ActiveDocument.C2233.Height=20.00
App.ActiveDocument.C2233.Angle=360.00 
App.ActiveDocument.C2233.Placement=Base.Placement(Base.Vector(-51.412017,127.380867,-3.501205),Base.Rotation(0.144916,-0.709073,0.000000,0.690083))
App.ActiveDocument.addObject("Part::Cylinder","C2234")
App.ActiveDocument.C2234.Radius=0.477790
App.ActiveDocument.C2234.Height=20.00
App.ActiveDocument.C2234.Angle=360.00 
App.ActiveDocument.C2234.Placement=Base.Placement(Base.Vector(-50.468654,123.450416,-3.100447),Base.Rotation(0.177136,-0.697433,0.000000,0.694413))
App.ActiveDocument.addObject("Part::Cylinder","C2235")
App.ActiveDocument.C2235.Radius=0.478415
App.ActiveDocument.C2235.Height=20.00
App.ActiveDocument.C2235.Angle=360.00 
App.ActiveDocument.C2235.Placement=Base.Placement(Base.Vector(-49.274341,118.921767,-2.810736),Base.Rotation(0.181536,-0.690671,0.000000,0.700013))
App.ActiveDocument.addObject("Part::Cylinder","C2236")
App.ActiveDocument.C2236.Radius=0.479153
App.ActiveDocument.C2236.Height=20.00
App.ActiveDocument.C2236.Angle=360.00 
App.ActiveDocument.C2236.Placement=Base.Placement(Base.Vector(-48.140070,113.993415,-2.601324),Base.Rotation(0.151328,-0.695100,0.000000,0.702806))
App.ActiveDocument.recompute()
