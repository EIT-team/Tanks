import FreeCAD
import Part
import Part,PartGui
from FreeCAD import Base
App.ActiveDocument.addObject("Part::Cylinder","C1")
App.ActiveDocument.C1.Radius=0.750000
App.ActiveDocument.C1.Height=15.00
App.ActiveDocument.C1.Angle=360.00 
App.ActiveDocument.C1.Placement=Base.Placement(Base.Vector(-31.750473,-140.925197,548.718487),Base.Rotation(-0.001598,-0.044044,0.000000,0.999028))
App.ActiveDocument.addObject("Part::Cylinder","C2")
App.ActiveDocument.C2.Radius=0.750000
App.ActiveDocument.C2.Height=15.00
App.ActiveDocument.C2.Angle=360.00 
App.ActiveDocument.C2.Placement=Base.Placement(Base.Vector(-28.571134,-140.921141,548.888035),Base.Rotation(-0.001394,-0.008445,0.000000,0.999963))
App.ActiveDocument.addObject("Part::Cylinder","C3")
App.ActiveDocument.C3.Radius=0.750000
App.ActiveDocument.C3.Height=15.00
App.ActiveDocument.C3.Angle=360.00 
App.ActiveDocument.C3.Placement=Base.Placement(Base.Vector(-25.367793,-140.941206,548.830592),Base.Rotation(-0.002398,0.026158,0.000000,0.999655))
App.ActiveDocument.addObject("Part::Cylinder","C4")
App.ActiveDocument.C4.Radius=0.750000
App.ActiveDocument.C4.Height=15.00
App.ActiveDocument.C4.Angle=360.00 
App.ActiveDocument.C4.Placement=Base.Placement(Base.Vector(-22.154122,-140.920053,548.552135),Base.Rotation(-0.001342,0.059640,0.000000,0.998219))
App.ActiveDocument.addObject("Part::Cylinder","C5")
App.ActiveDocument.C5.Radius=0.750000
App.ActiveDocument.C5.Height=15.00
App.ActiveDocument.C5.Angle=360.00 
App.ActiveDocument.C5.Placement=Base.Placement(Base.Vector(-18.956487,-140.923837,548.056177),Base.Rotation(-0.001535,0.092561,0.000000,0.995706))
App.ActiveDocument.addObject("Part::Cylinder","C6")
App.ActiveDocument.C6.Radius=0.750000
App.ActiveDocument.C6.Height=15.00
App.ActiveDocument.C6.Angle=360.00 
App.ActiveDocument.C6.Placement=Base.Placement(Base.Vector(-15.792301,-140.910164,547.353100),Base.Rotation(-0.000852,0.125112,0.000000,0.992142))
App.ActiveDocument.addObject("Part::Cylinder","C7")
App.ActiveDocument.C7.Radius=0.750000
App.ActiveDocument.C7.Height=15.00
App.ActiveDocument.C7.Angle=360.00 
App.ActiveDocument.C7.Placement=Base.Placement(Base.Vector(-12.679737,-140.916922,546.445297),Base.Rotation(-0.001198,0.157489,0.000000,0.987520))
App.ActiveDocument.addObject("Part::Cylinder","C8")
App.ActiveDocument.C8.Radius=0.750000
App.ActiveDocument.C8.Height=15.00
App.ActiveDocument.C8.Angle=360.00 
App.ActiveDocument.C8.Placement=Base.Placement(Base.Vector(-9.638671,-140.909530,545.338622),Base.Rotation(-0.000829,0.189993,0.000000,0.981785))
App.ActiveDocument.addObject("Part::Cylinder","C9")
App.ActiveDocument.C9.Radius=0.750000
App.ActiveDocument.C9.Height=15.00
App.ActiveDocument.C9.Angle=360.00 
App.ActiveDocument.C9.Placement=Base.Placement(Base.Vector(-6.702642,-140.917282,544.040554),Base.Rotation(-0.001232,0.223558,0.000000,0.974690))
App.ActiveDocument.addObject("Part::Cylinder","C10")
App.ActiveDocument.C10.Radius=0.750000
App.ActiveDocument.C10.Height=15.00
App.ActiveDocument.C10.Angle=360.00 
App.ActiveDocument.C10.Placement=Base.Placement(Base.Vector(-3.893753,-140.909850,542.555589),Base.Rotation(-0.000859,0.258443,0.000000,0.966026))
App.ActiveDocument.addObject("Part::Cylinder","C11")
App.ActiveDocument.C11.Radius=0.750000
App.ActiveDocument.C11.Height=15.00
App.ActiveDocument.C11.Angle=360.00 
App.ActiveDocument.C11.Placement=Base.Placement(Base.Vector(-1.243220,-140.917632,540.892045),Base.Rotation(-0.001275,0.295286,0.000000,0.955408))
App.ActiveDocument.addObject("Part::Cylinder","C12")
App.ActiveDocument.C12.Radius=0.750000
App.ActiveDocument.C12.Height=15.00
App.ActiveDocument.C12.Angle=360.00 
App.ActiveDocument.C12.Placement=Base.Placement(Base.Vector(1.218168,-140.910089,539.059684),Base.Rotation(-0.000893,0.334547,0.000000,0.942378))
App.ActiveDocument.addObject("Part::Cylinder","C13")
App.ActiveDocument.C13.Radius=0.750000
App.ActiveDocument.C13.Height=15.00
App.ActiveDocument.C13.Angle=360.00 
App.ActiveDocument.C13.Placement=Base.Placement(Base.Vector(3.460064,-140.917709,537.068811),Base.Rotation(-0.001320,0.376494,0.000000,0.926418))
App.ActiveDocument.addObject("Part::Cylinder","C14")
App.ActiveDocument.C14.Radius=0.750000
App.ActiveDocument.C14.Height=15.00
App.ActiveDocument.C14.Angle=360.00 
App.ActiveDocument.C14.Placement=Base.Placement(Base.Vector(5.449918,-140.910070,534.937638),Base.Rotation(-0.000927,0.421413,0.000000,0.906868))
App.ActiveDocument.addObject("Part::Cylinder","C15")
App.ActiveDocument.C15.Radius=0.750000
App.ActiveDocument.C15.Height=15.00
App.ActiveDocument.C15.Angle=360.00 
App.ActiveDocument.C15.Placement=Base.Placement(Base.Vector(7.159542,-140.917169,532.681650),Base.Rotation(-0.001354,0.469084,0.000000,0.883153))
App.ActiveDocument.addObject("Part::Cylinder","C16")
App.ActiveDocument.C16.Radius=0.750000
App.ActiveDocument.C16.Height=15.00
App.ActiveDocument.C16.Angle=360.00 
App.ActiveDocument.C16.Placement=Base.Placement(Base.Vector(8.592016,-140.909588,530.286029),Base.Rotation(-0.000954,0.517090,0.000000,0.855931))
App.ActiveDocument.addObject("Part::Cylinder","C17")
App.ActiveDocument.C17.Radius=0.750000
App.ActiveDocument.C17.Height=15.00
App.ActiveDocument.C17.Angle=360.00 
App.ActiveDocument.C17.Placement=Base.Placement(Base.Vector(9.782967,-140.916292,527.693536),Base.Rotation(-0.001391,0.560991,0.000000,0.827820))
App.ActiveDocument.addObject("Part::Cylinder","C18")
App.ActiveDocument.C18.Radius=0.750000
App.ActiveDocument.C18.Height=15.00
App.ActiveDocument.C18.Angle=360.00 
App.ActiveDocument.C18.Placement=Base.Placement(Base.Vector(10.731606,-140.908903,524.925574),Base.Rotation(-0.000978,0.600449,0.000000,0.799662))
App.ActiveDocument.addObject("Part::Cylinder","C19")
App.ActiveDocument.C19.Radius=0.750000
App.ActiveDocument.C19.Height=15.00
App.ActiveDocument.C19.Angle=360.00 
App.ActiveDocument.C19.Placement=Base.Placement(Base.Vector(11.437141,-140.915461,522.004531),Base.Rotation(-0.001438,0.635467,0.000000,0.772126))
App.ActiveDocument.addObject("Part::Cylinder","C20")
App.ActiveDocument.C20.Radius=0.750000
App.ActiveDocument.C20.Height=15.00
App.ActiveDocument.C20.Angle=360.00 
App.ActiveDocument.C20.Placement=Base.Placement(Base.Vector(11.902352,-140.908322,518.963047),Base.Rotation(-0.001010,0.666547,0.000000,0.745463))
App.ActiveDocument.addObject("Part::Cylinder","C21")
App.ActiveDocument.C21.Radius=0.750000
App.ActiveDocument.C21.Height=15.00
App.ActiveDocument.C21.Angle=360.00 
App.ActiveDocument.C21.Placement=Base.Placement(Base.Vector(12.132182,-140.914847,515.827547),Base.Rotation(-0.001499,0.694115,0.000000,0.719862))
App.ActiveDocument.addObject("Part::Cylinder","C22")
App.ActiveDocument.C22.Radius=0.750000
App.ActiveDocument.C22.Height=15.00
App.ActiveDocument.C22.Angle=360.00 
App.ActiveDocument.C22.Placement=Base.Placement(Base.Vector(12.135582,-140.907961,512.627918),Base.Rotation(-0.001057,0.718757,0.000000,0.695260))
App.ActiveDocument.addObject("Part::Cylinder","C23")
App.ActiveDocument.C23.Radius=0.750000
App.ActiveDocument.C23.Height=15.00
App.ActiveDocument.C23.Angle=360.00 
App.ActiveDocument.C23.Placement=Base.Placement(Base.Vector(11.920341,-140.914602,509.388495),Base.Rotation(-0.001589,0.740971,0.000000,0.671535))
App.ActiveDocument.addObject("Part::Cylinder","C24")
App.ActiveDocument.C24.Radius=0.750000
App.ActiveDocument.C24.Height=15.00
App.ActiveDocument.C24.Angle=360.00 
App.ActiveDocument.C24.Placement=Base.Placement(Base.Vector(11.497409,-140.907902,506.131440),Base.Rotation(-0.001129,0.761167,0.000000,0.648555))
App.ActiveDocument.addObject("Part::Cylinder","C25")
App.ActiveDocument.C25.Radius=0.750000
App.ActiveDocument.C25.Height=15.00
App.ActiveDocument.C25.Angle=360.00 
App.ActiveDocument.C25.Placement=Base.Placement(Base.Vector(10.875085,-140.914797,502.878013),Base.Rotation(-0.001720,0.779789,0.000000,0.626040))
App.ActiveDocument.addObject("Part::Cylinder","C26")
App.ActiveDocument.C26.Radius=0.750000
App.ActiveDocument.C26.Height=15.00
App.ActiveDocument.C26.Angle=360.00 
App.ActiveDocument.C26.Placement=Base.Placement(Base.Vector(10.062934,-140.908186,499.644635),Base.Rotation(-0.001236,0.797087,0.000000,0.603864))
App.ActiveDocument.addObject("Part::Cylinder","C27")
App.ActiveDocument.C27.Radius=0.750000
App.ActiveDocument.C27.Height=15.00
App.ActiveDocument.C27.Angle=360.00 
App.ActiveDocument.C27.Placement=Base.Placement(Base.Vector(9.068466,-140.915528,496.450397),Base.Rotation(-0.001914,0.813430,0.000000,0.581659))
App.ActiveDocument.addObject("Part::Cylinder","C28")
App.ActiveDocument.C28.Radius=0.750000
App.ActiveDocument.C28.Height=15.00
App.ActiveDocument.C28.Angle=360.00 
App.ActiveDocument.C28.Placement=Base.Placement(Base.Vector(7.899069,-140.908905,493.309507),Base.Rotation(-0.001399,0.828972,0.000000,0.559288))
App.ActiveDocument.addObject("Part::Cylinder","C29")
App.ActiveDocument.C29.Radius=0.750000
App.ActiveDocument.C29.Height=15.00
App.ActiveDocument.C29.Angle=360.00 
App.ActiveDocument.C29.Placement=Base.Placement(Base.Vector(6.561055,-140.916917,490.240190),Base.Rotation(-0.002205,0.844010,0.000000,0.536323))
App.ActiveDocument.addObject("Part::Cylinder","C30")
App.ActiveDocument.C30.Radius=0.750000
App.ActiveDocument.C30.Height=15.00
App.ActiveDocument.C30.Angle=360.00 
App.ActiveDocument.C30.Placement=Base.Placement(Base.Vector(5.060057,-140.910190,487.256905),Base.Rotation(-0.001651,0.858610,0.000000,0.512626))
App.ActiveDocument.addObject("Part::Cylinder","C31")
App.ActiveDocument.C31.Radius=0.750000
App.ActiveDocument.C31.Height=15.00
App.ActiveDocument.C31.Angle=360.00 
App.ActiveDocument.C31.Placement=Base.Placement(Base.Vector(3.402220,-140.919391,484.380265),Base.Rotation(-0.002679,0.873039,0.000000,0.487642))
App.ActiveDocument.addObject("Part::Cylinder","C32")
App.ActiveDocument.C32.Radius=0.750000
App.ActiveDocument.C32.Height=15.00
App.ActiveDocument.C32.Angle=360.00 
App.ActiveDocument.C32.Placement=Base.Placement(Base.Vector(1.592932,-140.912478,481.628184),Base.Rotation(-0.002084,0.887335,0.000000,0.461120))
App.ActiveDocument.addObject("Part::Cylinder","C33")
App.ActiveDocument.C33.Radius=0.750000
App.ActiveDocument.C33.Height=15.00
App.ActiveDocument.C33.Angle=360.00 
App.ActiveDocument.C33.Placement=Base.Placement(Base.Vector(-0.361154,-140.923667,479.023676),Base.Rotation(-0.003516,0.901655,0.000000,0.432441))
App.ActiveDocument.addObject("Part::Cylinder","C34")
App.ActiveDocument.C34.Radius=0.750000
App.ActiveDocument.C34.Height=15.00
App.ActiveDocument.C34.Angle=360.00 
App.ActiveDocument.C34.Placement=Base.Placement(Base.Vector(-2.450550,-140.935734,476.591652),Base.Rotation(-0.005296,0.916060,0.000000,0.401007))
App.ActiveDocument.addObject("Part::Cylinder","C35")
App.ActiveDocument.C35.Radius=0.750000
App.ActiveDocument.C35.Height=15.00
App.ActiveDocument.C35.Angle=360.00 
App.ActiveDocument.C35.Placement=Base.Placement(Base.Vector(-4.670420,-140.957112,474.354130),Base.Rotation(-0.008710,0.930362,0.000000,0.366538))
App.ActiveDocument.addObject("Part::Cylinder","C36")
App.ActiveDocument.C36.Radius=0.750000
App.ActiveDocument.C36.Height=15.00
App.ActiveDocument.C36.Angle=360.00 
App.ActiveDocument.C36.Placement=Base.Placement(Base.Vector(-6.993628,-140.941891,472.353387),Base.Rotation(-0.007420,0.944755,0.000000,0.327693))
App.ActiveDocument.addObject("Part::Cylinder","C37")
App.ActiveDocument.C37.Radius=0.750000
App.ActiveDocument.C37.Height=15.00
App.ActiveDocument.C37.Angle=360.00 
App.ActiveDocument.C37.Placement=Base.Placement(Base.Vector(-9.408923,-140.966756,470.611933),Base.Rotation(-0.013049,0.959437,0.000000,0.281620))
App.ActiveDocument.addObject("Part::Cylinder","C38")
App.ActiveDocument.C38.Radius=0.750000
App.ActiveDocument.C38.Height=15.00
App.ActiveDocument.C38.Angle=360.00 
App.ActiveDocument.C38.Placement=Base.Placement(Base.Vector(-34.904286,-140.909792,548.321187),Base.Rotation(-0.000829,-0.079850,0.000000,0.996807))
App.ActiveDocument.addObject("Part::Cylinder","C39")
App.ActiveDocument.C39.Radius=0.750000
App.ActiveDocument.C39.Height=15.00
App.ActiveDocument.C39.Angle=360.00 
App.ActiveDocument.C39.Placement=Base.Placement(Base.Vector(-38.040284,-140.915269,547.700474),Base.Rotation(-0.001108,-0.114657,0.000000,0.993405))
App.ActiveDocument.addObject("Part::Cylinder","C40")
App.ActiveDocument.C40.Radius=0.750000
App.ActiveDocument.C40.Height=15.00
App.ActiveDocument.C40.Angle=360.00 
App.ActiveDocument.C40.Placement=Base.Placement(Base.Vector(-41.145440,-140.908136,546.861036),Base.Rotation(-0.000752,-0.148343,0.000000,0.988936))
App.ActiveDocument.addObject("Part::Cylinder","C41")
App.ActiveDocument.C41.Radius=0.750000
App.ActiveDocument.C41.Height=15.00
App.ActiveDocument.C41.Angle=360.00 
App.ActiveDocument.C41.Placement=Base.Placement(Base.Vector(-44.210321,-140.914903,545.808068),Base.Rotation(-0.001100,-0.180680,0.000000,0.983541))
App.ActiveDocument.addObject("Part::Cylinder","C42")
App.ActiveDocument.C42.Radius=0.750000
App.ActiveDocument.C42.Height=15.00
App.ActiveDocument.C42.Angle=360.00 
App.ActiveDocument.C42.Placement=Base.Placement(Base.Vector(-47.222222,-140.908039,544.551559),Base.Rotation(-0.000756,-0.211706,0.000000,0.977333))
App.ActiveDocument.addObject("Part::Cylinder","C43")
App.ActiveDocument.C43.Radius=0.750000
App.ActiveDocument.C43.Height=15.00
App.ActiveDocument.C43.Angle=360.00 
App.ActiveDocument.C43.Placement=Base.Placement(Base.Vector(-50.174448,-140.914912,543.098651),Base.Rotation(-0.001116,-0.241225,0.000000,0.970468))
App.ActiveDocument.addObject("Part::Cylinder","C44")
App.ActiveDocument.C44.Radius=0.750000
App.ActiveDocument.C44.Height=15.00
App.ActiveDocument.C44.Angle=360.00 
App.ActiveDocument.C44.Placement=Base.Placement(Base.Vector(-53.058412,-140.908101,541.460817),Base.Rotation(-0.000771,-0.269256,0.000000,0.963068))
App.ActiveDocument.addObject("Part::Cylinder","C45")
App.ActiveDocument.C45.Radius=0.750000
App.ActiveDocument.C45.Height=15.00
App.ActiveDocument.C45.Angle=360.00 
App.ActiveDocument.C45.Placement=Base.Placement(Base.Vector(-55.866087,-140.915201,539.648036),Base.Rotation(-0.001148,-0.295855,0.000000,0.955232))
App.ActiveDocument.addObject("Part::Cylinder","C46")
App.ActiveDocument.C46.Radius=0.750000
App.ActiveDocument.C46.Height=15.00
App.ActiveDocument.C46.Angle=360.00 
App.ActiveDocument.C46.Placement=Base.Placement(Base.Vector(-58.590646,-140.908376,537.672171),Base.Rotation(-0.000798,-0.321104,0.000000,0.947044))
App.ActiveDocument.addObject("Part::Cylinder","C47")
App.ActiveDocument.C47.Radius=0.750000
App.ActiveDocument.C47.Height=15.00
App.ActiveDocument.C47.Angle=360.00 
App.ActiveDocument.C47.Placement=Base.Placement(Base.Vector(-61.227011,-140.915848,535.542469),Base.Rotation(-0.001203,-0.345035,0.000000,0.938589))
App.ActiveDocument.addObject("Part::Cylinder","C48")
App.ActiveDocument.C48.Radius=0.750000
App.ActiveDocument.C48.Height=15.00
App.ActiveDocument.C48.Angle=360.00 
App.ActiveDocument.C48.Placement=Base.Placement(Base.Vector(-63.772271,-140.908925,533.269557),Base.Rotation(-0.000842,-0.367653,0.000000,0.929963))
App.ActiveDocument.addObject("Part::Cylinder","C49")
App.ActiveDocument.C49.Radius=0.750000
App.ActiveDocument.C49.Height=15.00
App.ActiveDocument.C49.Angle=360.00 
App.ActiveDocument.C49.Placement=Base.Placement(Base.Vector(-66.215877,-140.916893,530.869099),Base.Rotation(-0.001283,-0.389468,0.000000,0.921039))
App.ActiveDocument.addObject("Part::Cylinder","C50")
App.ActiveDocument.C50.Radius=0.750000
App.ActiveDocument.C50.Height=15.00
App.ActiveDocument.C50.Angle=360.00 
App.ActiveDocument.C50.Placement=Base.Placement(Base.Vector(-68.534097,-140.909735,528.364527),Base.Rotation(-0.000904,-0.411630,0.000000,0.911351))
App.ActiveDocument.addObject("Part::Cylinder","C51")
App.ActiveDocument.C51.Radius=0.750000
App.ActiveDocument.C51.Height=15.00
App.ActiveDocument.C51.Angle=360.00 
App.ActiveDocument.C51.Placement=Base.Placement(Base.Vector(-70.715210,-140.918202,525.761955),Base.Rotation(-0.001384,-0.434332,0.000000,0.900752))
App.ActiveDocument.addObject("Part::Cylinder","C52")
App.ActiveDocument.C52.Radius=0.750000
App.ActiveDocument.C52.Height=15.00
App.ActiveDocument.C52.Angle=360.00 
App.ActiveDocument.C52.Placement=Base.Placement(Base.Vector(-72.741443,-140.910706,523.075213),Base.Rotation(-0.000981,-0.458104,0.000000,0.888898))
App.ActiveDocument.addObject("Part::Cylinder","C53")
App.ActiveDocument.C53.Radius=0.750000
App.ActiveDocument.C53.Height=15.00
App.ActiveDocument.C53.Angle=360.00 
App.ActiveDocument.C53.Placement=Base.Placement(Base.Vector(-74.597706,-140.919619,520.310064),Base.Rotation(-0.001505,-0.483082,0.000000,0.875574))
App.ActiveDocument.addObject("Part::Cylinder","C54")
App.ActiveDocument.C54.Radius=0.750000
App.ActiveDocument.C54.Height=15.00
App.ActiveDocument.C54.Angle=360.00 
App.ActiveDocument.C54.Placement=Base.Placement(Base.Vector(-76.268224,-140.911735,517.477076),Base.Rotation(-0.001073,-0.509449,0.000000,0.860500))
App.ActiveDocument.addObject("Part::Cylinder","C55")
App.ActiveDocument.C55.Radius=0.750000
App.ActiveDocument.C55.Height=15.00
App.ActiveDocument.C55.Angle=360.00 
App.ActiveDocument.C55.Placement=Base.Placement(Base.Vector(-77.734513,-140.921038,514.587024),Base.Rotation(-0.001647,-0.537385,0.000000,0.843335))
App.ActiveDocument.addObject("Part::Cylinder","C56")
App.ActiveDocument.C56.Radius=0.750000
App.ActiveDocument.C56.Height=15.00
App.ActiveDocument.C56.Angle=360.00 
App.ActiveDocument.C56.Placement=Base.Placement(Base.Vector(-78.981114,-140.912704,511.651628),Base.Rotation(-0.001180,-0.566855,0.000000,0.823817))
App.ActiveDocument.addObject("Part::Cylinder","C57")
App.ActiveDocument.C57.Radius=0.750000
App.ActiveDocument.C57.Height=15.00
App.ActiveDocument.C57.Angle=360.00 
App.ActiveDocument.C57.Placement=Base.Placement(Base.Vector(-79.989560,-140.922176,508.687455),Base.Rotation(-0.001804,-0.597957,0.000000,0.801526))
App.ActiveDocument.addObject("Part::Cylinder","C58")
App.ActiveDocument.C58.Radius=0.750000
App.ActiveDocument.C58.Height=15.00
App.ActiveDocument.C58.Angle=360.00 
App.ActiveDocument.C58.Placement=Base.Placement(Base.Vector(-80.744929,-140.913367,505.710547),Base.Rotation(-0.001295,-0.630487,0.000000,0.776199))
App.ActiveDocument.addObject("Part::Cylinder","C59")
App.ActiveDocument.C59.Radius=0.750000
App.ActiveDocument.C59.Height=15.00
App.ActiveDocument.C59.Angle=360.00 
App.ActiveDocument.C59.Placement=Base.Placement(Base.Vector(-81.236389,-140.922669,502.728880),Base.Rotation(-0.001966,-0.663805,0.000000,0.747903))
App.ActiveDocument.addObject("Part::Cylinder","C60")
App.ActiveDocument.C60.Radius=0.750000
App.ActiveDocument.C60.Height=15.00
App.ActiveDocument.C60.Angle=360.00 
App.ActiveDocument.C60.Placement=Base.Placement(Base.Vector(-81.454330,-140.913452,499.768026),Base.Rotation(-0.001409,-0.697736,0.000000,0.716354))
App.ActiveDocument.addObject("Part::Cylinder","C61")
App.ActiveDocument.C61.Radius=0.750000
App.ActiveDocument.C61.Height=15.00
App.ActiveDocument.C61.Angle=360.00 
App.ActiveDocument.C61.Placement=Base.Placement(Base.Vector(-81.391587,-140.922143,496.826127),Base.Rotation(-0.002117,-0.731084,0.000000,0.682284))
App.ActiveDocument.addObject("Part::Cylinder","C62")
App.ActiveDocument.C62.Radius=0.750000
App.ActiveDocument.C62.Height=15.00
App.ActiveDocument.C62.Angle=360.00 
App.ActiveDocument.C62.Placement=Base.Placement(Base.Vector(-81.049689,-140.912762,493.914483),Base.Rotation(-0.001509,-0.763107,0.000000,0.646270))
App.ActiveDocument.addObject("Part::Cylinder","C63")
App.ActiveDocument.C63.Radius=0.750000
App.ActiveDocument.C63.Height=15.00
App.ActiveDocument.C63.Angle=360.00 
App.ActiveDocument.C63.Placement=Base.Placement(Base.Vector(-80.426859,-140.925487,491.048783),Base.Rotation(-0.002647,-0.793348,0.000000,0.608762))
App.ActiveDocument.addObject("Part::Cylinder","C64")
App.ActiveDocument.C64.Radius=0.750000
App.ActiveDocument.C64.Height=15.00
App.ActiveDocument.C64.Angle=360.00 
App.ActiveDocument.C64.Placement=Base.Placement(Base.Vector(-79.524238,-140.911517,488.215901),Base.Rotation(-0.001597,-0.820572,0.000000,0.571541))
App.ActiveDocument.addObject("Part::Cylinder","C65")
App.ActiveDocument.C65.Radius=0.750000
App.ActiveDocument.C65.Height=15.00
App.ActiveDocument.C65.Angle=360.00 
App.ActiveDocument.C65.Placement=Base.Placement(Base.Vector(-78.353648,-140.923075,485.437782),Base.Rotation(-0.002787,-0.844958,0.000000,0.534825))
App.ActiveDocument.addObject("Part::Cylinder","C66")
App.ActiveDocument.C66.Radius=0.750000
App.ActiveDocument.C66.Height=15.00
App.ActiveDocument.C66.Angle=360.00 
App.ActiveDocument.C66.Placement=Base.Placement(Base.Vector(-76.925165,-140.917675,482.721587),Base.Rotation(-0.002444,-0.866334,0.000000,0.499459))
App.ActiveDocument.addObject("Part::Cylinder","C67")
App.ActiveDocument.C67.Radius=0.750000
App.ActiveDocument.C67.Height=15.00
App.ActiveDocument.C67.Angle=360.00 
App.ActiveDocument.C67.Placement=Base.Placement(Base.Vector(-75.246220,-140.920876,480.061045),Base.Rotation(-0.002959,-0.884451,0.000000,0.466624))
App.ActiveDocument.addObject("Part::Cylinder","C68")
App.ActiveDocument.C68.Radius=0.750000
App.ActiveDocument.C68.Height=15.00
App.ActiveDocument.C68.Angle=360.00 
App.ActiveDocument.C68.Placement=Base.Placement(Base.Vector(-73.343169,-140.924129,477.478541),Base.Rotation(-0.003542,-0.900075,0.000000,0.435720))
App.ActiveDocument.addObject("Part::Cylinder","C69")
App.ActiveDocument.C69.Radius=0.750000
App.ActiveDocument.C69.Height=15.00
App.ActiveDocument.C69.Angle=360.00 
App.ActiveDocument.C69.Placement=Base.Placement(Base.Vector(-71.232303,-140.937483,474.976749),Base.Rotation(-0.005428,-0.913246,0.000000,0.407372))
App.ActiveDocument.addObject("Part::Cylinder","C70")
App.ActiveDocument.C70.Radius=0.750000
App.ActiveDocument.C70.Height=15.00
App.ActiveDocument.C70.Angle=360.00 
App.ActiveDocument.C70.Placement=Base.Placement(Base.Vector(-68.896061,-140.929084,472.521581),Base.Rotation(-0.004713,-0.924953,0.000000,0.380051))
App.ActiveDocument.addObject("Part::Cylinder","C71")
App.ActiveDocument.C71.Radius=0.750000
App.ActiveDocument.C71.Height=15.00
App.ActiveDocument.C71.Angle=360.00 
App.ActiveDocument.C71.Placement=Base.Placement(Base.Vector(-66.290677,-140.906605,470.069626),Base.Rotation(-0.001867,-0.933929,0.000000,0.357455))
App.ActiveDocument.addObject("Part::Cylinder","C72")
App.ActiveDocument.C72.Radius=0.750000
App.ActiveDocument.C72.Height=15.00
App.ActiveDocument.C72.Angle=360.00 
App.ActiveDocument.C72.Placement=Base.Placement(Base.Vector(-31.817105,-137.565838,548.591510),Base.Rotation(-0.031350,-0.040724,0.000000,0.998679))
App.ActiveDocument.addObject("Part::Cylinder","C73")
App.ActiveDocument.C73.Radius=0.750000
App.ActiveDocument.C73.Height=15.00
App.ActiveDocument.C73.Angle=360.00 
App.ActiveDocument.C73.Placement=Base.Placement(Base.Vector(-31.892802,-134.102859,548.265649),Base.Rotation(-0.061835,-0.036981,0.000000,0.997401))
App.ActiveDocument.addObject("Part::Cylinder","C74")
App.ActiveDocument.C74.Radius=0.750000
App.ActiveDocument.C74.Height=15.00
App.ActiveDocument.C74.Angle=360.00 
App.ActiveDocument.C74.Placement=Base.Placement(Base.Vector(-31.981055,-130.784569,547.736702),Base.Rotation(-0.095491,-0.032639,0.000000,0.994895))
App.ActiveDocument.addObject("Part::Cylinder","C75")
App.ActiveDocument.C75.Radius=0.750000
App.ActiveDocument.C75.Height=15.00
App.ActiveDocument.C75.Angle=360.00 
App.ActiveDocument.C75.Placement=Base.Placement(Base.Vector(-32.023508,-127.598074,546.990022),Base.Rotation(-0.130588,-0.030627,0.000000,0.990964))
App.ActiveDocument.addObject("Part::Cylinder","C76")
App.ActiveDocument.C76.Radius=0.750000
App.ActiveDocument.C76.Height=15.00
App.ActiveDocument.C76.Angle=360.00 
App.ActiveDocument.C76.Placement=Base.Placement(Base.Vector(-32.115900,-124.550285,546.037754),Base.Rotation(-0.170896,-0.026124,0.000000,0.984943))
App.ActiveDocument.addObject("Part::Cylinder","C77")
App.ActiveDocument.C77.Radius=0.750000
App.ActiveDocument.C77.Height=15.00
App.ActiveDocument.C77.Angle=360.00 
App.ActiveDocument.C77.Placement=Base.Placement(Base.Vector(-32.222250,-121.583575,544.836007),Base.Rotation(-0.214854,-0.020906,0.000000,0.976422))
App.ActiveDocument.addObject("Part::Cylinder","C78")
App.ActiveDocument.C78.Radius=0.750000
App.ActiveDocument.C78.Height=15.00
App.ActiveDocument.C78.Angle=360.00 
App.ActiveDocument.C78.Placement=Base.Placement(Base.Vector(-32.298004,-118.826702,543.413947),Base.Rotation(-0.254825,-0.017195,0.000000,0.966834))
App.ActiveDocument.addObject("Part::Cylinder","C79")
App.ActiveDocument.C79.Radius=0.750000
App.ActiveDocument.C79.Height=15.00
App.ActiveDocument.C79.Angle=360.00 
App.ActiveDocument.C79.Placement=Base.Placement(Base.Vector(-32.343247,-116.310269,541.813031),Base.Rotation(-0.302033,-0.015068,0.000000,0.953178))
App.ActiveDocument.addObject("Part::Cylinder","C80")
App.ActiveDocument.C80.Radius=0.750000
App.ActiveDocument.C80.Height=15.00
App.ActiveDocument.C80.Angle=360.00 
App.ActiveDocument.C80.Placement=Base.Placement(Base.Vector(-32.393544,-113.922991,539.961383),Base.Rotation(-0.347525,-0.012637,0.000000,0.937585))
App.ActiveDocument.addObject("Part::Cylinder","C81")
App.ActiveDocument.C81.Radius=0.750000
App.ActiveDocument.C81.Height=15.00
App.ActiveDocument.C81.Angle=360.00 
App.ActiveDocument.C81.Placement=Base.Placement(Base.Vector(-32.410904,-111.637827,537.796928),Base.Rotation(-0.393026,-0.011942,0.000000,0.919450))
App.ActiveDocument.addObject("Part::Cylinder","C82")
App.ActiveDocument.C82.Radius=0.750000
App.ActiveDocument.C82.Height=15.00
App.ActiveDocument.C82.Angle=360.00 
App.ActiveDocument.C82.Placement=Base.Placement(Base.Vector(-32.449895,-109.616551,535.465494),Base.Rotation(-0.435756,-0.010034,0.000000,0.900009))
App.ActiveDocument.addObject("Part::Cylinder","C83")
App.ActiveDocument.C83.Radius=0.750000
App.ActiveDocument.C83.Height=15.00
App.ActiveDocument.C83.Angle=360.00 
App.ActiveDocument.C83.Placement=Base.Placement(Base.Vector(-32.448238,-107.830616,532.975669),Base.Rotation(-0.476449,-0.010366,0.000000,0.879141))
App.ActiveDocument.addObject("Part::Cylinder","C84")
App.ActiveDocument.C84.Radius=0.750000
App.ActiveDocument.C84.Height=15.00
App.ActiveDocument.C84.Angle=360.00 
App.ActiveDocument.C84.Placement=Base.Placement(Base.Vector(-32.443271,-106.195129,530.197054),Base.Rotation(-0.515020,-0.010922,0.000000,0.857109))
App.ActiveDocument.addObject("Part::Cylinder","C85")
App.ActiveDocument.C85.Radius=0.750000
App.ActiveDocument.C85.Height=15.00
App.ActiveDocument.C85.Angle=360.00 
App.ActiveDocument.C85.Placement=Base.Placement(Base.Vector(-32.439030,-104.815083,527.315724),Base.Rotation(-0.550236,-0.011466,0.000000,0.834931))
App.ActiveDocument.addObject("Part::Cylinder","C86")
App.ActiveDocument.C86.Radius=0.750000
App.ActiveDocument.C86.Height=15.00
App.ActiveDocument.C86.Angle=360.00 
App.ActiveDocument.C86.Placement=Base.Placement(Base.Vector(-32.455836,-103.651417,524.280978),Base.Rotation(-0.582271,-0.010743,0.000000,0.812924))
App.ActiveDocument.addObject("Part::Cylinder","C87")
App.ActiveDocument.C87.Radius=0.750000
App.ActiveDocument.C87.Height=15.00
App.ActiveDocument.C87.Angle=360.00 
App.ActiveDocument.C87.Placement=Base.Placement(Base.Vector(-32.508593,-102.698900,521.080940),Base.Rotation(-0.613242,-0.007717,0.000000,0.789857))
App.ActiveDocument.addObject("Part::Cylinder","C88")
App.ActiveDocument.C88.Radius=0.750000
App.ActiveDocument.C88.Height=15.00
App.ActiveDocument.C88.Angle=360.00 
App.ActiveDocument.C88.Placement=Base.Placement(Base.Vector(-32.605783,-101.994522,517.851180),Base.Rotation(-0.641252,-0.001611,0.000000,0.767329))
App.ActiveDocument.addObject("Part::Cylinder","C89")
App.ActiveDocument.C89.Radius=0.750000
App.ActiveDocument.C89.Height=15.00
App.ActiveDocument.C89.Angle=360.00 
App.ActiveDocument.C89.Placement=Base.Placement(Base.Vector(-32.725049,-101.515725,514.585032),Base.Rotation(-0.666558,0.006342,0.000000,0.745426))
App.ActiveDocument.addObject("Part::Cylinder","C90")
App.ActiveDocument.C90.Radius=0.750000
App.ActiveDocument.C90.Height=15.00
App.ActiveDocument.C90.Angle=360.00 
App.ActiveDocument.C90.Placement=Base.Placement(Base.Vector(-32.847438,-101.249582,511.231476),Base.Rotation(-0.690297,0.014995,0.000000,0.723371))
App.ActiveDocument.addObject("Part::Cylinder","C91")
App.ActiveDocument.C91.Radius=0.750000
App.ActiveDocument.C91.Height=15.00
App.ActiveDocument.C91.Angle=360.00 
App.ActiveDocument.C91.Placement=Base.Placement(Base.Vector(-32.957801,-101.194299,507.960353),Base.Rotation(-0.710843,0.023280,0.000000,0.702966))
App.ActiveDocument.addObject("Part::Cylinder","C92")
App.ActiveDocument.C92.Radius=0.750000
App.ActiveDocument.C92.Height=15.00
App.ActiveDocument.C92.Angle=360.00 
App.ActiveDocument.C92.Placement=Base.Placement(Base.Vector(-33.069797,-101.342303,504.428941),Base.Rotation(-0.731816,0.032266,0.000000,0.680738))
App.ActiveDocument.addObject("Part::Cylinder","C93")
App.ActiveDocument.C93.Radius=0.750000
App.ActiveDocument.C93.Height=15.00
App.ActiveDocument.C93.Angle=360.00 
App.ActiveDocument.C93.Placement=Base.Placement(Base.Vector(-33.156105,-101.679544,500.992297),Base.Rotation(-0.749976,0.039802,0.000000,0.660266))
App.ActiveDocument.addObject("Part::Cylinder","C94")
App.ActiveDocument.C94.Radius=0.750000
App.ActiveDocument.C94.Height=15.00
App.ActiveDocument.C94.Angle=360.00 
App.ActiveDocument.C94.Placement=Base.Placement(Base.Vector(-33.255331,-102.237975,497.461667),Base.Rotation(-0.767293,0.048858,0.000000,0.639433))
App.ActiveDocument.addObject("Part::Cylinder","C95")
App.ActiveDocument.C95.Radius=0.750000
App.ActiveDocument.C95.Height=15.00
App.ActiveDocument.C95.Angle=360.00 
App.ActiveDocument.C95.Placement=Base.Placement(Base.Vector(-33.327860,-102.948734,494.082363),Base.Rotation(-0.783589,0.056355,0.000000,0.618719))
App.ActiveDocument.addObject("Part::Cylinder","C96")
App.ActiveDocument.C96.Radius=0.750000
App.ActiveDocument.C96.Height=15.00
App.ActiveDocument.C96.Angle=360.00 
App.ActiveDocument.C96.Placement=Base.Placement(Base.Vector(-33.393386,-103.838631,490.767395),Base.Rotation(-0.799153,0.063815,0.000000,0.597730))
App.ActiveDocument.addObject("Part::Cylinder","C97")
App.ActiveDocument.C97.Radius=0.750000
App.ActiveDocument.C97.Height=15.00
App.ActiveDocument.C97.Angle=360.00 
App.ActiveDocument.C97.Placement=Base.Placement(Base.Vector(-33.498752,-104.909394,487.458340),Base.Rotation(-0.813914,0.075359,0.000000,0.576077))
App.ActiveDocument.addObject("Part::Cylinder","C98")
App.ActiveDocument.C98.Radius=0.750000
App.ActiveDocument.C98.Height=15.00
App.ActiveDocument.C98.Angle=360.00 
App.ActiveDocument.C98.Placement=Base.Placement(Base.Vector(-33.591618,-106.138199,484.255386),Base.Rotation(-0.827213,0.086559,0.000000,0.555182))
App.ActiveDocument.addObject("Part::Cylinder","C99")
App.ActiveDocument.C99.Radius=0.750000
App.ActiveDocument.C99.Height=15.00
App.ActiveDocument.C99.Angle=360.00 
App.ActiveDocument.C99.Placement=Base.Placement(Base.Vector(-33.668362,-107.591203,480.999002),Base.Rotation(-0.841685,0.097717,0.000000,0.531053))
App.ActiveDocument.addObject("Part::Cylinder","C100")
App.ActiveDocument.C100.Radius=0.750000
App.ActiveDocument.C100.Height=15.00
App.ActiveDocument.C100.Angle=360.00 
App.ActiveDocument.C100.Placement=Base.Placement(Base.Vector(-33.763289,-109.191757,477.934078),Base.Rotation(-0.853348,0.111200,0.000000,0.509345))
App.ActiveDocument.addObject("Part::Cylinder","C101")
App.ActiveDocument.C101.Radius=0.750000
App.ActiveDocument.C101.Height=15.00
App.ActiveDocument.C101.Angle=360.00 
App.ActiveDocument.C101.Placement=Base.Placement(Base.Vector(-33.847850,-110.872699,475.072937),Base.Rotation(-0.866642,0.126088,0.000000,0.482736))
App.ActiveDocument.addObject("Part::Cylinder","C102")
App.ActiveDocument.C102.Radius=0.750000
App.ActiveDocument.C102.Height=15.00
App.ActiveDocument.C102.Angle=360.00 
App.ActiveDocument.C102.Placement=Base.Placement(Base.Vector(-33.939420,-112.689922,472.380267),Base.Rotation(-0.878187,0.143425,0.000000,0.456307))
App.ActiveDocument.addObject("Part::Cylinder","C103")
App.ActiveDocument.C103.Radius=0.750000
App.ActiveDocument.C103.Height=15.00
App.ActiveDocument.C103.Angle=360.00 
App.ActiveDocument.C103.Placement=Base.Placement(Base.Vector(-34.040065,-114.702573,469.788908),Base.Rotation(-0.889054,0.165048,0.000000,0.427016))
App.ActiveDocument.addObject("Part::Cylinder","C104")
App.ActiveDocument.C104.Radius=0.750000
App.ActiveDocument.C104.Height=15.00
App.ActiveDocument.C104.Angle=360.00 
App.ActiveDocument.C104.Placement=Base.Placement(Base.Vector(-31.807668,-144.190103,548.614802),Base.Rotation(0.027948,-0.041193,0.000000,0.998760))
App.ActiveDocument.addObject("Part::Cylinder","C105")
App.ActiveDocument.C105.Radius=0.750000
App.ActiveDocument.C105.Height=15.00
App.ActiveDocument.C105.Angle=360.00 
App.ActiveDocument.C105.Placement=Base.Placement(Base.Vector(-31.890592,-147.602454,548.317206),Base.Rotation(0.057892,-0.037083,0.000000,0.997634))
App.ActiveDocument.addObject("Part::Cylinder","C106")
App.ActiveDocument.C106.Radius=0.750000
App.ActiveDocument.C106.Height=15.00
App.ActiveDocument.C106.Angle=360.00 
App.ActiveDocument.C106.Placement=Base.Placement(Base.Vector(-31.969856,-150.956514,547.812579),Base.Rotation(0.091143,-0.033189,0.000000,0.995285))
App.ActiveDocument.addObject("Part::Cylinder","C107")
App.ActiveDocument.C107.Radius=0.750000
App.ActiveDocument.C107.Height=15.00
App.ActiveDocument.C107.Angle=360.00 
App.ActiveDocument.C107.Placement=Base.Placement(Base.Vector(-32.005665,-154.177455,547.090123),Base.Rotation(0.126210,-0.031510,0.000000,0.991503))
App.ActiveDocument.addObject("Part::Cylinder","C108")
App.ActiveDocument.C108.Radius=0.750000
App.ActiveDocument.C108.Height=15.00
App.ActiveDocument.C108.Angle=360.00 
App.ActiveDocument.C108.Placement=Base.Placement(Base.Vector(-32.082073,-157.188239,546.177810),Base.Rotation(0.164200,-0.027810,0.000000,0.986035))
App.ActiveDocument.addObject("Part::Cylinder","C109")
App.ActiveDocument.C109.Radius=0.750000
App.ActiveDocument.C109.Height=15.00
App.ActiveDocument.C109.Angle=360.00 
App.ActiveDocument.C109.Placement=Base.Placement(Base.Vector(-32.186012,-160.128380,545.026168),Base.Rotation(0.207274,-0.022724,0.000000,0.978019))
App.ActiveDocument.addObject("Part::Cylinder","C110")
App.ActiveDocument.C110.Radius=0.750000
App.ActiveDocument.C110.Height=15.00
App.ActiveDocument.C110.Angle=360.00 
App.ActiveDocument.C110.Placement=Base.Placement(Base.Vector(-32.279084,-162.948987,543.617158),Base.Rotation(0.249495,-0.018148,0.000000,0.968206))
App.ActiveDocument.addObject("Part::Cylinder","C111")
App.ActiveDocument.C111.Radius=0.750000
App.ActiveDocument.C111.Height=15.00
App.ActiveDocument.C111.Angle=360.00 
App.ActiveDocument.C111.Placement=Base.Placement(Base.Vector(-32.324232,-165.537564,542.010656),Base.Rotation(0.297750,-0.016043,0.000000,0.954509))
App.ActiveDocument.addObject("Part::Cylinder","C112")
App.ActiveDocument.C112.Radius=0.750000
App.ActiveDocument.C112.Height=15.00
App.ActiveDocument.C112.Angle=360.00 
App.ActiveDocument.C112.Placement=Base.Placement(Base.Vector(-32.399987,-167.913206,540.213306),Base.Rotation(0.341185,-0.012263,0.000000,0.939916))
App.ActiveDocument.addObject("Part::Cylinder","C113")
App.ActiveDocument.C113.Radius=0.750000
App.ActiveDocument.C113.Height=15.00
App.ActiveDocument.C113.Angle=360.00 
App.ActiveDocument.C113.Placement=Base.Placement(Base.Vector(-32.411163,-170.187706,538.109528),Base.Rotation(0.386194,-0.011890,0.000000,0.922341))
App.ActiveDocument.addObject("Part::Cylinder","C114")
App.ActiveDocument.C114.Radius=0.750000
App.ActiveDocument.C114.Height=15.00
App.ActiveDocument.C114.Angle=360.00 
App.ActiveDocument.C114.Placement=Base.Placement(Base.Vector(-32.443022,-172.155023,535.915094),Base.Rotation(0.428533,-0.010376,0.000000,0.903466))
App.ActiveDocument.addObject("Part::Cylinder","C115")
App.ActiveDocument.C115.Radius=0.750000
App.ActiveDocument.C115.Height=15.00
App.ActiveDocument.C115.Angle=360.00 
App.ActiveDocument.C115.Placement=Base.Placement(Base.Vector(-32.455754,-173.980100,533.460961),Base.Rotation(0.469559,-0.009897,0.000000,0.882846))
App.ActiveDocument.addObject("Part::Cylinder","C116")
App.ActiveDocument.C116.Radius=0.750000
App.ActiveDocument.C116.Height=15.00
App.ActiveDocument.C116.Angle=360.00 
App.ActiveDocument.C116.Placement=Base.Placement(Base.Vector(-32.453490,-175.592554,530.828710),Base.Rotation(0.506321,-0.010264,0.000000,0.862284))
App.ActiveDocument.addObject("Part::Cylinder","C117")
App.ActiveDocument.C117.Radius=0.750000
App.ActiveDocument.C117.Height=15.00
App.ActiveDocument.C117.Angle=360.00 
App.ActiveDocument.C117.Placement=Base.Placement(Base.Vector(-32.443455,-177.025886,527.973952),Base.Rotation(0.542601,-0.011135,0.000000,0.839917))
App.ActiveDocument.addObject("Part::Cylinder","C118")
App.ActiveDocument.C118.Radius=0.750000
App.ActiveDocument.C118.Height=15.00
App.ActiveDocument.C118.Angle=360.00 
App.ActiveDocument.C118.Placement=Base.Placement(Base.Vector(-32.443285,-178.233658,524.986319),Base.Rotation(0.574086,-0.011434,0.000000,0.818715))
App.ActiveDocument.addObject("Part::Cylinder","C119")
App.ActiveDocument.C119.Radius=0.750000
App.ActiveDocument.C119.Height=15.00
App.ActiveDocument.C119.Angle=360.00 
App.ActiveDocument.C119.Placement=Base.Placement(Base.Vector(-32.498080,-179.219114,521.882800),Base.Rotation(0.605092,-0.008317,0.000000,0.796112))
App.ActiveDocument.addObject("Part::Cylinder","C120")
App.ActiveDocument.C120.Radius=0.750000
App.ActiveDocument.C120.Height=15.00
App.ActiveDocument.C120.Angle=360.00 
App.ActiveDocument.C120.Placement=Base.Placement(Base.Vector(-32.562353,-179.969155,518.734010),Base.Rotation(0.633043,-0.004402,0.000000,0.774104))
App.ActiveDocument.addObject("Part::Cylinder","C121")
App.ActiveDocument.C121.Radius=0.750000
App.ActiveDocument.C121.Height=15.00
App.ActiveDocument.C121.Angle=360.00 
App.ActiveDocument.C121.Placement=Base.Placement(Base.Vector(-32.682805,-180.497690,515.554280),Base.Rotation(0.658457,0.003475,0.000000,0.752611))
App.ActiveDocument.addObject("Part::Cylinder","C122")
App.ActiveDocument.C122.Radius=0.750000
App.ActiveDocument.C122.Height=15.00
App.ActiveDocument.C122.Angle=360.00 
App.ActiveDocument.C122.Placement=Base.Placement(Base.Vector(-32.808113,-180.834005,512.124223),Base.Rotation(0.684368,0.012181,0.000000,0.729035))
App.ActiveDocument.addObject("Part::Cylinder","C123")
App.ActiveDocument.C123.Radius=0.750000
App.ActiveDocument.C123.Height=15.00
App.ActiveDocument.C123.Angle=360.00 
App.ActiveDocument.C123.Placement=Base.Placement(Base.Vector(-32.930256,-180.948617,508.713692),Base.Rotation(0.706324,0.021182,0.000000,0.707572))
App.ActiveDocument.addObject("Part::Cylinder","C124")
App.ActiveDocument.C124.Radius=0.750000
App.ActiveDocument.C124.Height=15.00
App.ActiveDocument.C124.Angle=360.00 
App.ActiveDocument.C124.Placement=Base.Placement(Base.Vector(-33.052767,-180.851601,505.302657),Base.Rotation(0.726904,0.030775,0.000000,0.686049))
App.ActiveDocument.addObject("Part::Cylinder","C125")
App.ActiveDocument.C125.Radius=0.750000
App.ActiveDocument.C125.Height=15.00
App.ActiveDocument.C125.Angle=360.00 
App.ActiveDocument.C125.Placement=Base.Placement(Base.Vector(-33.137191,-180.557144,501.887140),Base.Rotation(0.745587,0.038079,0.000000,0.665319))
App.ActiveDocument.addObject("Part::Cylinder","C126")
App.ActiveDocument.C126.Radius=0.750000
App.ActiveDocument.C126.Height=15.00
App.ActiveDocument.C126.Angle=360.00 
App.ActiveDocument.C126.Placement=Base.Placement(Base.Vector(-33.220030,-180.089131,498.562908),Base.Rotation(0.761799,0.045614,0.000000,0.646205))
App.ActiveDocument.addObject("Part::Cylinder","C127")
App.ActiveDocument.C127.Radius=0.750000
App.ActiveDocument.C127.Height=15.00
App.ActiveDocument.C127.Angle=360.00 
App.ActiveDocument.C127.Placement=Base.Placement(Base.Vector(-33.295017,-179.434358,495.147629),Base.Rotation(0.778574,0.053136,0.000000,0.625299))
App.ActiveDocument.addObject("Part::Cylinder","C128")
App.ActiveDocument.C128.Radius=0.750000
App.ActiveDocument.C128.Height=15.00
App.ActiveDocument.C128.Angle=360.00 
App.ActiveDocument.C128.Placement=Base.Placement(Base.Vector(-33.367719,-178.593023,491.823765),Base.Rotation(0.794487,0.061007,0.000000,0.604210))
App.ActiveDocument.addObject("Part::Cylinder","C129")
App.ActiveDocument.C129.Radius=0.750000
App.ActiveDocument.C129.Height=15.00
App.ActiveDocument.C129.Angle=360.00 
App.ActiveDocument.C129.Placement=Base.Placement(Base.Vector(-33.453598,-177.590130,488.527112),Base.Rotation(0.807529,0.070275,0.000000,0.585626))
App.ActiveDocument.addObject("Part::Cylinder","C130")
App.ActiveDocument.C130.Radius=0.750000
App.ActiveDocument.C130.Height=15.00
App.ActiveDocument.C130.Angle=360.00 
App.ActiveDocument.C130.Placement=Base.Placement(Base.Vector(-33.583914,-176.443551,485.397286),Base.Rotation(0.822510,0.084763,0.000000,0.562399))
App.ActiveDocument.addObject("Part::Cylinder","C131")
App.ActiveDocument.C131.Radius=0.750000
App.ActiveDocument.C131.Height=15.00
App.ActiveDocument.C131.Angle=360.00 
App.ActiveDocument.C131.Placement=Base.Placement(Base.Vector(-33.641913,-175.093732,482.198092),Base.Rotation(0.836026,0.093535,0.000000,0.540658))
App.ActiveDocument.addObject("Part::Cylinder","C132")
App.ActiveDocument.C132.Radius=0.750000
App.ActiveDocument.C132.Height=15.00
App.ActiveDocument.C132.Angle=360.00 
App.ActiveDocument.C132.Placement=Base.Placement(Base.Vector(-33.726123,-173.648536,479.200672),Base.Rotation(0.848813,0.105753,0.000000,0.518009))
App.ActiveDocument.addObject("Part::Cylinder","C133")
App.ActiveDocument.C133.Radius=0.750000
App.ActiveDocument.C133.Height=15.00
App.ActiveDocument.C133.Angle=360.00 
App.ActiveDocument.C133.Placement=Base.Placement(Base.Vector(-33.812662,-171.965518,476.249063),Base.Rotation(0.861561,0.119819,0.000000,0.493311))
App.ActiveDocument.addObject("Part::Cylinder","C134")
App.ActiveDocument.C134.Radius=0.750000
App.ActiveDocument.C134.Height=15.00
App.ActiveDocument.C134.Angle=360.00 
App.ActiveDocument.C134.Placement=Base.Placement(Base.Vector(-33.902258,-170.166379,473.434636),Base.Rotation(0.873766,0.136195,0.000000,0.466888))
App.ActiveDocument.addObject("Part::Cylinder","C135")
App.ActiveDocument.C135.Radius=0.750000
App.ActiveDocument.C135.Height=15.00
App.ActiveDocument.C135.Angle=360.00 
App.ActiveDocument.C135.Placement=Base.Placement(Base.Vector(-33.993520,-168.258661,470.796749),Base.Rotation(0.884818,0.155114,0.000000,0.439359))
App.ActiveDocument.addObject("Part::Cylinder","C136")
App.ActiveDocument.C136.Radius=0.750000
App.ActiveDocument.C136.Height=15.00
App.ActiveDocument.C136.Angle=360.00 
App.ActiveDocument.C136.Placement=Base.Placement(Base.Vector(-34.120644,-166.151986,468.286750),Base.Rotation(0.895036,0.183238,0.000000,0.406613))
App.ActiveDocument.addObject("Part::Cylinder","C137")
App.ActiveDocument.C137.Radius=0.750000
App.ActiveDocument.C137.Height=15.00
App.ActiveDocument.C137.Angle=360.00 
App.ActiveDocument.C137.Placement=Base.Placement(Base.Vector(-28.582528,-137.571759,548.727472),Base.Rotation(-0.035616,-0.004972,0.000000,0.999353))
App.ActiveDocument.addObject("Part::Cylinder","C138")
App.ActiveDocument.C138.Radius=0.750000
App.ActiveDocument.C138.Height=15.00
App.ActiveDocument.C138.Angle=360.00 
App.ActiveDocument.C138.Placement=Base.Placement(Base.Vector(-28.630527,-134.187146,548.383699),Base.Rotation(-0.065717,-0.000901,0.000000,0.997838))
App.ActiveDocument.addObject("Part::Cylinder","C139")
App.ActiveDocument.C139.Radius=0.750000
App.ActiveDocument.C139.Height=15.00
App.ActiveDocument.C139.Angle=360.00 
App.ActiveDocument.C139.Placement=Base.Placement(Base.Vector(-28.720636,-130.880845,547.836919),Base.Rotation(-0.102172,0.002971,0.000000,0.994762))
App.ActiveDocument.addObject("Part::Cylinder","C140")
App.ActiveDocument.C140.Radius=0.750000
App.ActiveDocument.C140.Height=15.00
App.ActiveDocument.C140.Angle=360.00 
App.ActiveDocument.C140.Placement=Base.Placement(Base.Vector(-28.748166,-127.622246,547.060723),Base.Rotation(-0.133968,0.005853,0.000000,0.990968))
App.ActiveDocument.addObject("Part::Cylinder","C141")
App.ActiveDocument.C141.Radius=0.750000
App.ActiveDocument.C141.Height=15.00
App.ActiveDocument.C141.Angle=360.00 
App.ActiveDocument.C141.Placement=Base.Placement(Base.Vector(-28.867229,-124.670193,546.121076),Base.Rotation(-0.172201,0.007305,0.000000,0.985035))
App.ActiveDocument.addObject("Part::Cylinder","C142")
App.ActiveDocument.C142.Radius=0.750000
App.ActiveDocument.C142.Height=15.00
App.ActiveDocument.C142.Angle=360.00 
App.ActiveDocument.C142.Placement=Base.Placement(Base.Vector(-28.835197,-121.789949,544.946538),Base.Rotation(-0.212541,0.009672,0.000000,0.977104))
App.ActiveDocument.addObject("Part::Cylinder","C143")
App.ActiveDocument.C143.Radius=0.750000
App.ActiveDocument.C143.Height=15.00
App.ActiveDocument.C143.Angle=360.00 
App.ActiveDocument.C143.Placement=Base.Placement(Base.Vector(-28.852245,-119.061426,543.548930),Base.Rotation(-0.255940,0.011392,0.000000,0.966625))
App.ActiveDocument.addObject("Part::Cylinder","C144")
App.ActiveDocument.C144.Radius=0.750000
App.ActiveDocument.C144.Height=15.00
App.ActiveDocument.C144.Angle=360.00 
App.ActiveDocument.C144.Placement=Base.Placement(Base.Vector(-28.954234,-116.497463,541.935406),Base.Rotation(-0.299241,0.009813,0.000000,0.954127))
App.ActiveDocument.addObject("Part::Cylinder","C145")
App.ActiveDocument.C145.Radius=0.750000
App.ActiveDocument.C145.Height=15.00
App.ActiveDocument.C145.Angle=360.00 
App.ActiveDocument.C145.Placement=Base.Placement(Base.Vector(-28.837326,-114.068408,540.065957),Base.Rotation(-0.343334,0.008759,0.000000,0.939173))
App.ActiveDocument.addObject("Part::Cylinder","C146")
App.ActiveDocument.C146.Radius=0.750000
App.ActiveDocument.C146.Height=15.00
App.ActiveDocument.C146.Angle=360.00 
App.ActiveDocument.C146.Placement=Base.Placement(Base.Vector(-28.871962,-111.918046,538.068448),Base.Rotation(-0.386723,0.006504,0.000000,0.922173))
App.ActiveDocument.addObject("Part::Cylinder","C147")
App.ActiveDocument.C147.Radius=0.750000
App.ActiveDocument.C147.Height=15.00
App.ActiveDocument.C147.Angle=360.00 
App.ActiveDocument.C147.Placement=Base.Placement(Base.Vector(-28.853642,-109.897402,535.811752),Base.Rotation(-0.429649,0.004711,0.000000,0.902984))
App.ActiveDocument.addObject("Part::Cylinder","C148")
App.ActiveDocument.C148.Radius=0.750000
App.ActiveDocument.C148.Height=15.00
App.ActiveDocument.C148.Angle=360.00 
App.ActiveDocument.C148.Placement=Base.Placement(Base.Vector(-28.733538,-108.104683,533.397321),Base.Rotation(-0.467917,0.004903,0.000000,0.883759))
App.ActiveDocument.addObject("Part::Cylinder","C149")
App.ActiveDocument.C149.Radius=0.750000
App.ActiveDocument.C149.Height=15.00
App.ActiveDocument.C149.Angle=360.00 
App.ActiveDocument.C149.Placement=Base.Placement(Base.Vector(-28.888201,-106.511148,530.802063),Base.Rotation(-0.508328,0.004692,0.000000,0.861151))
App.ActiveDocument.addObject("Part::Cylinder","C150")
App.ActiveDocument.C150.Radius=0.750000
App.ActiveDocument.C150.Height=15.00
App.ActiveDocument.C150.Angle=360.00 
App.ActiveDocument.C150.Placement=Base.Placement(Base.Vector(-28.943472,-105.088126,527.954459),Base.Rotation(-0.544152,0.009378,0.000000,0.838935))
App.ActiveDocument.addObject("Part::Cylinder","C151")
App.ActiveDocument.C151.Radius=0.750000
App.ActiveDocument.C151.Height=15.00
App.ActiveDocument.C151.Angle=360.00 
App.ActiveDocument.C151.Placement=Base.Placement(Base.Vector(-29.004608,-103.924017,525.026481),Base.Rotation(-0.577701,0.016051,0.000000,0.816091))
App.ActiveDocument.addObject("Part::Cylinder","C152")
App.ActiveDocument.C152.Radius=0.750000
App.ActiveDocument.C152.Height=15.00
App.ActiveDocument.C152.Angle=360.00 
App.ActiveDocument.C152.Placement=Base.Placement(Base.Vector(-29.250002,-102.972956,521.959243),Base.Rotation(-0.608874,0.021666,0.000000,0.792971))
App.ActiveDocument.addObject("Part::Cylinder","C153")
App.ActiveDocument.C153.Radius=0.750000
App.ActiveDocument.C153.Height=15.00
App.ActiveDocument.C153.Angle=360.00 
App.ActiveDocument.C153.Placement=Base.Placement(Base.Vector(-29.287336,-102.252200,518.778386),Base.Rotation(-0.637760,0.031994,0.000000,0.769570))
App.ActiveDocument.addObject("Part::Cylinder","C154")
App.ActiveDocument.C154.Radius=0.750000
App.ActiveDocument.C154.Height=15.00
App.ActiveDocument.C154.Angle=360.00 
App.ActiveDocument.C154.Placement=Base.Placement(Base.Vector(-29.456612,-101.750993,515.538459),Base.Rotation(-0.663834,0.042474,0.000000,0.746673))
App.ActiveDocument.addObject("Part::Cylinder","C155")
App.ActiveDocument.C155.Radius=0.750000
App.ActiveDocument.C155.Height=15.00
App.ActiveDocument.C155.Angle=360.00 
App.ActiveDocument.C155.Placement=Base.Placement(Base.Vector(-29.556828,-101.459974,512.164432),Base.Rotation(-0.686644,0.049122,0.000000,0.725332))
App.ActiveDocument.addObject("Part::Cylinder","C156")
App.ActiveDocument.C156.Radius=0.750000
App.ActiveDocument.C156.Height=15.00
App.ActiveDocument.C156.Angle=360.00 
App.ActiveDocument.C156.Placement=Base.Placement(Base.Vector(-29.631404,-101.384115,508.779747),Base.Rotation(-0.708600,0.057630,0.000000,0.703253))
App.ActiveDocument.addObject("Part::Cylinder","C157")
App.ActiveDocument.C157.Radius=0.750000
App.ActiveDocument.C157.Height=15.00
App.ActiveDocument.C157.Angle=360.00 
App.ActiveDocument.C157.Placement=Base.Placement(Base.Vector(-29.692905,-101.513107,505.341433),Base.Rotation(-0.727346,0.067016,0.000000,0.682991))
App.ActiveDocument.addObject("Part::Cylinder","C158")
App.ActiveDocument.C158.Radius=0.750000
App.ActiveDocument.C158.Height=15.00
App.ActiveDocument.C158.Angle=360.00 
App.ActiveDocument.C158.Placement=Base.Placement(Base.Vector(-29.823833,-101.829445,501.915758),Base.Rotation(-0.745615,0.073065,0.000000,0.662360))
App.ActiveDocument.addObject("Part::Cylinder","C159")
App.ActiveDocument.C159.Radius=0.750000
App.ActiveDocument.C159.Height=15.00
App.ActiveDocument.C159.Angle=360.00 
App.ActiveDocument.C159.Placement=Base.Placement(Base.Vector(-29.926210,-102.330074,498.542853),Base.Rotation(-0.762148,0.081969,0.000000,0.642193))
App.ActiveDocument.addObject("Part::Cylinder","C160")
App.ActiveDocument.C160.Radius=0.750000
App.ActiveDocument.C160.Height=15.00
App.ActiveDocument.C160.Angle=360.00 
App.ActiveDocument.C160.Placement=Base.Placement(Base.Vector(-29.983733,-103.020525,495.167472),Base.Rotation(-0.777970,0.091676,0.000000,0.621577))
App.ActiveDocument.addObject("Part::Cylinder","C161")
App.ActiveDocument.C161.Radius=0.750000
App.ActiveDocument.C161.Height=15.00
App.ActiveDocument.C161.Angle=360.00 
App.ActiveDocument.C161.Placement=Base.Placement(Base.Vector(-30.124169,-103.885841,491.809533),Base.Rotation(-0.792712,0.099838,0.000000,0.601366))
App.ActiveDocument.addObject("Part::Cylinder","C162")
App.ActiveDocument.C162.Radius=0.750000
App.ActiveDocument.C162.Height=15.00
App.ActiveDocument.C162.Angle=360.00 
App.ActiveDocument.C162.Placement=Base.Placement(Base.Vector(-30.198095,-104.923007,488.540071),Base.Rotation(-0.806352,0.109432,0.000000,0.581224))
App.ActiveDocument.addObject("Part::Cylinder","C163")
App.ActiveDocument.C163.Radius=0.750000
App.ActiveDocument.C163.Height=15.00
App.ActiveDocument.C163.Angle=360.00 
App.ActiveDocument.C163.Placement=Base.Placement(Base.Vector(-30.164168,-106.168997,485.277477),Base.Rotation(-0.820513,0.128470,0.000000,0.557004))
App.ActiveDocument.addObject("Part::Cylinder","C164")
App.ActiveDocument.C164.Radius=0.750000
App.ActiveDocument.C164.Height=15.00
App.ActiveDocument.C164.Angle=360.00 
App.ActiveDocument.C164.Placement=Base.Placement(Base.Vector(-30.329830,-107.576614,482.057526),Base.Rotation(-0.833503,0.139780,0.000000,0.534541))
App.ActiveDocument.addObject("Part::Cylinder","C165")
App.ActiveDocument.C165.Radius=0.750000
App.ActiveDocument.C165.Height=15.00
App.ActiveDocument.C165.Angle=360.00 
App.ActiveDocument.C165.Placement=Base.Placement(Base.Vector(-30.489340,-109.118205,479.003802),Base.Rotation(-0.845210,0.152321,0.000000,0.512268))
App.ActiveDocument.addObject("Part::Cylinder","C166")
App.ActiveDocument.C166.Radius=0.750000
App.ActiveDocument.C166.Height=15.00
App.ActiveDocument.C166.Angle=360.00 
App.ActiveDocument.C166.Placement=Base.Placement(Base.Vector(-30.501004,-110.812732,476.121953),Base.Rotation(-0.855341,0.174506,0.000000,0.487790))
App.ActiveDocument.addObject("Part::Cylinder","C167")
App.ActiveDocument.C167.Radius=0.750000
App.ActiveDocument.C167.Height=15.00
App.ActiveDocument.C167.Angle=360.00 
App.ActiveDocument.C167.Placement=Base.Placement(Base.Vector(-30.569826,-112.664256,473.355998),Base.Rotation(-0.866038,0.194459,0.000000,0.460612))
App.ActiveDocument.addObject("Part::Cylinder","C168")
App.ActiveDocument.C168.Radius=0.750000
App.ActiveDocument.C168.Height=15.00
App.ActiveDocument.C168.Angle=360.00 
App.ActiveDocument.C168.Placement=Base.Placement(Base.Vector(-30.730821,-114.630951,470.769110),Base.Rotation(-0.874347,0.223479,0.000000,0.430784))
App.ActiveDocument.addObject("Part::Cylinder","C169")
App.ActiveDocument.C169.Radius=0.750000
App.ActiveDocument.C169.Height=15.00
App.ActiveDocument.C169.Angle=360.00 
App.ActiveDocument.C169.Placement=Base.Placement(Base.Vector(-25.211075,-137.587305,548.648359),Base.Rotation(-0.037820,0.027500,0.000000,0.998906))
App.ActiveDocument.addObject("Part::Cylinder","C170")
App.ActiveDocument.C170.Radius=0.750000
App.ActiveDocument.C170.Height=15.00
App.ActiveDocument.C170.Angle=360.00 
App.ActiveDocument.C170.Placement=Base.Placement(Base.Vector(-25.218321,-134.198902,548.290570),Base.Rotation(-0.067519,0.026679,0.000000,0.997361))
App.ActiveDocument.addObject("Part::Cylinder","C171")
App.ActiveDocument.C171.Radius=0.750000
App.ActiveDocument.C171.Height=15.00
App.ActiveDocument.C171.Angle=360.00 
App.ActiveDocument.C171.Placement=Base.Placement(Base.Vector(-25.282249,-130.933638,547.742349),Base.Rotation(-0.100067,0.025128,0.000000,0.994663))
App.ActiveDocument.addObject("Part::Cylinder","C172")
App.ActiveDocument.C172.Radius=0.750000
App.ActiveDocument.C172.Height=15.00
App.ActiveDocument.C172.Angle=360.00 
App.ActiveDocument.C172.Placement=Base.Placement(Base.Vector(-25.082575,-127.812123,546.988848),Base.Rotation(-0.132717,0.025842,0.000000,0.990817))
App.ActiveDocument.addObject("Part::Cylinder","C173")
App.ActiveDocument.C173.Radius=0.750000
App.ActiveDocument.C173.Height=15.00
App.ActiveDocument.C173.Angle=360.00 
App.ActiveDocument.C173.Placement=Base.Placement(Base.Vector(-25.304676,-124.791698,546.043083),Base.Rotation(-0.171205,0.022274,0.000000,0.984984))
App.ActiveDocument.addObject("Part::Cylinder","C174")
App.ActiveDocument.C174.Radius=0.750000
App.ActiveDocument.C174.Height=15.00
App.ActiveDocument.C174.Angle=360.00 
App.ActiveDocument.C174.Placement=Base.Placement(Base.Vector(-25.114676,-121.887385,544.856069),Base.Rotation(-0.210451,0.022619,0.000000,0.977343))
App.ActiveDocument.addObject("Part::Cylinder","C175")
App.ActiveDocument.C175.Radius=0.750000
App.ActiveDocument.C175.Height=15.00
App.ActiveDocument.C175.Angle=360.00 
App.ActiveDocument.C175.Placement=Base.Placement(Base.Vector(-25.055868,-119.180842,543.482014),Base.Rotation(-0.253590,0.022306,0.000000,0.967054))
App.ActiveDocument.addObject("Part::Cylinder","C176")
App.ActiveDocument.C176.Radius=0.750000
App.ActiveDocument.C176.Height=15.00
App.ActiveDocument.C176.Angle=360.00 
App.ActiveDocument.C176.Placement=Base.Placement(Base.Vector(-25.267337,-116.603485,541.885868),Base.Rotation(-0.296475,0.019940,0.000000,0.954833))
App.ActiveDocument.addObject("Part::Cylinder","C177")
App.ActiveDocument.C177.Radius=0.750000
App.ActiveDocument.C177.Height=15.00
App.ActiveDocument.C177.Angle=360.00 
App.ActiveDocument.C177.Placement=Base.Placement(Base.Vector(-25.100503,-114.186906,540.042689),Base.Rotation(-0.341183,0.021384,0.000000,0.939754))
App.ActiveDocument.addObject("Part::Cylinder","C178")
App.ActiveDocument.C178.Radius=0.750000
App.ActiveDocument.C178.Height=15.00
App.ActiveDocument.C178.Angle=360.00 
App.ActiveDocument.C178.Placement=Base.Placement(Base.Vector(-25.213029,-112.002898,538.035663),Base.Rotation(-0.385666,0.022545,0.000000,0.922363))
App.ActiveDocument.addObject("Part::Cylinder","C179")
App.ActiveDocument.C179.Radius=0.750000
App.ActiveDocument.C179.Height=15.00
App.ActiveDocument.C179.Angle=360.00 
App.ActiveDocument.C179.Placement=Base.Placement(Base.Vector(-25.284514,-109.998953,535.804205),Base.Rotation(-0.428275,0.025559,0.000000,0.903287))
App.ActiveDocument.addObject("Part::Cylinder","C180")
App.ActiveDocument.C180.Radius=0.750000
App.ActiveDocument.C180.Height=15.00
App.ActiveDocument.C180.Angle=360.00 
App.ActiveDocument.C180.Placement=Base.Placement(Base.Vector(-25.224056,-108.191803,533.348298),Base.Rotation(-0.471864,0.032083,0.000000,0.881088))
App.ActiveDocument.addObject("Part::Cylinder","C181")
App.ActiveDocument.C181.Radius=0.750000
App.ActiveDocument.C181.Height=15.00
App.ActiveDocument.C181.Angle=360.00 
App.ActiveDocument.C181.Placement=Base.Placement(Base.Vector(-25.492220,-106.625352,530.773717),Base.Rotation(-0.510252,0.037256,0.000000,0.859218))
App.ActiveDocument.addObject("Part::Cylinder","C182")
App.ActiveDocument.C182.Radius=0.750000
App.ActiveDocument.C182.Height=15.00
App.ActiveDocument.C182.Angle=360.00 
App.ActiveDocument.C182.Placement=Base.Placement(Base.Vector(-25.593729,-105.288846,528.038855),Base.Rotation(-0.547379,0.048481,0.000000,0.835479))
App.ActiveDocument.addObject("Part::Cylinder","C183")
App.ActiveDocument.C183.Radius=0.750000
App.ActiveDocument.C183.Height=15.00
App.ActiveDocument.C183.Angle=360.00 
App.ActiveDocument.C183.Placement=Base.Placement(Base.Vector(-25.676570,-104.171900,525.152710),Base.Rotation(-0.580486,0.058153,0.000000,0.812191))
App.ActiveDocument.addObject("Part::Cylinder","C184")
App.ActiveDocument.C184.Radius=0.750000
App.ActiveDocument.C184.Height=15.00
App.ActiveDocument.C184.Angle=360.00 
App.ActiveDocument.C184.Placement=Base.Placement(Base.Vector(-26.006746,-103.238523,522.117841),Base.Rotation(-0.610923,0.061377,0.000000,0.789307))
App.ActiveDocument.addObject("Part::Cylinder","C185")
App.ActiveDocument.C185.Radius=0.750000
App.ActiveDocument.C185.Height=15.00
App.ActiveDocument.C185.Angle=360.00 
App.ActiveDocument.C185.Placement=Base.Placement(Base.Vector(-25.953465,-102.546509,518.883927),Base.Rotation(-0.639405,0.072355,0.000000,0.765458))
App.ActiveDocument.addObject("Part::Cylinder","C186")
App.ActiveDocument.C186.Radius=0.750000
App.ActiveDocument.C186.Height=15.00
App.ActiveDocument.C186.Angle=360.00 
App.ActiveDocument.C186.Placement=Base.Placement(Base.Vector(-25.984551,-102.076554,515.600018),Base.Rotation(-0.663072,0.078514,0.000000,0.744427))
App.ActiveDocument.addObject("Part::Cylinder","C187")
App.ActiveDocument.C187.Radius=0.750000
App.ActiveDocument.C187.Height=15.00
App.ActiveDocument.C187.Angle=360.00 
App.ActiveDocument.C187.Placement=Base.Placement(Base.Vector(-26.130030,-101.808447,512.314891),Base.Rotation(-0.685716,0.086149,0.000000,0.722753))
App.ActiveDocument.addObject("Part::Cylinder","C188")
App.ActiveDocument.C188.Radius=0.750000
App.ActiveDocument.C188.Height=15.00
App.ActiveDocument.C188.Angle=360.00 
App.ActiveDocument.C188.Placement=Base.Placement(Base.Vector(-26.179351,-101.754291,508.932052),Base.Rotation(-0.706685,0.094431,0.000000,0.701199))
App.ActiveDocument.addObject("Part::Cylinder","C189")
App.ActiveDocument.C189.Radius=0.750000
App.ActiveDocument.C189.Height=15.00
App.ActiveDocument.C189.Angle=360.00 
App.ActiveDocument.C189.Placement=Base.Placement(Base.Vector(-26.262498,-101.900180,505.459914),Base.Rotation(-0.725760,0.101418,0.000000,0.680431))
App.ActiveDocument.addObject("Part::Cylinder","C190")
App.ActiveDocument.C190.Radius=0.750000
App.ActiveDocument.C190.Height=15.00
App.ActiveDocument.C190.Angle=360.00 
App.ActiveDocument.C190.Placement=Base.Placement(Base.Vector(-26.354033,-102.233261,502.106144),Base.Rotation(-0.742737,0.110611,0.000000,0.660384))
App.ActiveDocument.addObject("Part::Cylinder","C191")
App.ActiveDocument.C191.Radius=0.750000
App.ActiveDocument.C191.Height=15.00
App.ActiveDocument.C191.Angle=360.00 
App.ActiveDocument.C191.Placement=Base.Placement(Base.Vector(-26.477099,-102.745341,498.763624),Base.Rotation(-0.759192,0.118937,0.000000,0.639907))
App.ActiveDocument.addObject("Part::Cylinder","C192")
App.ActiveDocument.C192.Radius=0.750000
App.ActiveDocument.C192.Height=15.00
App.ActiveDocument.C192.Angle=360.00 
App.ActiveDocument.C192.Placement=Base.Placement(Base.Vector(-26.504299,-103.458053,495.417316),Base.Rotation(-0.774061,0.129437,0.000000,0.619739))
App.ActiveDocument.addObject("Part::Cylinder","C193")
App.ActiveDocument.C193.Radius=0.750000
App.ActiveDocument.C193.Height=15.00
App.ActiveDocument.C193.Angle=360.00 
App.ActiveDocument.C193.Placement=Base.Placement(Base.Vector(-26.692952,-104.322601,492.107054),Base.Rotation(-0.787811,0.140242,0.000000,0.599738))
App.ActiveDocument.addObject("Part::Cylinder","C194")
App.ActiveDocument.C194.Radius=0.750000
App.ActiveDocument.C194.Height=15.00
App.ActiveDocument.C194.Angle=360.00 
App.ActiveDocument.C194.Placement=Base.Placement(Base.Vector(-26.771932,-105.356683,488.910466),Base.Rotation(-0.801181,0.153537,0.000000,0.578391))
App.ActiveDocument.addObject("Part::Cylinder","C195")
App.ActiveDocument.C195.Radius=0.750000
App.ActiveDocument.C195.Height=15.00
App.ActiveDocument.C195.Angle=360.00 
App.ActiveDocument.C195.Placement=Base.Placement(Base.Vector(-26.733475,-106.620800,485.676595),Base.Rotation(-0.813679,0.168437,0.000000,0.556377))
App.ActiveDocument.addObject("Part::Cylinder","C196")
App.ActiveDocument.C196.Radius=0.750000
App.ActiveDocument.C196.Height=15.00
App.ActiveDocument.C196.Angle=360.00 
App.ActiveDocument.C196.Placement=Base.Placement(Base.Vector(-26.922573,-108.001490,482.546741),Base.Rotation(-0.825360,0.184598,0.000000,0.533577))
App.ActiveDocument.addObject("Part::Cylinder","C197")
App.ActiveDocument.C197.Radius=0.750000
App.ActiveDocument.C197.Height=15.00
App.ActiveDocument.C197.Angle=360.00 
App.ActiveDocument.C197.Placement=Base.Placement(Base.Vector(-27.087534,-109.560311,479.499060),Base.Rotation(-0.836011,0.200034,0.000000,0.510953))
App.ActiveDocument.addObject("Part::Cylinder","C198")
App.ActiveDocument.C198.Radius=0.750000
App.ActiveDocument.C198.Height=15.00
App.ActiveDocument.C198.Angle=360.00 
App.ActiveDocument.C198.Placement=Base.Placement(Base.Vector(-27.054394,-111.309728,476.609559),Base.Rotation(-0.844373,0.226244,0.000000,0.485642))
App.ActiveDocument.addObject("Part::Cylinder","C199")
App.ActiveDocument.C199.Radius=0.750000
App.ActiveDocument.C199.Height=15.00
App.ActiveDocument.C199.Angle=360.00 
App.ActiveDocument.C199.Placement=Base.Placement(Base.Vector(-27.186750,-113.125747,473.935328),Base.Rotation(-0.849925,0.256491,0.000000,0.460261))
App.ActiveDocument.addObject("Part::Cylinder","C200")
App.ActiveDocument.C200.Radius=0.750000
App.ActiveDocument.C200.Height=15.00
App.ActiveDocument.C200.Angle=360.00 
App.ActiveDocument.C200.Placement=Base.Placement(Base.Vector(-27.451773,-115.124887,471.336747),Base.Rotation(-0.855044,0.292526,0.000000,0.428168))
App.ActiveDocument.addObject("Part::Cylinder","C201")
App.ActiveDocument.C201.Radius=0.750000
App.ActiveDocument.C201.Height=15.00
App.ActiveDocument.C201.Angle=360.00 
App.ActiveDocument.C201.Placement=Base.Placement(Base.Vector(-21.870136,-137.583015,548.362748),Base.Rotation(-0.035773,0.058416,0.000000,0.997651))
App.ActiveDocument.addObject("Part::Cylinder","C202")
App.ActiveDocument.C202.Radius=0.750000
App.ActiveDocument.C202.Height=15.00
App.ActiveDocument.C202.Angle=360.00 
App.ActiveDocument.C202.Placement=Base.Placement(Base.Vector(-21.851262,-134.215939,548.022706),Base.Rotation(-0.065273,0.054664,0.000000,0.996369))
App.ActiveDocument.addObject("Part::Cylinder","C203")
App.ActiveDocument.C203.Radius=0.750000
App.ActiveDocument.C203.Height=15.00
App.ActiveDocument.C203.Angle=360.00 
App.ActiveDocument.C203.Placement=Base.Placement(Base.Vector(-21.900838,-131.001896,547.501326),Base.Rotation(-0.097192,0.051482,0.000000,0.993933))
App.ActiveDocument.addObject("Part::Cylinder","C204")
App.ActiveDocument.C204.Radius=0.750000
App.ActiveDocument.C204.Height=15.00
App.ActiveDocument.C204.Angle=360.00 
App.ActiveDocument.C204.Placement=Base.Placement(Base.Vector(-21.600877,-127.812545,546.723940),Base.Rotation(-0.132353,0.051552,0.000000,0.989861))
App.ActiveDocument.addObject("Part::Cylinder","C205")
App.ActiveDocument.C205.Radius=0.750000
App.ActiveDocument.C205.Height=15.00
App.ActiveDocument.C205.Angle=360.00 
App.ActiveDocument.C205.Placement=Base.Placement(Base.Vector(-21.937103,-124.826618,545.819641),Base.Rotation(-0.167976,0.046711,0.000000,0.984684))
App.ActiveDocument.addObject("Part::Cylinder","C206")
App.ActiveDocument.C206.Radius=0.750000
App.ActiveDocument.C206.Height=15.00
App.ActiveDocument.C206.Angle=360.00 
App.ActiveDocument.C206.Placement=Base.Placement(Base.Vector(-21.655945,-121.970042,544.641695),Base.Rotation(-0.210017,0.048880,0.000000,0.976475))
App.ActiveDocument.addObject("Part::Cylinder","C207")
App.ActiveDocument.C207.Radius=0.750000
App.ActiveDocument.C207.Height=15.00
App.ActiveDocument.C207.Angle=360.00 
App.ActiveDocument.C207.Placement=Base.Placement(Base.Vector(-21.564250,-119.226548,543.242769),Base.Rotation(-0.252681,0.051581,0.000000,0.966174))
App.ActiveDocument.addObject("Part::Cylinder","C208")
App.ActiveDocument.C208.Radius=0.750000
App.ActiveDocument.C208.Height=15.00
App.ActiveDocument.C208.Angle=360.00 
App.ActiveDocument.C208.Placement=Base.Placement(Base.Vector(-21.905303,-116.638497,541.652780),Base.Rotation(-0.297306,0.048036,0.000000,0.953573))
App.ActiveDocument.addObject("Part::Cylinder","C209")
App.ActiveDocument.C209.Radius=0.750000
App.ActiveDocument.C209.Height=15.00
App.ActiveDocument.C209.Angle=360.00 
App.ActiveDocument.C209.Placement=Base.Placement(Base.Vector(-21.756467,-114.305534,539.840081),Base.Rotation(-0.343153,0.057580,0.000000,0.937513))
App.ActiveDocument.addObject("Part::Cylinder","C210")
App.ActiveDocument.C210.Radius=0.750000
App.ActiveDocument.C210.Height=15.00
App.ActiveDocument.C210.Angle=360.00 
App.ActiveDocument.C210.Placement=Base.Placement(Base.Vector(-21.975589,-112.104806,537.800584),Base.Rotation(-0.389604,0.060744,0.000000,0.918977))
App.ActiveDocument.addObject("Part::Cylinder","C211")
App.ActiveDocument.C211.Radius=0.750000
App.ActiveDocument.C211.Height=15.00
App.ActiveDocument.C211.Angle=360.00 
App.ActiveDocument.C211.Placement=Base.Placement(Base.Vector(-22.083924,-110.137276,535.560112),Base.Rotation(-0.435259,0.067265,0.000000,0.897789))
App.ActiveDocument.addObject("Part::Cylinder","C212")
App.ActiveDocument.C212.Radius=0.750000
App.ActiveDocument.C212.Height=15.00
App.ActiveDocument.C212.Angle=360.00 
App.ActiveDocument.C212.Placement=Base.Placement(Base.Vector(-22.053615,-108.382240,533.078773),Base.Rotation(-0.477294,0.077725,0.000000,0.875300))
App.ActiveDocument.addObject("Part::Cylinder","C213")
App.ActiveDocument.C213.Radius=0.750000
App.ActiveDocument.C213.Height=15.00
App.ActiveDocument.C213.Angle=360.00 
App.ActiveDocument.C213.Placement=Base.Placement(Base.Vector(-22.343410,-106.833006,530.464015),Base.Rotation(-0.513920,0.082123,0.000000,0.853898))
App.ActiveDocument.addObject("Part::Cylinder","C214")
App.ActiveDocument.C214.Radius=0.750000
App.ActiveDocument.C214.Height=15.00
App.ActiveDocument.C214.Angle=360.00 
App.ActiveDocument.C214.Placement=Base.Placement(Base.Vector(-22.250543,-105.561154,527.676970),Base.Rotation(-0.549160,0.092428,0.000000,0.830590))
App.ActiveDocument.addObject("Part::Cylinder","C215")
App.ActiveDocument.C215.Radius=0.750000
App.ActiveDocument.C215.Height=15.00
App.ActiveDocument.C215.Angle=360.00 
App.ActiveDocument.C215.Placement=Base.Placement(Base.Vector(-22.288093,-104.487157,524.732757),Base.Rotation(-0.583350,0.099316,0.000000,0.806126))
App.ActiveDocument.addObject("Part::Cylinder","C216")
App.ActiveDocument.C216.Radius=0.750000
App.ActiveDocument.C216.Height=15.00
App.ActiveDocument.C216.Angle=360.00 
App.ActiveDocument.C216.Placement=Base.Placement(Base.Vector(-22.691064,-103.576036,521.681624),Base.Rotation(-0.613760,0.100416,0.000000,0.783080))
App.ActiveDocument.addObject("Part::Cylinder","C217")
App.ActiveDocument.C217.Radius=0.750000
App.ActiveDocument.C217.Height=15.00
App.ActiveDocument.C217.Angle=360.00 
App.ActiveDocument.C217.Placement=Base.Placement(Base.Vector(-22.534754,-102.962468,518.471016),Base.Rotation(-0.639027,0.108242,0.000000,0.761530))
App.ActiveDocument.addObject("Part::Cylinder","C218")
App.ActiveDocument.C218.Radius=0.750000
App.ActiveDocument.C218.Height=15.00
App.ActiveDocument.C218.Angle=360.00 
App.ActiveDocument.C218.Placement=Base.Placement(Base.Vector(-22.516118,-102.551325,515.220431),Base.Rotation(-0.664123,0.116709,0.000000,0.738457))
App.ActiveDocument.addObject("Part::Cylinder","C219")
App.ActiveDocument.C219.Radius=0.750000
App.ActiveDocument.C219.Height=15.00
App.ActiveDocument.C219.Angle=360.00 
App.ActiveDocument.C219.Placement=Base.Placement(Base.Vector(-22.633711,-102.323851,511.848786),Base.Rotation(-0.685998,0.124466,0.000000,0.716878))
App.ActiveDocument.addObject("Part::Cylinder","C220")
App.ActiveDocument.C220.Radius=0.750000
App.ActiveDocument.C220.Height=15.00
App.ActiveDocument.C220.Angle=360.00 
App.ActiveDocument.C220.Placement=Base.Placement(Base.Vector(-22.764608,-102.307376,508.421462),Base.Rotation(-0.706364,0.130082,0.000000,0.695794))
App.ActiveDocument.addObject("Part::Cylinder","C221")
App.ActiveDocument.C221.Radius=0.750000
App.ActiveDocument.C221.Height=15.00
App.ActiveDocument.C221.Angle=360.00 
App.ActiveDocument.C221.Placement=Base.Placement(Base.Vector(-22.825150,-102.504152,505.067716),Base.Rotation(-0.725372,0.138212,0.000000,0.674339))
App.ActiveDocument.addObject("Part::Cylinder","C222")
App.ActiveDocument.C222.Radius=0.750000
App.ActiveDocument.C222.Height=15.00
App.ActiveDocument.C222.Angle=360.00 
App.ActiveDocument.C222.Placement=Base.Placement(Base.Vector(-22.900922,-102.904485,501.612296),Base.Rotation(-0.742543,0.149083,0.000000,0.652997))
App.ActiveDocument.addObject("Part::Cylinder","C223")
App.ActiveDocument.C223.Radius=0.750000
App.ActiveDocument.C223.Height=15.00
App.ActiveDocument.C223.Angle=360.00 
App.ActiveDocument.C223.Placement=Base.Placement(Base.Vector(-23.031682,-103.470683,498.277141),Base.Rotation(-0.757393,0.158889,0.000000,0.633333))
App.ActiveDocument.addObject("Part::Cylinder","C224")
App.ActiveDocument.C224.Radius=0.750000
App.ActiveDocument.C224.Height=15.00
App.ActiveDocument.C224.Angle=360.00 
App.ActiveDocument.C224.Placement=Base.Placement(Base.Vector(-22.955116,-104.262594,494.978962),Base.Rotation(-0.771094,0.175417,0.000000,0.612081))
App.ActiveDocument.addObject("Part::Cylinder","C225")
App.ActiveDocument.C225.Radius=0.750000
App.ActiveDocument.C225.Height=15.00
App.ActiveDocument.C225.Angle=360.00 
App.ActiveDocument.C225.Placement=Base.Placement(Base.Vector(-23.233665,-105.151199,491.723781),Base.Rotation(-0.784210,0.184404,0.000000,0.592461))
App.ActiveDocument.addObject("Part::Cylinder","C226")
App.ActiveDocument.C226.Radius=0.750000
App.ActiveDocument.C226.Height=15.00
App.ActiveDocument.C226.Angle=360.00 
App.ActiveDocument.C226.Placement=Base.Placement(Base.Vector(-23.294981,-106.272534,488.495370),Base.Rotation(-0.796737,0.199568,0.000000,0.570423))
App.ActiveDocument.addObject("Part::Cylinder","C227")
App.ActiveDocument.C227.Radius=0.750000
App.ActiveDocument.C227.Height=15.00
App.ActiveDocument.C227.Angle=360.00 
App.ActiveDocument.C227.Placement=Base.Placement(Base.Vector(-23.304323,-107.563547,485.381167),Base.Rotation(-0.806995,0.219113,0.000000,0.548406))
App.ActiveDocument.addObject("Part::Cylinder","C228")
App.ActiveDocument.C228.Radius=0.750000
App.ActiveDocument.C228.Height=15.00
App.ActiveDocument.C228.Angle=360.00 
App.ActiveDocument.C228.Placement=Base.Placement(Base.Vector(-23.554844,-108.996461,482.273553),Base.Rotation(-0.816915,0.237900,0.000000,0.525409))
App.ActiveDocument.addObject("Part::Cylinder","C229")
App.ActiveDocument.C229.Radius=0.750000
App.ActiveDocument.C229.Height=15.00
App.ActiveDocument.C229.Angle=360.00 
App.ActiveDocument.C229.Placement=Base.Placement(Base.Vector(-23.706063,-110.598107,479.327451),Base.Rotation(-0.824239,0.264559,0.000000,0.500638))
App.ActiveDocument.addObject("Part::Cylinder","C230")
App.ActiveDocument.C230.Radius=0.750000
App.ActiveDocument.C230.Height=15.00
App.ActiveDocument.C230.Angle=360.00 
App.ActiveDocument.C230.Placement=Base.Placement(Base.Vector(-23.729612,-112.354233,476.595046),Base.Rotation(-0.828004,0.294807,0.000000,0.476968))
App.ActiveDocument.addObject("Part::Cylinder","C231")
App.ActiveDocument.C231.Radius=0.750000
App.ActiveDocument.C231.Height=15.00
App.ActiveDocument.C231.Angle=360.00 
App.ActiveDocument.C231.Placement=Base.Placement(Base.Vector(-24.007895,-114.237561,473.933980),Base.Rotation(-0.828847,0.334211,0.000000,0.448682))
App.ActiveDocument.addObject("Part::Cylinder","C232")
App.ActiveDocument.C232.Radius=0.750000
App.ActiveDocument.C232.Height=15.00
App.ActiveDocument.C232.Angle=360.00 
App.ActiveDocument.C232.Placement=Base.Placement(Base.Vector(-24.439103,-116.266808,471.393464),Base.Rotation(-0.826688,0.376091,0.000000,0.418501))
App.ActiveDocument.addObject("Part::Cylinder","C233")
App.ActiveDocument.C233.Radius=0.750000
App.ActiveDocument.C233.Height=15.00
App.ActiveDocument.C233.Angle=360.00 
App.ActiveDocument.C233.Placement=Base.Placement(Base.Vector(-18.606223,-137.471453,547.857308),Base.Rotation(-0.031615,0.092667,0.000000,0.995195))
App.ActiveDocument.addObject("Part::Cylinder","C234")
App.ActiveDocument.C234.Radius=0.750000
App.ActiveDocument.C234.Height=15.00
App.ActiveDocument.C234.Angle=360.00 
App.ActiveDocument.C234.Placement=Base.Placement(Base.Vector(-18.579967,-134.092515,547.528308),Base.Rotation(-0.062872,0.090291,0.000000,0.993929))
App.ActiveDocument.addObject("Part::Cylinder","C235")
App.ActiveDocument.C235.Radius=0.750000
App.ActiveDocument.C235.Height=15.00
App.ActiveDocument.C235.Angle=360.00 
App.ActiveDocument.C235.Placement=Base.Placement(Base.Vector(-18.617476,-130.813743,547.003460),Base.Rotation(-0.096503,0.088273,0.000000,0.991411))
App.ActiveDocument.addObject("Part::Cylinder","C236")
App.ActiveDocument.C236.Radius=0.750000
App.ActiveDocument.C236.Height=15.00
App.ActiveDocument.C236.Angle=360.00 
App.ActiveDocument.C236.Placement=Base.Placement(Base.Vector(-18.402958,-127.686806,546.224113),Base.Rotation(-0.135054,0.092042,0.000000,0.986554))
App.ActiveDocument.addObject("Part::Cylinder","C237")
App.ActiveDocument.C237.Radius=0.750000
App.ActiveDocument.C237.Height=15.00
App.ActiveDocument.C237.Angle=360.00 
App.ActiveDocument.C237.Placement=Base.Placement(Base.Vector(-18.743473,-124.649469,545.315884),Base.Rotation(-0.171757,0.088945,0.000000,0.981116))
App.ActiveDocument.addObject("Part::Cylinder","C238")
App.ActiveDocument.C238.Radius=0.750000
App.ActiveDocument.C238.Height=15.00
App.ActiveDocument.C238.Angle=360.00 
App.ActiveDocument.C238.Placement=Base.Placement(Base.Vector(-18.498512,-121.809400,544.089167),Base.Rotation(-0.214680,0.093263,0.000000,0.972221))
App.ActiveDocument.addObject("Part::Cylinder","C239")
App.ActiveDocument.C239.Radius=0.750000
App.ActiveDocument.C239.Height=15.00
App.ActiveDocument.C239.Angle=360.00 
App.ActiveDocument.C239.Placement=Base.Placement(Base.Vector(-18.516008,-119.115685,542.671896),Base.Rotation(-0.259694,0.097177,0.000000,0.960789))
App.ActiveDocument.addObject("Part::Cylinder","C240")
App.ActiveDocument.C240.Radius=0.750000
App.ActiveDocument.C240.Height=15.00
App.ActiveDocument.C240.Angle=360.00 
App.ActiveDocument.C240.Placement=Base.Placement(Base.Vector(-18.814355,-116.591014,541.087792),Base.Rotation(-0.306539,0.099100,0.000000,0.946685))
App.ActiveDocument.addObject("Part::Cylinder","C241")
App.ActiveDocument.C241.Radius=0.750000
App.ActiveDocument.C241.Height=15.00
App.ActiveDocument.C241.Angle=360.00 
App.ActiveDocument.C241.Placement=Base.Placement(Base.Vector(-18.641004,-114.265770,539.164642),Base.Rotation(-0.352150,0.106518,0.000000,0.929862))
App.ActiveDocument.addObject("Part::Cylinder","C242")
App.ActiveDocument.C242.Radius=0.750000
App.ActiveDocument.C242.Height=15.00
App.ActiveDocument.C242.Angle=360.00 
App.ActiveDocument.C242.Placement=Base.Placement(Base.Vector(-18.930911,-112.127031,537.121316),Base.Rotation(-0.398355,0.108293,0.000000,0.910816))
App.ActiveDocument.addObject("Part::Cylinder","C243")
App.ActiveDocument.C243.Radius=0.750000
App.ActiveDocument.C243.Height=15.00
App.ActiveDocument.C243.Angle=360.00 
App.ActiveDocument.C243.Placement=Base.Placement(Base.Vector(-18.859233,-110.260295,534.830731),Base.Rotation(-0.442977,0.113635,0.000000,0.889302))
App.ActiveDocument.addObject("Part::Cylinder","C244")
App.ActiveDocument.C244.Radius=0.750000
App.ActiveDocument.C244.Height=15.00
App.ActiveDocument.C244.Angle=360.00 
App.ActiveDocument.C244.Placement=Base.Placement(Base.Vector(-18.865760,-108.581162,532.328094),Base.Rotation(-0.481501,0.118812,0.000000,0.868355))
App.ActiveDocument.addObject("Part::Cylinder","C245")
App.ActiveDocument.C245.Radius=0.750000
App.ActiveDocument.C245.Height=15.00
App.ActiveDocument.C245.Angle=360.00 
App.ActiveDocument.C245.Placement=Base.Placement(Base.Vector(-19.014060,-107.133911,529.732562),Base.Rotation(-0.520589,0.123725,0.000000,0.844795))
App.ActiveDocument.addObject("Part::Cylinder","C246")
App.ActiveDocument.C246.Radius=0.750000
App.ActiveDocument.C246.Height=15.00
App.ActiveDocument.C246.Angle=360.00 
App.ActiveDocument.C246.Placement=Base.Placement(Base.Vector(-18.925954,-105.919216,526.894874),Base.Rotation(-0.553106,0.128720,0.000000,0.823107))
App.ActiveDocument.addObject("Part::Cylinder","C247")
App.ActiveDocument.C247.Radius=0.750000
App.ActiveDocument.C247.Height=15.00
App.ActiveDocument.C247.Angle=360.00 
App.ActiveDocument.C247.Placement=Base.Placement(Base.Vector(-18.868527,-104.924284,523.921100),Base.Rotation(-0.586445,0.136095,0.000000,0.798474))
App.ActiveDocument.addObject("Part::Cylinder","C248")
App.ActiveDocument.C248.Radius=0.750000
App.ActiveDocument.C248.Height=15.00
App.ActiveDocument.C248.Angle=360.00 
App.ActiveDocument.C248.Placement=Base.Placement(Base.Vector(-19.300430,-104.049238,520.870884),Base.Rotation(-0.615072,0.137287,0.000000,0.776427))
App.ActiveDocument.addObject("Part::Cylinder","C249")
App.ActiveDocument.C249.Radius=0.750000
App.ActiveDocument.C249.Height=15.00
App.ActiveDocument.C249.Angle=360.00 
App.ActiveDocument.C249.Placement=Base.Placement(Base.Vector(-19.051745,-103.541415,517.708811),Base.Rotation(-0.639306,0.146526,0.000000,0.754863))
App.ActiveDocument.addObject("Part::Cylinder","C250")
App.ActiveDocument.C250.Radius=0.750000
App.ActiveDocument.C250.Height=15.00
App.ActiveDocument.C250.Angle=360.00 
App.ActiveDocument.C250.Placement=Base.Placement(Base.Vector(-19.098512,-103.185012,514.508258),Base.Rotation(-0.663618,0.153482,0.000000,0.732157))
App.ActiveDocument.addObject("Part::Cylinder","C251")
App.ActiveDocument.C251.Radius=0.750000
App.ActiveDocument.C251.Height=15.00
App.ActiveDocument.C251.Angle=360.00 
App.ActiveDocument.C251.Placement=Base.Placement(Base.Vector(-19.210311,-103.019918,511.235962),Base.Rotation(-0.684568,0.160277,0.000000,0.711110))
App.ActiveDocument.addObject("Part::Cylinder","C252")
App.ActiveDocument.C252.Radius=0.750000
App.ActiveDocument.C252.Height=15.00
App.ActiveDocument.C252.Angle=360.00 
App.ActiveDocument.C252.Placement=Base.Placement(Base.Vector(-19.368127,-103.048120,507.890129),Base.Rotation(-0.704474,0.168880,0.000000,0.689345))
App.ActiveDocument.addObject("Part::Cylinder","C253")
App.ActiveDocument.C253.Radius=0.750000
App.ActiveDocument.C253.Height=15.00
App.ActiveDocument.C253.Angle=360.00 
App.ActiveDocument.C253.Placement=Base.Placement(Base.Vector(-19.414826,-103.307236,504.512454),Base.Rotation(-0.722137,0.178737,0.000000,0.668260))
App.ActiveDocument.addObject("Part::Cylinder","C254")
App.ActiveDocument.C254.Radius=0.750000
App.ActiveDocument.C254.Height=15.00
App.ActiveDocument.C254.Angle=360.00 
App.ActiveDocument.C254.Placement=Base.Placement(Base.Vector(-19.471968,-103.764794,501.136815),Base.Rotation(-0.738270,0.189885,0.000000,0.647226))
App.ActiveDocument.addObject("Part::Cylinder","C255")
App.ActiveDocument.C255.Radius=0.750000
App.ActiveDocument.C255.Height=15.00
App.ActiveDocument.C255.Angle=360.00 
App.ActiveDocument.C255.Placement=Base.Placement(Base.Vector(-19.586541,-104.385732,497.849490),Base.Rotation(-0.752587,0.202709,0.000000,0.626515))
App.ActiveDocument.addObject("Part::Cylinder","C256")
App.ActiveDocument.C256.Radius=0.750000
App.ActiveDocument.C256.Height=15.00
App.ActiveDocument.C256.Angle=360.00 
App.ActiveDocument.C256.Placement=Base.Placement(Base.Vector(-19.554554,-105.228366,494.599798),Base.Rotation(-0.764780,0.217377,0.000000,0.606514))
App.ActiveDocument.addObject("Part::Cylinder","C257")
App.ActiveDocument.C257.Radius=0.750000
App.ActiveDocument.C257.Height=15.00
App.ActiveDocument.C257.Angle=360.00 
App.ActiveDocument.C257.Placement=Base.Placement(Base.Vector(-19.914379,-106.156354,491.338103),Base.Rotation(-0.778366,0.229050,0.000000,0.584536))
App.ActiveDocument.addObject("Part::Cylinder","C258")
App.ActiveDocument.C258.Radius=0.750000
App.ActiveDocument.C258.Height=15.00
App.ActiveDocument.C258.Angle=360.00 
App.ActiveDocument.C258.Placement=Base.Placement(Base.Vector(-19.901591,-107.354171,488.190820),Base.Rotation(-0.787973,0.248978,0.000000,0.563123))
App.ActiveDocument.addObject("Part::Cylinder","C259")
App.ActiveDocument.C259.Radius=0.750000
App.ActiveDocument.C259.Height=15.00
App.ActiveDocument.C259.Angle=360.00 
App.ActiveDocument.C259.Placement=Base.Placement(Base.Vector(-20.004027,-108.688574,485.134394),Base.Rotation(-0.794627,0.274687,0.000000,0.541401))
App.ActiveDocument.addObject("Part::Cylinder","C260")
App.ActiveDocument.C260.Radius=0.750000
App.ActiveDocument.C260.Height=15.00
App.ActiveDocument.C260.Angle=360.00 
App.ActiveDocument.C260.Placement=Base.Placement(Base.Vector(-20.343912,-110.136940,482.124469),Base.Rotation(-0.801915,0.301316,0.000000,0.515888))
App.ActiveDocument.addObject("Part::Cylinder","C261")
App.ActiveDocument.C261.Radius=0.750000
App.ActiveDocument.C261.Height=15.00
App.ActiveDocument.C261.Angle=360.00 
App.ActiveDocument.C261.Placement=Base.Placement(Base.Vector(-20.439136,-111.819421,479.283610),Base.Rotation(-0.803914,0.335846,0.000000,0.490846))
App.ActiveDocument.addObject("Part::Cylinder","C262")
App.ActiveDocument.C262.Radius=0.750000
App.ActiveDocument.C262.Height=15.00
App.ActiveDocument.C262.Angle=360.00 
App.ActiveDocument.C262.Placement=Base.Placement(Base.Vector(-20.671090,-113.634547,476.561281),Base.Rotation(-0.802754,0.375444,0.000000,0.463279))
App.ActiveDocument.addObject("Part::Cylinder","C263")
App.ActiveDocument.C263.Radius=0.750000
App.ActiveDocument.C263.Height=15.00
App.ActiveDocument.C263.Angle=360.00 
App.ActiveDocument.C263.Placement=Base.Placement(Base.Vector(-20.933786,-115.600391,474.009287),Base.Rotation(-0.794103,0.420673,0.000000,0.438673))
App.ActiveDocument.addObject("Part::Cylinder","C264")
App.ActiveDocument.C264.Radius=0.750000
App.ActiveDocument.C264.Height=15.00
App.ActiveDocument.C264.Angle=360.00 
App.ActiveDocument.C264.Placement=Base.Placement(Base.Vector(-21.575023,-117.651944,471.510588),Base.Rotation(-0.782942,0.471210,0.000000,0.406155))
App.ActiveDocument.addObject("Part::Cylinder","C265")
App.ActiveDocument.C265.Radius=0.750000
App.ActiveDocument.C265.Height=15.00
App.ActiveDocument.C265.Angle=360.00 
App.ActiveDocument.C265.Placement=Base.Placement(Base.Vector(-15.384605,-137.434847,547.123909),Base.Rotation(-0.030123,0.129056,0.000000,0.991180))
App.ActiveDocument.addObject("Part::Cylinder","C266")
App.ActiveDocument.C266.Radius=0.750000
App.ActiveDocument.C266.Height=15.00
App.ActiveDocument.C266.Angle=360.00 
App.ActiveDocument.C266.Placement=Base.Placement(Base.Vector(-15.482089,-134.110967,546.835313),Base.Rotation(-0.061784,0.127804,0.000000,0.989873))
App.ActiveDocument.addObject("Part::Cylinder","C267")
App.ActiveDocument.C267.Radius=0.750000
App.ActiveDocument.C267.Height=15.00
App.ActiveDocument.C267.Angle=360.00 
App.ActiveDocument.C267.Placement=Base.Placement(Base.Vector(-15.466152,-130.872343,546.306141),Base.Rotation(-0.096251,0.127871,0.000000,0.987109))
App.ActiveDocument.addObject("Part::Cylinder","C268")
App.ActiveDocument.C268.Radius=0.750000
App.ActiveDocument.C268.Height=15.00
App.ActiveDocument.C268.Angle=360.00 
App.ActiveDocument.C268.Placement=Base.Placement(Base.Vector(-15.249244,-127.750191,545.499690),Base.Rotation(-0.132664,0.131637,0.000000,0.982381))
App.ActiveDocument.addObject("Part::Cylinder","C269")
App.ActiveDocument.C269.Radius=0.750000
App.ActiveDocument.C269.Height=15.00
App.ActiveDocument.C269.Angle=360.00 
App.ActiveDocument.C269.Placement=Base.Placement(Base.Vector(-15.644132,-124.748785,544.628313),Base.Rotation(-0.173129,0.128787,0.000000,0.976443))
App.ActiveDocument.addObject("Part::Cylinder","C270")
App.ActiveDocument.C270.Radius=0.750000
App.ActiveDocument.C270.Height=15.00
App.ActiveDocument.C270.Angle=360.00 
App.ActiveDocument.C270.Placement=Base.Placement(Base.Vector(-15.338752,-121.940302,543.344205),Base.Rotation(-0.215815,0.135558,0.000000,0.966979))
App.ActiveDocument.addObject("Part::Cylinder","C271")
App.ActiveDocument.C271.Radius=0.750000
App.ActiveDocument.C271.Height=15.00
App.ActiveDocument.C271.Angle=360.00 
App.ActiveDocument.C271.Placement=Base.Placement(Base.Vector(-15.438037,-119.235469,541.908719),Base.Rotation(-0.262741,0.139015,0.000000,0.954800))
App.ActiveDocument.addObject("Part::Cylinder","C272")
App.ActiveDocument.C272.Radius=0.750000
App.ActiveDocument.C272.Height=15.00
App.ActiveDocument.C272.Angle=360.00 
App.ActiveDocument.C272.Placement=Base.Placement(Base.Vector(-15.610515,-116.769836,540.293596),Base.Rotation(-0.308299,0.141758,0.000000,0.940668))
App.ActiveDocument.addObject("Part::Cylinder","C273")
App.ActiveDocument.C273.Radius=0.750000
App.ActiveDocument.C273.Height=15.00
App.ActiveDocument.C273.Angle=360.00 
App.ActiveDocument.C273.Placement=Base.Placement(Base.Vector(-15.455632,-114.525046,538.355352),Base.Rotation(-0.354149,0.146924,0.000000,0.923576))
App.ActiveDocument.addObject("Part::Cylinder","C274")
App.ActiveDocument.C274.Radius=0.750000
App.ActiveDocument.C274.Height=15.00
App.ActiveDocument.C274.Angle=360.00 
App.ActiveDocument.C274.Placement=Base.Placement(Base.Vector(-15.707436,-112.424118,536.293504),Base.Rotation(-0.401098,0.146263,0.000000,0.904283))
App.ActiveDocument.addObject("Part::Cylinder","C275")
App.ActiveDocument.C275.Radius=0.750000
App.ActiveDocument.C275.Height=15.00
App.ActiveDocument.C275.Angle=360.00 
App.ActiveDocument.C275.Placement=Base.Placement(Base.Vector(-15.602132,-110.579451,533.913412),Base.Rotation(-0.444848,0.152334,0.000000,0.882556))
App.ActiveDocument.addObject("Part::Cylinder","C276")
App.ActiveDocument.C276.Radius=0.750000
App.ActiveDocument.C276.Height=15.00
App.ActiveDocument.C276.Angle=360.00 
App.ActiveDocument.C276.Placement=Base.Placement(Base.Vector(-15.594805,-108.946285,531.358239),Base.Rotation(-0.485290,0.156421,0.000000,0.860248))
App.ActiveDocument.addObject("Part::Cylinder","C277")
App.ActiveDocument.C277.Radius=0.750000
App.ActiveDocument.C277.Height=15.00
App.ActiveDocument.C277.Angle=360.00 
App.ActiveDocument.C277.Placement=Base.Placement(Base.Vector(-15.677354,-107.552090,528.700744),Base.Rotation(-0.524783,0.161365,0.000000,0.835802))
App.ActiveDocument.addObject("Part::Cylinder","C278")
App.ActiveDocument.C278.Radius=0.750000
App.ActiveDocument.C278.Height=15.00
App.ActiveDocument.C278.Angle=360.00 
App.ActiveDocument.C278.Placement=Base.Placement(Base.Vector(-15.603808,-106.408195,525.839622),Base.Rotation(-0.557035,0.166451,0.000000,0.813638))
App.ActiveDocument.addObject("Part::Cylinder","C279")
App.ActiveDocument.C279.Radius=0.750000
App.ActiveDocument.C279.Height=15.00
App.ActiveDocument.C279.Angle=360.00 
App.ActiveDocument.C279.Placement=Base.Placement(Base.Vector(-15.572898,-105.485553,522.855898),Base.Rotation(-0.586590,0.172161,0.000000,0.791374))
App.ActiveDocument.addObject("Part::Cylinder","C280")
App.ActiveDocument.C280.Radius=0.750000
App.ActiveDocument.C280.Height=15.00
App.ActiveDocument.C280.Angle=360.00 
App.ActiveDocument.C280.Placement=Base.Placement(Base.Vector(-15.875116,-104.709025,519.854808),Base.Rotation(-0.616640,0.173847,0.000000,0.767810))
App.ActiveDocument.addObject("Part::Cylinder","C281")
App.ActiveDocument.C281.Radius=0.750000
App.ActiveDocument.C281.Height=15.00
App.ActiveDocument.C281.Angle=360.00 
App.ActiveDocument.C281.Placement=Base.Placement(Base.Vector(-15.643179,-104.288660,516.694216),Base.Rotation(-0.640551,0.185824,0.000000,0.745093))
App.ActiveDocument.addObject("Part::Cylinder","C282")
App.ActiveDocument.C282.Radius=0.750000
App.ActiveDocument.C282.Height=15.00
App.ActiveDocument.C282.Angle=360.00 
App.ActiveDocument.C282.Placement=Base.Placement(Base.Vector(-15.763331,-103.985234,513.458885),Base.Rotation(-0.662456,0.191422,0.000000,0.724230))
App.ActiveDocument.addObject("Part::Cylinder","C283")
App.ActiveDocument.C283.Radius=0.750000
App.ActiveDocument.C283.Height=15.00
App.ActiveDocument.C283.Angle=360.00 
App.ActiveDocument.C283.Placement=Base.Placement(Base.Vector(-15.830863,-103.910371,510.163027),Base.Rotation(-0.684016,0.201061,0.000000,0.701211))
App.ActiveDocument.addObject("Part::Cylinder","C284")
App.ActiveDocument.C284.Radius=0.750000
App.ActiveDocument.C284.Height=15.00
App.ActiveDocument.C284.Angle=360.00 
App.ActiveDocument.C284.Placement=Base.Placement(Base.Vector(-15.988561,-104.013306,506.917846),Base.Rotation(-0.701893,0.209216,0.000000,0.680864))
App.ActiveDocument.addObject("Part::Cylinder","C285")
App.ActiveDocument.C285.Radius=0.750000
App.ActiveDocument.C285.Height=15.00
App.ActiveDocument.C285.Angle=360.00 
App.ActiveDocument.C285.Placement=Base.Placement(Base.Vector(-16.048548,-104.339811,503.677369),Base.Rotation(-0.717550,0.221783,0.000000,0.660254))
App.ActiveDocument.addObject("Part::Cylinder","C286")
App.ActiveDocument.C286.Radius=0.750000
App.ActiveDocument.C286.Height=15.00
App.ActiveDocument.C286.Angle=360.00 
App.ActiveDocument.C286.Placement=Base.Placement(Base.Vector(-16.147103,-104.847035,500.426847),Base.Rotation(-0.732707,0.234754,0.000000,0.638773))
App.ActiveDocument.addObject("Part::Cylinder","C287")
App.ActiveDocument.C287.Radius=0.750000
App.ActiveDocument.C287.Height=15.00
App.ActiveDocument.C287.Angle=360.00 
App.ActiveDocument.C287.Placement=Base.Placement(Base.Vector(-16.244272,-105.538762,497.212714),Base.Rotation(-0.745724,0.247995,0.000000,0.618380))
App.ActiveDocument.addObject("Part::Cylinder","C288")
App.ActiveDocument.C288.Radius=0.750000
App.ActiveDocument.C288.Height=15.00
App.ActiveDocument.C288.Angle=360.00 
App.ActiveDocument.C288.Placement=Base.Placement(Base.Vector(-16.283325,-106.450150,493.985525),Base.Rotation(-0.756704,0.266525,0.000000,0.596962))
App.ActiveDocument.addObject("Part::Cylinder","C289")
App.ActiveDocument.C289.Radius=0.750000
App.ActiveDocument.C289.Height=15.00
App.ActiveDocument.C289.Angle=360.00 
App.ActiveDocument.C289.Placement=Base.Placement(Base.Vector(-16.624993,-107.414524,490.879986),Base.Rotation(-0.766297,0.284858,0.000000,0.575886))
App.ActiveDocument.addObject("Part::Cylinder","C290")
App.ActiveDocument.C290.Radius=0.750000
App.ActiveDocument.C290.Height=15.00
App.ActiveDocument.C290.Angle=360.00 
App.ActiveDocument.C290.Placement=Base.Placement(Base.Vector(-16.716172,-108.628315,487.884895),Base.Rotation(-0.773220,0.310418,0.000000,0.552966))
App.ActiveDocument.addObject("Part::Cylinder","C291")
App.ActiveDocument.C291.Radius=0.750000
App.ActiveDocument.C291.Height=15.00
App.ActiveDocument.C291.Angle=360.00 
App.ActiveDocument.C291.Placement=Base.Placement(Base.Vector(-16.884732,-110.070458,484.813240),Base.Rotation(-0.776606,0.340804,0.000000,0.529845))
App.ActiveDocument.addObject("Part::Cylinder","C292")
App.ActiveDocument.C292.Radius=0.750000
App.ActiveDocument.C292.Height=15.00
App.ActiveDocument.C292.Angle=360.00 
App.ActiveDocument.C292.Placement=Base.Placement(Base.Vector(-17.255309,-111.567239,481.920741),Base.Rotation(-0.778864,0.369807,0.000000,0.506571))
App.ActiveDocument.addObject("Part::Cylinder","C293")
App.ActiveDocument.C293.Radius=0.750000
App.ActiveDocument.C293.Height=15.00
App.ActiveDocument.C293.Angle=360.00 
App.ActiveDocument.C293.Placement=Base.Placement(Base.Vector(-17.362057,-113.291446,479.266261),Base.Rotation(-0.772150,0.415891,0.000000,0.480437))
App.ActiveDocument.addObject("Part::Cylinder","C294")
App.ActiveDocument.C294.Radius=0.750000
App.ActiveDocument.C294.Height=15.00
App.ActiveDocument.C294.Angle=360.00 
App.ActiveDocument.C294.Placement=Base.Placement(Base.Vector(-17.695153,-115.108576,476.694265),Base.Rotation(-0.766828,0.450819,0.000000,0.456877))
App.ActiveDocument.addObject("Part::Cylinder","C295")
App.ActiveDocument.C295.Radius=0.750000
App.ActiveDocument.C295.Height=15.00
App.ActiveDocument.C295.Angle=360.00 
App.ActiveDocument.C295.Placement=Base.Placement(Base.Vector(-17.993149,-117.141164,474.260697),Base.Rotation(-0.746611,0.507150,0.000000,0.430547))
App.ActiveDocument.addObject("Part::Cylinder","C296")
App.ActiveDocument.C296.Radius=0.750000
App.ActiveDocument.C296.Height=15.00
App.ActiveDocument.C296.Angle=360.00 
App.ActiveDocument.C296.Placement=Base.Placement(Base.Vector(-18.772725,-119.194012,471.838559),Base.Rotation(-0.725019,0.562148,0.000000,0.397915))
App.ActiveDocument.addObject("Part::Cylinder","C297")
App.ActiveDocument.C297.Radius=0.750000
App.ActiveDocument.C297.Height=15.00
App.ActiveDocument.C297.Angle=360.00 
App.ActiveDocument.C297.Placement=Base.Placement(Base.Vector(-12.220148,-137.486521,546.172954),Base.Rotation(-0.030509,0.162884,0.000000,0.986173))
App.ActiveDocument.addObject("Part::Cylinder","C298")
App.ActiveDocument.C298.Radius=0.750000
App.ActiveDocument.C298.Height=15.00
App.ActiveDocument.C298.Angle=360.00 
App.ActiveDocument.C298.Placement=Base.Placement(Base.Vector(-12.399165,-134.183208,545.916041),Base.Rotation(-0.061123,0.161764,0.000000,0.984935))
App.ActiveDocument.addObject("Part::Cylinder","C299")
App.ActiveDocument.C299.Radius=0.750000
App.ActiveDocument.C299.Height=15.00
App.ActiveDocument.C299.Angle=360.00 
App.ActiveDocument.C299.Placement=Base.Placement(Base.Vector(-12.334271,-130.951713,545.361245),Base.Rotation(-0.096878,0.163621,0.000000,0.981755))
App.ActiveDocument.addObject("Part::Cylinder","C300")
App.ActiveDocument.C300.Radius=0.750000
App.ActiveDocument.C300.Height=15.00
App.ActiveDocument.C300.Angle=360.00 
App.ActiveDocument.C300.Placement=Base.Placement(Base.Vector(-12.151577,-127.844921,544.531978),Base.Rotation(-0.134173,0.167326,0.000000,0.976729))
App.ActiveDocument.addObject("Part::Cylinder","C301")
App.ActiveDocument.C301.Radius=0.750000
App.ActiveDocument.C301.Height=15.00
App.ActiveDocument.C301.Angle=360.00 
App.ActiveDocument.C301.Placement=Base.Placement(Base.Vector(-12.615803,-124.890712,543.708607),Base.Rotation(-0.177030,0.164372,0.000000,0.970383))
App.ActiveDocument.addObject("Part::Cylinder","C302")
App.ActiveDocument.C302.Radius=0.750000
App.ActiveDocument.C302.Height=15.00
App.ActiveDocument.C302.Angle=360.00 
App.ActiveDocument.C302.Placement=Base.Placement(Base.Vector(-12.232576,-122.087624,542.337021),Base.Rotation(-0.221651,0.170967,0.000000,0.960021))
App.ActiveDocument.addObject("Part::Cylinder","C303")
App.ActiveDocument.C303.Radius=0.750000
App.ActiveDocument.C303.Height=15.00
App.ActiveDocument.C303.Angle=360.00 
App.ActiveDocument.C303.Placement=Base.Placement(Base.Vector(-12.268147,-119.424602,540.855552),Base.Rotation(-0.267663,0.175170,0.000000,0.947456))
App.ActiveDocument.addObject("Part::Cylinder","C304")
App.ActiveDocument.C304.Radius=0.750000
App.ActiveDocument.C304.Height=15.00
App.ActiveDocument.C304.Angle=360.00 
App.ActiveDocument.C304.Placement=Base.Placement(Base.Vector(-12.375496,-116.970978,539.174765),Base.Rotation(-0.311044,0.178223,0.000000,0.933535))
App.ActiveDocument.addObject("Part::Cylinder","C305")
App.ActiveDocument.C305.Radius=0.750000
App.ActiveDocument.C305.Height=15.00
App.ActiveDocument.C305.Angle=360.00 
App.ActiveDocument.C305.Placement=Base.Placement(Base.Vector(-12.272914,-114.753352,537.184671),Base.Rotation(-0.359406,0.180738,0.000000,0.915511))
App.ActiveDocument.addObject("Part::Cylinder","C306")
App.ActiveDocument.C306.Radius=0.750000
App.ActiveDocument.C306.Height=15.00
App.ActiveDocument.C306.Angle=360.00 
App.ActiveDocument.C306.Placement=Base.Placement(Base.Vector(-12.521148,-112.706376,535.104528),Base.Rotation(-0.405837,0.181715,0.000000,0.895699))
App.ActiveDocument.addObject("Part::Cylinder","C307")
App.ActiveDocument.C307.Radius=0.750000
App.ActiveDocument.C307.Height=15.00
App.ActiveDocument.C307.Angle=360.00 
App.ActiveDocument.C307.Placement=Base.Placement(Base.Vector(-12.366021,-111.004511,532.752453),Base.Rotation(-0.448085,0.187009,0.000000,0.874213))
App.ActiveDocument.addObject("Part::Cylinder","C308")
App.ActiveDocument.C308.Radius=0.750000
App.ActiveDocument.C308.Height=15.00
App.ActiveDocument.C308.Angle=360.00 
App.ActiveDocument.C308.Placement=Base.Placement(Base.Vector(-12.336231,-109.462285,530.194974),Base.Rotation(-0.488276,0.192464,0.000000,0.851202))
App.ActiveDocument.addObject("Part::Cylinder","C309")
App.ActiveDocument.C309.Radius=0.750000
App.ActiveDocument.C309.Height=15.00
App.ActiveDocument.C309.Angle=360.00 
App.ActiveDocument.C309.Placement=Base.Placement(Base.Vector(-12.452142,-108.086745,527.442354),Base.Rotation(-0.524984,0.195531,0.000000,0.828348))
App.ActiveDocument.addObject("Part::Cylinder","C310")
App.ActiveDocument.C310.Radius=0.750000
App.ActiveDocument.C310.Height=15.00
App.ActiveDocument.C310.Angle=360.00 
App.ActiveDocument.C310.Placement=Base.Placement(Base.Vector(-12.306684,-107.067048,524.584984),Base.Rotation(-0.559640,0.202366,0.000000,0.803649))
App.ActiveDocument.addObject("Part::Cylinder","C311")
App.ActiveDocument.C311.Radius=0.750000
App.ActiveDocument.C311.Height=15.00
App.ActiveDocument.C311.Angle=360.00 
App.ActiveDocument.C311.Placement=Base.Placement(Base.Vector(-12.346642,-106.179411,521.482689),Base.Rotation(-0.588677,0.208661,0.000000,0.780974))
App.ActiveDocument.addObject("Part::Cylinder","C312")
App.ActiveDocument.C312.Radius=0.750000
App.ActiveDocument.C312.Height=15.00
App.ActiveDocument.C312.Angle=360.00 
App.ActiveDocument.C312.Placement=Base.Placement(Base.Vector(-12.517893,-105.528432,518.500176),Base.Rotation(-0.615807,0.214865,0.000000,0.758033))
App.ActiveDocument.addObject("Part::Cylinder","C313")
App.ActiveDocument.C313.Radius=0.750000
App.ActiveDocument.C313.Height=15.00
App.ActiveDocument.C313.Angle=360.00 
App.ActiveDocument.C313.Placement=Base.Placement(Base.Vector(-12.331393,-105.213686,515.404333),Base.Rotation(-0.637327,0.226490,0.000000,0.736557))
App.ActiveDocument.addObject("Part::Cylinder","C314")
App.ActiveDocument.C314.Radius=0.750000
App.ActiveDocument.C314.Height=15.00
App.ActiveDocument.C314.Angle=360.00 
App.ActiveDocument.C314.Placement=Base.Placement(Base.Vector(-12.504405,-104.984676,512.232721),Base.Rotation(-0.660833,0.232388,0.000000,0.713650))
App.ActiveDocument.addObject("Part::Cylinder","C315")
App.ActiveDocument.C315.Radius=0.750000
App.ActiveDocument.C315.Height=15.00
App.ActiveDocument.C315.Angle=360.00 
App.ActiveDocument.C315.Placement=Base.Placement(Base.Vector(-12.524105,-105.016507,509.068189),Base.Rotation(-0.679467,0.243992,0.000000,0.691948))
App.ActiveDocument.addObject("Part::Cylinder","C316")
App.ActiveDocument.C316.Radius=0.750000
App.ActiveDocument.C316.Height=15.00
App.ActiveDocument.C316.Angle=360.00 
App.ActiveDocument.C316.Placement=Base.Placement(Base.Vector(-12.778429,-105.171459,505.830855),Base.Rotation(-0.697376,0.252289,0.000000,0.670833))
App.ActiveDocument.addObject("Part::Cylinder","C317")
App.ActiveDocument.C317.Radius=0.750000
App.ActiveDocument.C317.Height=15.00
App.ActiveDocument.C317.Angle=360.00 
App.ActiveDocument.C317.Placement=Base.Placement(Base.Vector(-12.841550,-105.594338,502.602671),Base.Rotation(-0.711485,0.269399,0.000000,0.649009))
App.ActiveDocument.addObject("Part::Cylinder","C318")
App.ActiveDocument.C318.Radius=0.750000
App.ActiveDocument.C318.Height=15.00
App.ActiveDocument.C318.Angle=360.00 
App.ActiveDocument.C318.Placement=Base.Placement(Base.Vector(-12.965685,-106.191221,499.401898),Base.Rotation(-0.724121,0.283406,0.000000,0.628753))
App.ActiveDocument.addObject("Part::Cylinder","C319")
App.ActiveDocument.C319.Radius=0.750000
App.ActiveDocument.C319.Height=15.00
App.ActiveDocument.C319.Angle=360.00 
App.ActiveDocument.C319.Placement=Base.Placement(Base.Vector(-13.052462,-106.960012,496.351001),Base.Rotation(-0.734045,0.303954,0.000000,0.607281))
App.ActiveDocument.addObject("Part::Cylinder","C320")
App.ActiveDocument.C320.Radius=0.750000
App.ActiveDocument.C320.Height=15.00
App.ActiveDocument.C320.Angle=360.00 
App.ActiveDocument.C320.Placement=Base.Placement(Base.Vector(-13.283831,-107.890085,493.232491),Base.Rotation(-0.743741,0.323662,0.000000,0.584886))
App.ActiveDocument.addObject("Part::Cylinder","C321")
App.ActiveDocument.C321.Radius=0.750000
App.ActiveDocument.C321.Height=15.00
App.ActiveDocument.C321.Angle=360.00 
App.ActiveDocument.C321.Placement=Base.Placement(Base.Vector(-13.554193,-108.920293,490.332314),Base.Rotation(-0.747609,0.352026,0.000000,0.563168))
App.ActiveDocument.addObject("Part::Cylinder","C322")
App.ActiveDocument.C322.Radius=0.750000
App.ActiveDocument.C322.Height=15.00
App.ActiveDocument.C322.Angle=360.00 
App.ActiveDocument.C322.Placement=Base.Placement(Base.Vector(-13.676003,-110.233338,487.415110),Base.Rotation(-0.748527,0.383372,0.000000,0.541048))
App.ActiveDocument.addObject("Part::Cylinder","C323")
App.ActiveDocument.C323.Radius=0.750000
App.ActiveDocument.C323.Height=15.00
App.ActiveDocument.C323.Angle=360.00 
App.ActiveDocument.C323.Placement=Base.Placement(Base.Vector(-13.957471,-111.674123,484.545346),Base.Rotation(-0.749297,0.411253,0.000000,0.519062))
App.ActiveDocument.addObject("Part::Cylinder","C324")
App.ActiveDocument.C324.Radius=0.750000
App.ActiveDocument.C324.Height=15.00
App.ActiveDocument.C324.Angle=360.00 
App.ActiveDocument.C324.Placement=Base.Placement(Base.Vector(-14.339524,-113.208184,481.823904),Base.Rotation(-0.742625,0.451636,0.000000,0.494503))
App.ActiveDocument.addObject("Part::Cylinder","C325")
App.ActiveDocument.C325.Radius=0.750000
App.ActiveDocument.C325.Height=15.00
App.ActiveDocument.C325.Angle=360.00 
App.ActiveDocument.C325.Placement=Base.Placement(Base.Vector(-14.336630,-115.073155,479.347156),Base.Rotation(-0.726134,0.501490,0.000000,0.470359))
App.ActiveDocument.addObject("Part::Cylinder","C326")
App.ActiveDocument.C326.Radius=0.750000
App.ActiveDocument.C326.Height=15.00
App.ActiveDocument.C326.Angle=360.00 
App.ActiveDocument.C326.Placement=Base.Placement(Base.Vector(-14.904697,-116.872522,476.835436),Base.Rotation(-0.714010,0.539211,0.000000,0.446589))
App.ActiveDocument.addObject("Part::Cylinder","C327")
App.ActiveDocument.C327.Radius=0.750000
App.ActiveDocument.C327.Height=15.00
App.ActiveDocument.C327.Angle=360.00 
App.ActiveDocument.C327.Placement=Base.Placement(Base.Vector(-15.268569,-118.970958,474.524667),Base.Rotation(-0.685560,0.594811,0.000000,0.419771))
App.ActiveDocument.addObject("Part::Cylinder","C328")
App.ActiveDocument.C328.Radius=0.750000
App.ActiveDocument.C328.Height=15.00
App.ActiveDocument.C328.Angle=360.00 
App.ActiveDocument.C328.Placement=Base.Placement(Base.Vector(-16.150277,-121.031383,472.198229),Base.Rotation(-0.653287,0.648658,0.000000,0.390459))
App.ActiveDocument.addObject("Part::Cylinder","C329")
App.ActiveDocument.C329.Radius=0.750000
App.ActiveDocument.C329.Height=15.00
App.ActiveDocument.C329.Angle=360.00 
App.ActiveDocument.C329.Placement=Base.Placement(Base.Vector(-9.078257,-137.471247,544.984259),Base.Rotation(-0.031177,0.196748,0.000000,0.979958))
App.ActiveDocument.addObject("Part::Cylinder","C330")
App.ActiveDocument.C330.Radius=0.750000
App.ActiveDocument.C330.Height=15.00
App.ActiveDocument.C330.Angle=360.00 
App.ActiveDocument.C330.Placement=Base.Placement(Base.Vector(-9.314372,-134.124875,544.747971),Base.Rotation(-0.063511,0.194940,0.000000,0.978757))
App.ActiveDocument.addObject("Part::Cylinder","C331")
App.ActiveDocument.C331.Radius=0.750000
App.ActiveDocument.C331.Height=15.00
App.ActiveDocument.C331.Angle=360.00 
App.ActiveDocument.C331.Placement=Base.Placement(Base.Vector(-9.178845,-130.906495,544.131628),Base.Rotation(-0.099587,0.198421,0.000000,0.975044))
App.ActiveDocument.addObject("Part::Cylinder","C332")
App.ActiveDocument.C332.Radius=0.750000
App.ActiveDocument.C332.Height=15.00
App.ActiveDocument.C332.Angle=360.00 
App.ActiveDocument.C332.Placement=Base.Placement(Base.Vector(-9.068229,-127.777270,543.274091),Base.Rotation(-0.140097,0.202870,0.000000,0.969132))
App.ActiveDocument.addObject("Part::Cylinder","C333")
App.ActiveDocument.C333.Radius=0.750000
App.ActiveDocument.C333.Height=15.00
App.ActiveDocument.C333.Angle=360.00 
App.ActiveDocument.C333.Placement=Base.Placement(Base.Vector(-9.491483,-124.798775,542.407624),Base.Rotation(-0.181499,0.200348,0.000000,0.962766))
App.ActiveDocument.addObject("Part::Cylinder","C334")
App.ActiveDocument.C334.Radius=0.750000
App.ActiveDocument.C334.Height=15.00
App.ActiveDocument.C334.Angle=360.00 
App.ActiveDocument.C334.Placement=Base.Placement(Base.Vector(-9.151263,-122.111825,541.004056),Base.Rotation(-0.224480,0.206967,0.000000,0.952246))
App.ActiveDocument.addObject("Part::Cylinder","C335")
App.ActiveDocument.C335.Radius=0.750000
App.ActiveDocument.C335.Height=15.00
App.ActiveDocument.C335.Angle=360.00 
App.ActiveDocument.C335.Placement=Base.Placement(Base.Vector(-9.116447,-119.510664,539.445577),Base.Rotation(-0.271050,0.210771,0.000000,0.939206))
App.ActiveDocument.addObject("Part::Cylinder","C336")
App.ActiveDocument.C336.Radius=0.750000
App.ActiveDocument.C336.Height=15.00
App.ActiveDocument.C336.Angle=360.00 
App.ActiveDocument.C336.Placement=Base.Placement(Base.Vector(-9.240901,-117.142315,537.749187),Base.Rotation(-0.318135,0.213360,0.000000,0.923725))
App.ActiveDocument.addObject("Part::Cylinder","C337")
App.ActiveDocument.C337.Radius=0.750000
App.ActiveDocument.C337.Height=15.00
App.ActiveDocument.C337.Angle=360.00 
App.ActiveDocument.C337.Placement=Base.Placement(Base.Vector(-9.217339,-115.026616,535.776881),Base.Rotation(-0.364157,0.218088,0.000000,0.905443))
App.ActiveDocument.addObject("Part::Cylinder","C338")
App.ActiveDocument.C338.Radius=0.750000
App.ActiveDocument.C338.Height=15.00
App.ActiveDocument.C338.Angle=360.00 
App.ActiveDocument.C338.Placement=Base.Placement(Base.Vector(-9.366493,-113.126614,533.704968),Base.Rotation(-0.409206,0.221298,0.000000,0.885199))
App.ActiveDocument.addObject("Part::Cylinder","C339")
App.ActiveDocument.C339.Radius=0.750000
App.ActiveDocument.C339.Height=15.00
App.ActiveDocument.C339.Angle=360.00 
App.ActiveDocument.C339.Placement=Base.Placement(Base.Vector(-9.214024,-111.493561,531.288548),Base.Rotation(-0.448294,0.226453,0.000000,0.864726))
App.ActiveDocument.addObject("Part::Cylinder","C340")
App.ActiveDocument.C340.Radius=0.750000
App.ActiveDocument.C340.Height=15.00
App.ActiveDocument.C340.Angle=360.00 
App.ActiveDocument.C340.Placement=Base.Placement(Base.Vector(-9.249156,-110.026856,528.728067),Base.Rotation(-0.488300,0.228785,0.000000,0.842152))
App.ActiveDocument.addObject("Part::Cylinder","C341")
App.ActiveDocument.C341.Radius=0.750000
App.ActiveDocument.C341.Height=15.00
App.ActiveDocument.C341.Angle=360.00 
App.ActiveDocument.C341.Placement=Base.Placement(Base.Vector(-9.285675,-108.813733,526.052304),Base.Rotation(-0.526138,0.233891,0.000000,0.817603))
App.ActiveDocument.addObject("Part::Cylinder","C342")
App.ActiveDocument.C342.Radius=0.750000
App.ActiveDocument.C342.Height=15.00
App.ActiveDocument.C342.Angle=360.00 
App.ActiveDocument.C342.Placement=Base.Placement(Base.Vector(-9.199980,-107.848526,523.121501),Base.Rotation(-0.557589,0.242929,0.000000,0.793776))
App.ActiveDocument.addObject("Part::Cylinder","C343")
App.ActiveDocument.C343.Radius=0.750000
App.ActiveDocument.C343.Height=15.00
App.ActiveDocument.C343.Angle=360.00 
App.ActiveDocument.C343.Placement=Base.Placement(Base.Vector(-9.181618,-107.116398,520.148439),Base.Rotation(-0.587143,0.250518,0.000000,0.769743))
App.ActiveDocument.addObject("Part::Cylinder","C344")
App.ActiveDocument.C344.Radius=0.750000
App.ActiveDocument.C344.Height=15.00
App.ActiveDocument.C344.Angle=360.00 
App.ActiveDocument.C344.Placement=Base.Placement(Base.Vector(-9.234855,-106.592720,517.149283),Base.Rotation(-0.612708,0.257338,0.000000,0.747239))
App.ActiveDocument.addObject("Part::Cylinder","C345")
App.ActiveDocument.C345.Radius=0.750000
App.ActiveDocument.C345.Height=15.00
App.ActiveDocument.C345.Angle=360.00 
App.ActiveDocument.C345.Placement=Base.Placement(Base.Vector(-9.240492,-106.310966,514.062114),Base.Rotation(-0.634044,0.267831,0.000000,0.725434))
App.ActiveDocument.addObject("Part::Cylinder","C346")
App.ActiveDocument.C346.Radius=0.750000
App.ActiveDocument.C346.Height=15.00
App.ActiveDocument.C346.Angle=360.00 
App.ActiveDocument.C346.Placement=Base.Placement(Base.Vector(-9.385243,-106.186887,510.978826),Base.Rotation(-0.654745,0.278347,0.000000,0.702731))
App.ActiveDocument.addObject("Part::Cylinder","C347")
App.ActiveDocument.C347.Radius=0.750000
App.ActiveDocument.C347.Height=15.00
App.ActiveDocument.C347.Angle=360.00 
App.ActiveDocument.C347.Placement=Base.Placement(Base.Vector(-9.427168,-106.313920,507.868294),Base.Rotation(-0.671440,0.292169,0.000000,0.681032))
App.ActiveDocument.addObject("Part::Cylinder","C348")
App.ActiveDocument.C348.Radius=0.750000
App.ActiveDocument.C348.Height=15.00
App.ActiveDocument.C348.Angle=360.00 
App.ActiveDocument.C348.Placement=Base.Placement(Base.Vector(-9.633812,-106.575135,504.722583),Base.Rotation(-0.686618,0.306829,0.000000,0.659099))
App.ActiveDocument.addObject("Part::Cylinder","C349")
App.ActiveDocument.C349.Radius=0.750000
App.ActiveDocument.C349.Height=15.00
App.ActiveDocument.C349.Angle=360.00 
App.ActiveDocument.C349.Placement=Base.Placement(Base.Vector(-9.763695,-107.062582,501.641994),Base.Rotation(-0.698866,0.324493,0.000000,0.637409))
App.ActiveDocument.addObject("Part::Cylinder","C350")
App.ActiveDocument.C350.Radius=0.750000
App.ActiveDocument.C350.Height=15.00
App.ActiveDocument.C350.Angle=360.00 
App.ActiveDocument.C350.Placement=Base.Placement(Base.Vector(-9.961823,-107.697890,498.635862),Base.Rotation(-0.708253,0.345029,0.000000,0.615900))
App.ActiveDocument.addObject("Part::Cylinder","C351")
App.ActiveDocument.C351.Radius=0.750000
App.ActiveDocument.C351.Height=15.00
App.ActiveDocument.C351.Angle=360.00 
App.ActiveDocument.C351.Placement=Base.Placement(Base.Vector(-10.135795,-108.580293,495.521234),Base.Rotation(-0.714536,0.369817,0.000000,0.593864))
App.ActiveDocument.addObject("Part::Cylinder","C352")
App.ActiveDocument.C352.Radius=0.750000
App.ActiveDocument.C352.Height=15.00
App.ActiveDocument.C352.Angle=360.00 
App.ActiveDocument.C352.Placement=Base.Placement(Base.Vector(-10.402016,-109.594328,492.510935),Base.Rotation(-0.717959,0.397618,0.000000,0.571345))
App.ActiveDocument.addObject("Part::Cylinder","C353")
App.ActiveDocument.C353.Radius=0.750000
App.ActiveDocument.C353.Height=15.00
App.ActiveDocument.C353.Angle=360.00 
App.ActiveDocument.C353.Placement=Base.Placement(Base.Vector(-10.627106,-110.742663,489.726384),Base.Rotation(-0.717445,0.427175,0.000000,0.550268))
App.ActiveDocument.addObject("Part::Cylinder","C354")
App.ActiveDocument.C354.Radius=0.750000
App.ActiveDocument.C354.Height=15.00
App.ActiveDocument.C354.Angle=360.00 
App.ActiveDocument.C354.Placement=Base.Placement(Base.Vector(-10.866116,-112.114960,486.924075),Base.Rotation(-0.713108,0.461335,0.000000,0.527870))
App.ActiveDocument.addObject("Part::Cylinder","C355")
App.ActiveDocument.C355.Radius=0.750000
App.ActiveDocument.C355.Height=15.00
App.ActiveDocument.C355.Angle=360.00 
App.ActiveDocument.C355.Placement=Base.Placement(Base.Vector(-11.193874,-113.596467,484.238052),Base.Rotation(-0.707442,0.493601,0.000000,0.505850))
App.ActiveDocument.addObject("Part::Cylinder","C356")
App.ActiveDocument.C356.Radius=0.750000
App.ActiveDocument.C356.Height=15.00
App.ActiveDocument.C356.Angle=360.00 
App.ActiveDocument.C356.Placement=Base.Placement(Base.Vector(-11.386317,-115.239957,481.814532),Base.Rotation(-0.693090,0.535539,0.000000,0.482518))
App.ActiveDocument.addObject("Part::Cylinder","C357")
App.ActiveDocument.C357.Radius=0.750000
App.ActiveDocument.C357.Height=15.00
App.ActiveDocument.C357.Angle=360.00 
App.ActiveDocument.C357.Placement=Base.Placement(Base.Vector(-11.627717,-117.165256,479.356246),Base.Rotation(-0.670882,0.581986,0.000000,0.459575))
App.ActiveDocument.addObject("Part::Cylinder","C358")
App.ActiveDocument.C358.Radius=0.750000
App.ActiveDocument.C358.Height=15.00
App.ActiveDocument.C358.Angle=360.00 
App.ActiveDocument.C358.Placement=Base.Placement(Base.Vector(-12.181852,-119.005100,477.037474),Base.Rotation(-0.648670,0.623082,0.000000,0.437030))
App.ActiveDocument.addObject("Part::Cylinder","C359")
App.ActiveDocument.C359.Radius=0.750000
App.ActiveDocument.C359.Height=15.00
App.ActiveDocument.C359.Angle=360.00 
App.ActiveDocument.C359.Placement=Base.Placement(Base.Vector(-12.758384,-121.148346,474.758633),Base.Rotation(-0.609442,0.679277,0.000000,0.408855))
App.ActiveDocument.addObject("Part::Cylinder","C360")
App.ActiveDocument.C360.Radius=0.750000
App.ActiveDocument.C360.Height=15.00
App.ActiveDocument.C360.Angle=360.00 
App.ActiveDocument.C360.Placement=Base.Placement(Base.Vector(-13.744470,-123.239265,472.519902),Base.Rotation(-0.572497,0.724535,0.000000,0.383792))
App.ActiveDocument.addObject("Part::Cylinder","C361")
App.ActiveDocument.C361.Radius=0.750000
App.ActiveDocument.C361.Height=15.00
App.ActiveDocument.C361.Angle=360.00 
App.ActiveDocument.C361.Placement=Base.Placement(Base.Vector(-6.125184,-137.570509,543.631347),Base.Rotation(-0.030956,0.231298,0.000000,0.972390))
App.ActiveDocument.addObject("Part::Cylinder","C362")
App.ActiveDocument.C362.Radius=0.750000
App.ActiveDocument.C362.Height=15.00
App.ActiveDocument.C362.Angle=360.00 
App.ActiveDocument.C362.Placement=Base.Placement(Base.Vector(-6.324014,-134.263188,543.392986),Base.Rotation(-0.063981,0.230158,0.000000,0.971048))
App.ActiveDocument.addObject("Part::Cylinder","C363")
App.ActiveDocument.C363.Radius=0.750000
App.ActiveDocument.C363.Height=15.00
App.ActiveDocument.C363.Angle=360.00 
App.ActiveDocument.C363.Placement=Base.Placement(Base.Vector(-6.159981,-131.051909,542.734013),Base.Rotation(-0.099819,0.233599,0.000000,0.967196))
App.ActiveDocument.addObject("Part::Cylinder","C364")
App.ActiveDocument.C364.Radius=0.750000
App.ActiveDocument.C364.Height=15.00
App.ActiveDocument.C364.Angle=360.00 
App.ActiveDocument.C364.Placement=Base.Placement(Base.Vector(-6.113145,-127.978195,541.888233),Base.Rotation(-0.138577,0.235889,0.000000,0.961849))
App.ActiveDocument.addObject("Part::Cylinder","C365")
App.ActiveDocument.C365.Radius=0.750000
App.ActiveDocument.C365.Height=15.00
App.ActiveDocument.C365.Angle=360.00 
App.ActiveDocument.C365.Placement=Base.Placement(Base.Vector(-6.499448,-125.066386,541.030949),Base.Rotation(-0.180566,0.233480,0.000000,0.955449))
App.ActiveDocument.addObject("Part::Cylinder","C366")
App.ActiveDocument.C366.Radius=0.750000
App.ActiveDocument.C366.Height=15.00
App.ActiveDocument.C366.Angle=360.00 
App.ActiveDocument.C366.Placement=Base.Placement(Base.Vector(-6.160224,-122.399175,539.557428),Base.Rotation(-0.226687,0.242855,0.000000,0.943204))
App.ActiveDocument.addObject("Part::Cylinder","C367")
App.ActiveDocument.C367.Radius=0.750000
App.ActiveDocument.C367.Height=15.00
App.ActiveDocument.C367.Angle=360.00 
App.ActiveDocument.C367.Placement=Base.Placement(Base.Vector(-6.139089,-119.854517,537.971139),Base.Rotation(-0.273932,0.247139,0.000000,0.929454))
App.ActiveDocument.addObject("Part::Cylinder","C368")
App.ActiveDocument.C368.Radius=0.750000
App.ActiveDocument.C368.Height=15.00
App.ActiveDocument.C368.Angle=360.00 
App.ActiveDocument.C368.Placement=Base.Placement(Base.Vector(-6.284385,-117.520425,536.243713),Base.Rotation(-0.320960,0.249114,0.000000,0.913743))
App.ActiveDocument.addObject("Part::Cylinder","C369")
App.ActiveDocument.C369.Radius=0.750000
App.ActiveDocument.C369.Height=15.00
App.ActiveDocument.C369.Angle=360.00 
App.ActiveDocument.C369.Placement=Base.Placement(Base.Vector(-6.212470,-115.493954,534.215867),Base.Rotation(-0.366844,0.256026,0.000000,0.894358))
App.ActiveDocument.addObject("Part::Cylinder","C370")
App.ActiveDocument.C370.Radius=0.750000
App.ActiveDocument.C370.Height=15.00
App.ActiveDocument.C370.Angle=360.00 
App.ActiveDocument.C370.Placement=Base.Placement(Base.Vector(-6.289095,-113.646283,532.030165),Base.Rotation(-0.411252,0.258953,0.000000,0.873965))
App.ActiveDocument.addObject("Part::Cylinder","C371")
App.ActiveDocument.C371.Radius=0.750000
App.ActiveDocument.C371.Height=15.00
App.ActiveDocument.C371.Angle=360.00 
App.ActiveDocument.C371.Placement=Base.Placement(Base.Vector(-6.114781,-112.131638,529.565598),Base.Rotation(-0.451134,0.267002,0.000000,0.851579))
App.ActiveDocument.addObject("Part::Cylinder","C372")
App.ActiveDocument.C372.Radius=0.750000
App.ActiveDocument.C372.Height=15.00
App.ActiveDocument.C372.Angle=360.00 
App.ActiveDocument.C372.Placement=Base.Placement(Base.Vector(-6.296767,-110.731397,527.072330),Base.Rotation(-0.489126,0.270451,0.000000,0.829224))
App.ActiveDocument.addObject("Part::Cylinder","C373")
App.ActiveDocument.C373.Radius=0.750000
App.ActiveDocument.C373.Height=15.00
App.ActiveDocument.C373.Angle=360.00 
App.ActiveDocument.C373.Placement=Base.Placement(Base.Vector(-6.187019,-109.708520,524.405481),Base.Rotation(-0.523193,0.279039,0.000000,0.805237))
App.ActiveDocument.addObject("Part::Cylinder","C374")
App.ActiveDocument.C374.Radius=0.750000
App.ActiveDocument.C374.Height=15.00
App.ActiveDocument.C374.Angle=360.00 
App.ActiveDocument.C374.Placement=Base.Placement(Base.Vector(-6.149948,-108.858436,521.534855),Base.Rotation(-0.555407,0.289070,0.000000,0.779719))
App.ActiveDocument.addObject("Part::Cylinder","C375")
App.ActiveDocument.C375.Radius=0.750000
App.ActiveDocument.C375.Height=15.00
App.ActiveDocument.C375.Angle=360.00 
App.ActiveDocument.C375.Placement=Base.Placement(Base.Vector(-6.115322,-108.256664,518.604903),Base.Rotation(-0.582657,0.295158,0.000000,0.757227))
App.ActiveDocument.addObject("Part::Cylinder","C376")
App.ActiveDocument.C376.Radius=0.750000
App.ActiveDocument.C376.Height=15.00
App.ActiveDocument.C376.Angle=360.00 
App.ActiveDocument.C376.Placement=Base.Placement(Base.Vector(-6.210512,-107.821725,515.611246),Base.Rotation(-0.604951,0.305370,0.000000,0.735380))
App.ActiveDocument.addObject("Part::Cylinder","C377")
App.ActiveDocument.C377.Radius=0.750000
App.ActiveDocument.C377.Height=15.00
App.ActiveDocument.C377.Angle=360.00 
App.ActiveDocument.C377.Placement=Base.Placement(Base.Vector(-6.211359,-107.666384,512.552141),Base.Rotation(-0.626873,0.317832,0.000000,0.711346))
App.ActiveDocument.addObject("Part::Cylinder","C378")
App.ActiveDocument.C378.Radius=0.750000
App.ActiveDocument.C378.Height=15.00
App.ActiveDocument.C378.Angle=360.00 
App.ActiveDocument.C378.Placement=Base.Placement(Base.Vector(-6.349182,-107.664031,509.481757),Base.Rotation(-0.643234,0.335022,0.000000,0.688484))
App.ActiveDocument.addObject("Part::Cylinder","C379")
App.ActiveDocument.C379.Radius=0.750000
App.ActiveDocument.C379.Height=15.00
App.ActiveDocument.C379.Angle=360.00 
App.ActiveDocument.C379.Placement=Base.Placement(Base.Vector(-6.517284,-107.858603,506.447477),Base.Rotation(-0.657542,0.353781,0.000000,0.665190))
App.ActiveDocument.addObject("Part::Cylinder","C380")
App.ActiveDocument.C380.Radius=0.750000
App.ActiveDocument.C380.Height=15.00
App.ActiveDocument.C380.Angle=360.00 
App.ActiveDocument.C380.Placement=Base.Placement(Base.Vector(-6.681299,-108.259694,503.432812),Base.Rotation(-0.668583,0.371721,0.000000,0.644066))
App.ActiveDocument.addObject("Part::Cylinder","C381")
App.ActiveDocument.C381.Radius=0.750000
App.ActiveDocument.C381.Height=15.00
App.ActiveDocument.C381.Angle=360.00 
App.ActiveDocument.C381.Placement=Base.Placement(Base.Vector(-6.921460,-108.824130,500.420492),Base.Rotation(-0.677268,0.392868,0.000000,0.622063))
App.ActiveDocument.addObject("Part::Cylinder","C382")
App.ActiveDocument.C382.Radius=0.750000
App.ActiveDocument.C382.Height=15.00
App.ActiveDocument.C382.Angle=360.00 
App.ActiveDocument.C382.Placement=Base.Placement(Base.Vector(-7.178704,-109.540459,497.548075),Base.Rotation(-0.683133,0.414582,0.000000,0.601208))
App.ActiveDocument.addObject("Part::Cylinder","C383")
App.ActiveDocument.C383.Radius=0.750000
App.ActiveDocument.C383.Height=15.00
App.ActiveDocument.C383.Angle=360.00 
App.ActiveDocument.C383.Placement=Base.Placement(Base.Vector(-7.355184,-110.509237,494.670543),Base.Rotation(-0.683127,0.444184,0.000000,0.579688))
App.ActiveDocument.addObject("Part::Cylinder","C384")
App.ActiveDocument.C384.Radius=0.750000
App.ActiveDocument.C384.Height=15.00
App.ActiveDocument.C384.Angle=360.00 
App.ActiveDocument.C384.Placement=Base.Placement(Base.Vector(-7.619124,-111.649752,491.766521),Base.Rotation(-0.682965,0.472611,0.000000,0.556954))
App.ActiveDocument.addObject("Part::Cylinder","C385")
App.ActiveDocument.C385.Radius=0.750000
App.ActiveDocument.C385.Height=15.00
App.ActiveDocument.C385.Angle=360.00 
App.ActiveDocument.C385.Placement=Base.Placement(Base.Vector(-7.798882,-112.993320,489.045789),Base.Rotation(-0.675779,0.505337,0.000000,0.536616))
App.ActiveDocument.addObject("Part::Cylinder","C386")
App.ActiveDocument.C386.Radius=0.750000
App.ActiveDocument.C386.Height=15.00
App.ActiveDocument.C386.Angle=360.00 
App.ActiveDocument.C386.Placement=Base.Placement(Base.Vector(-8.228118,-114.358020,486.377243),Base.Rotation(-0.670642,0.533706,0.000000,0.515168))
App.ActiveDocument.addObject("Part::Cylinder","C387")
App.ActiveDocument.C387.Radius=0.750000
App.ActiveDocument.C387.Height=15.00
App.ActiveDocument.C387.Angle=360.00 
App.ActiveDocument.C387.Placement=Base.Placement(Base.Vector(-8.446694,-115.939809,483.982536),Base.Rotation(-0.653026,0.575446,0.000000,0.492360))
App.ActiveDocument.addObject("Part::Cylinder","C388")
App.ActiveDocument.C388.Radius=0.750000
App.ActiveDocument.C388.Height=15.00
App.ActiveDocument.C388.Angle=360.00 
App.ActiveDocument.C388.Placement=Base.Placement(Base.Vector(-8.694239,-117.682867,481.689722),Base.Rotation(-0.630723,0.615924,0.000000,0.472045))
App.ActiveDocument.addObject("Part::Cylinder","C389")
App.ActiveDocument.C389.Radius=0.750000
App.ActiveDocument.C389.Height=15.00
App.ActiveDocument.C389.Angle=360.00 
App.ActiveDocument.C389.Placement=Base.Placement(Base.Vector(-9.078406,-119.632241,479.367971),Base.Rotation(-0.602926,0.659034,0.000000,0.449616))
App.ActiveDocument.addObject("Part::Cylinder","C390")
App.ActiveDocument.C390.Radius=0.750000
App.ActiveDocument.C390.Height=15.00
App.ActiveDocument.C390.Angle=360.00 
App.ActiveDocument.C390.Placement=Base.Placement(Base.Vector(-9.772674,-121.500088,477.131791),Base.Rotation(-0.577395,0.696307,0.000000,0.426347))
App.ActiveDocument.addObject("Part::Cylinder","C391")
App.ActiveDocument.C391.Radius=0.750000
App.ActiveDocument.C391.Height=15.00
App.ActiveDocument.C391.Angle=360.00 
App.ActiveDocument.C391.Placement=Base.Placement(Base.Vector(-10.340039,-123.737453,475.046668),Base.Rotation(-0.534119,0.743000,0.000000,0.403322))
App.ActiveDocument.addObject("Part::Cylinder","C392")
App.ActiveDocument.C392.Radius=0.750000
App.ActiveDocument.C392.Height=15.00
App.ActiveDocument.C392.Angle=360.00 
App.ActiveDocument.C392.Placement=Base.Placement(Base.Vector(-11.629708,-125.793375,472.775591),Base.Rotation(-0.488907,0.787871,0.000000,0.374472))
App.ActiveDocument.addObject("Part::Cylinder","C393")
App.ActiveDocument.C393.Radius=0.750000
App.ActiveDocument.C393.Height=15.00
App.ActiveDocument.C393.Angle=360.00 
App.ActiveDocument.C393.Placement=Base.Placement(Base.Vector(-3.277657,-137.562475,542.061320),Base.Rotation(-0.031611,0.267693,0.000000,0.962985))
App.ActiveDocument.addObject("Part::Cylinder","C394")
App.ActiveDocument.C394.Radius=0.750000
App.ActiveDocument.C394.Height=15.00
App.ActiveDocument.C394.Angle=360.00 
App.ActiveDocument.C394.Placement=Base.Placement(Base.Vector(-3.445647,-134.267162,541.806280),Base.Rotation(-0.064854,0.265888,0.000000,0.961820))
App.ActiveDocument.addObject("Part::Cylinder","C395")
App.ActiveDocument.C395.Radius=0.750000
App.ActiveDocument.C395.Height=15.00
App.ActiveDocument.C395.Angle=360.00 
App.ActiveDocument.C395.Placement=Base.Placement(Base.Vector(-3.289392,-131.136680,541.120401),Base.Rotation(-0.101502,0.270667,0.000000,0.957307))
App.ActiveDocument.addObject("Part::Cylinder","C396")
App.ActiveDocument.C396.Radius=0.750000
App.ActiveDocument.C396.Height=15.00
App.ActiveDocument.C396.Angle=360.00 
App.ActiveDocument.C396.Placement=Base.Placement(Base.Vector(-3.296403,-128.001844,540.237645),Base.Rotation(-0.143517,0.274583,0.000000,0.950793))
App.ActiveDocument.addObject("Part::Cylinder","C397")
App.ActiveDocument.C397.Radius=0.750000
App.ActiveDocument.C397.Height=15.00
App.ActiveDocument.C397.Angle=360.00 
App.ActiveDocument.C397.Placement=Base.Placement(Base.Vector(-3.575169,-125.189089,539.326729),Base.Rotation(-0.184492,0.275059,0.000000,0.943560))
App.ActiveDocument.addObject("Part::Cylinder","C398")
App.ActiveDocument.C398.Radius=0.750000
App.ActiveDocument.C398.Height=15.00
App.ActiveDocument.C398.Angle=360.00 
App.ActiveDocument.C398.Placement=Base.Placement(Base.Vector(-3.310554,-122.663261,537.857869),Base.Rotation(-0.228627,0.283561,0.000000,0.931302))
App.ActiveDocument.addObject("Part::Cylinder","C399")
App.ActiveDocument.C399.Radius=0.750000
App.ActiveDocument.C399.Height=15.00
App.ActiveDocument.C399.Angle=360.00 
App.ActiveDocument.C399.Placement=Base.Placement(Base.Vector(-3.280165,-120.190440,536.214155),Base.Rotation(-0.274486,0.289462,0.000000,0.916989))
App.ActiveDocument.addObject("Part::Cylinder","C400")
App.ActiveDocument.C400.Radius=0.750000
App.ActiveDocument.C400.Height=15.00
App.ActiveDocument.C400.Angle=360.00 
App.ActiveDocument.C400.Placement=Base.Placement(Base.Vector(-3.473761,-117.941886,534.499756),Base.Rotation(-0.322385,0.288255,0.000000,0.901652))
App.ActiveDocument.addObject("Part::Cylinder","C401")
App.ActiveDocument.C401.Radius=0.750000
App.ActiveDocument.C401.Height=15.00
App.ActiveDocument.C401.Angle=360.00 
App.ActiveDocument.C401.Placement=Base.Placement(Base.Vector(-3.389631,-116.032973,532.433392),Base.Rotation(-0.367589,0.296875,0.000000,0.881331))
App.ActiveDocument.addObject("Part::Cylinder","C402")
App.ActiveDocument.C402.Radius=0.750000
App.ActiveDocument.C402.Height=15.00
App.ActiveDocument.C402.Angle=360.00 
App.ActiveDocument.C402.Placement=Base.Placement(Base.Vector(-3.295667,-114.381725,530.181447),Base.Rotation(-0.409033,0.304122,0.000000,0.860350))
App.ActiveDocument.addObject("Part::Cylinder","C403")
App.ActiveDocument.C403.Radius=0.750000
App.ActiveDocument.C403.Height=15.00
App.ActiveDocument.C403.Angle=360.00 
App.ActiveDocument.C403.Placement=Base.Placement(Base.Vector(-3.279623,-112.922557,527.739771),Base.Rotation(-0.450499,0.311265,0.000000,0.836758))
App.ActiveDocument.addObject("Part::Cylinder","C404")
App.ActiveDocument.C404.Radius=0.750000
App.ActiveDocument.C404.Height=15.00
App.ActiveDocument.C404.Angle=360.00 
App.ActiveDocument.C404.Placement=Base.Placement(Base.Vector(-3.379710,-111.662054,525.207913),Base.Rotation(-0.486520,0.316959,0.000000,0.814147))
App.ActiveDocument.addObject("Part::Cylinder","C405")
App.ActiveDocument.C405.Radius=0.750000
App.ActiveDocument.C405.Height=15.00
App.ActiveDocument.C405.Angle=360.00 
App.ActiveDocument.C405.Placement=Base.Placement(Base.Vector(-3.210638,-110.796954,522.471629),Base.Rotation(-0.517368,0.326781,0.000000,0.790914))
App.ActiveDocument.addObject("Part::Cylinder","C406")
App.ActiveDocument.C406.Radius=0.750000
App.ActiveDocument.C406.Height=15.00
App.ActiveDocument.C406.Angle=360.00 
App.ActiveDocument.C406.Placement=Base.Placement(Base.Vector(-3.229389,-110.081285,519.706951),Base.Rotation(-0.547267,0.336207,0.000000,0.766462))
App.ActiveDocument.addObject("Part::Cylinder","C407")
App.ActiveDocument.C407.Radius=0.750000
App.ActiveDocument.C407.Height=15.00
App.ActiveDocument.C407.Angle=360.00 
App.ActiveDocument.C407.Placement=Base.Placement(Base.Vector(-3.332297,-109.542622,516.798214),Base.Rotation(-0.573134,0.348184,0.000000,0.741812))
App.ActiveDocument.addObject("Part::Cylinder","C408")
App.ActiveDocument.C408.Radius=0.750000
App.ActiveDocument.C408.Height=15.00
App.ActiveDocument.C408.Angle=360.00 
App.ActiveDocument.C408.Placement=Base.Placement(Base.Vector(-3.435813,-109.254409,513.994110),Base.Rotation(-0.592725,0.361822,0.000000,0.719557))
App.ActiveDocument.addObject("Part::Cylinder","C409")
App.ActiveDocument.C409.Radius=0.750000
App.ActiveDocument.C409.Height=15.00
App.ActiveDocument.C409.Angle=360.00 
App.ActiveDocument.C409.Placement=Base.Placement(Base.Vector(-3.481132,-109.220911,510.988951),Base.Rotation(-0.608502,0.381803,0.000000,0.695666))
App.ActiveDocument.addObject("Part::Cylinder","C410")
App.ActiveDocument.C410.Radius=0.750000
App.ActiveDocument.C410.Height=15.00
App.ActiveDocument.C410.Angle=360.00 
App.ActiveDocument.C410.Placement=Base.Placement(Base.Vector(-3.634046,-109.359368,507.941792),Base.Rotation(-0.623067,0.400548,0.000000,0.671825))
App.ActiveDocument.addObject("Part::Cylinder","C411")
App.ActiveDocument.C411.Radius=0.750000
App.ActiveDocument.C411.Height=15.00
App.ActiveDocument.C411.Angle=360.00 
App.ActiveDocument.C411.Placement=Base.Placement(Base.Vector(-3.786752,-109.708020,505.000946),Base.Rotation(-0.634507,0.418583,0.000000,0.649761))
App.ActiveDocument.addObject("Part::Cylinder","C412")
App.ActiveDocument.C412.Radius=0.750000
App.ActiveDocument.C412.Height=15.00
App.ActiveDocument.C412.Angle=360.00 
App.ActiveDocument.C412.Placement=Base.Placement(Base.Vector(-3.991418,-110.267967,501.933439),Base.Rotation(-0.642286,0.441941,0.000000,0.626224))
App.ActiveDocument.addObject("Part::Cylinder","C413")
App.ActiveDocument.C413.Radius=0.750000
App.ActiveDocument.C413.Height=15.00
App.ActiveDocument.C413.Angle=360.00 
App.ActiveDocument.C413.Placement=Base.Placement(Base.Vector(-4.268178,-110.986033,498.953032),Base.Rotation(-0.647737,0.463771,0.000000,0.604445))
App.ActiveDocument.addObject("Part::Cylinder","C414")
App.ActiveDocument.C414.Radius=0.750000
App.ActiveDocument.C414.Height=15.00
App.ActiveDocument.C414.Angle=360.00 
App.ActiveDocument.C414.Placement=Base.Placement(Base.Vector(-4.528621,-111.840728,496.210524),Base.Rotation(-0.646427,0.490492,0.000000,0.584423))
App.ActiveDocument.addObject("Part::Cylinder","C415")
App.ActiveDocument.C415.Radius=0.750000
App.ActiveDocument.C415.Height=15.00
App.ActiveDocument.C415.Angle=360.00 
App.ActiveDocument.C415.Placement=Base.Placement(Base.Vector(-4.743589,-112.917549,493.524596),Base.Rotation(-0.642201,0.520192,0.000000,0.563008))
App.ActiveDocument.addObject("Part::Cylinder","C416")
App.ActiveDocument.C416.Radius=0.750000
App.ActiveDocument.C416.Height=15.00
App.ActiveDocument.C416.Angle=360.00 
App.ActiveDocument.C416.Placement=Base.Placement(Base.Vector(-4.931013,-114.177420,490.945432),Base.Rotation(-0.633122,0.551598,0.000000,0.543044))
App.ActiveDocument.addObject("Part::Cylinder","C417")
App.ActiveDocument.C417.Radius=0.750000
App.ActiveDocument.C417.Height=15.00
App.ActiveDocument.C417.Angle=360.00 
App.ActiveDocument.C417.Placement=Base.Placement(Base.Vector(-5.315519,-115.526508,488.334395),Base.Rotation(-0.623723,0.582342,0.000000,0.521389))
App.ActiveDocument.addObject("Part::Cylinder","C418")
App.ActiveDocument.C418.Radius=0.750000
App.ActiveDocument.C418.Height=15.00
App.ActiveDocument.C418.Angle=360.00 
App.ActiveDocument.C418.Placement=Base.Placement(Base.Vector(-5.551668,-117.003711,486.058356),Base.Rotation(-0.605078,0.618073,0.000000,0.501863))
App.ActiveDocument.addObject("Part::Cylinder","C419")
App.ActiveDocument.C419.Radius=0.750000
App.ActiveDocument.C419.Height=15.00
App.ActiveDocument.C419.Angle=360.00 
App.ActiveDocument.C419.Placement=Base.Placement(Base.Vector(-5.871346,-118.709397,483.724244),Base.Rotation(-0.585673,0.651946,0.000000,0.481616))
App.ActiveDocument.addObject("Part::Cylinder","C420")
App.ActiveDocument.C420.Radius=0.750000
App.ActiveDocument.C420.Height=15.00
App.ActiveDocument.C420.Angle=360.00 
App.ActiveDocument.C420.Placement=Base.Placement(Base.Vector(-6.210080,-120.527412,481.562685),Base.Rotation(-0.560303,0.687944,0.000000,0.461296))
App.ActiveDocument.addObject("Part::Cylinder","C421")
App.ActiveDocument.C421.Radius=0.750000
App.ActiveDocument.C421.Height=15.00
App.ActiveDocument.C421.Angle=360.00 
App.ActiveDocument.C421.Placement=Base.Placement(Base.Vector(-6.743418,-122.562278,479.309479),Base.Rotation(-0.527293,0.727370,0.000000,0.439199))
App.ActiveDocument.addObject("Part::Cylinder","C422")
App.ActiveDocument.C422.Radius=0.750000
App.ActiveDocument.C422.Height=15.00
App.ActiveDocument.C422.Angle=360.00 
App.ActiveDocument.C422.Placement=Base.Placement(Base.Vector(-7.411573,-124.489280,477.292558),Base.Rotation(-0.500100,0.757778,0.000000,0.419133))
App.ActiveDocument.addObject("Part::Cylinder","C423")
App.ActiveDocument.C423.Radius=0.750000
App.ActiveDocument.C423.Height=15.00
App.ActiveDocument.C423.Angle=360.00 
App.ActiveDocument.C423.Placement=Base.Placement(Base.Vector(-8.248409,-126.639281,475.264669),Base.Rotation(-0.455652,0.797602,0.000000,0.395237))
App.ActiveDocument.addObject("Part::Cylinder","C424")
App.ActiveDocument.C424.Radius=0.750000
App.ActiveDocument.C424.Height=15.00
App.ActiveDocument.C424.Angle=360.00 
App.ActiveDocument.C424.Placement=Base.Placement(Base.Vector(-9.755333,-128.582309,473.045284),Base.Rotation(-0.412951,0.833855,0.000000,0.366275))
App.ActiveDocument.addObject("Part::Cylinder","C425")
App.ActiveDocument.C425.Radius=0.750000
App.ActiveDocument.C425.Height=15.00
App.ActiveDocument.C425.Angle=360.00 
App.ActiveDocument.C425.Placement=Base.Placement(Base.Vector(-0.537883,-137.603248,540.260352),Base.Rotation(-0.031271,0.306474,0.000000,0.951365))
App.ActiveDocument.addObject("Part::Cylinder","C426")
App.ActiveDocument.C426.Radius=0.750000
App.ActiveDocument.C426.Height=15.00
App.ActiveDocument.C426.Angle=360.00 
App.ActiveDocument.C426.Placement=Base.Placement(Base.Vector(-0.773343,-134.391075,540.063524),Base.Rotation(-0.065657,0.305285,0.000000,0.949995))
App.ActiveDocument.addObject("Part::Cylinder","C427")
App.ActiveDocument.C427.Radius=0.750000
App.ActiveDocument.C427.Height=15.00
App.ActiveDocument.C427.Angle=360.00 
App.ActiveDocument.C427.Placement=Base.Placement(Base.Vector(-0.640842,-131.209190,539.334813),Base.Rotation(-0.103159,0.309910,0.000000,0.945153))
App.ActiveDocument.addObject("Part::Cylinder","C428")
App.ActiveDocument.C428.Radius=0.750000
App.ActiveDocument.C428.Height=15.00
App.ActiveDocument.C428.Angle=360.00 
App.ActiveDocument.C428.Placement=Base.Placement(Base.Vector(-0.608571,-128.143859,538.386456),Base.Rotation(-0.145072,0.313913,0.000000,0.938303))
App.ActiveDocument.addObject("Part::Cylinder","C429")
App.ActiveDocument.C429.Radius=0.750000
App.ActiveDocument.C429.Height=15.00
App.ActiveDocument.C429.Angle=360.00 
App.ActiveDocument.C429.Placement=Base.Placement(Base.Vector(-0.844724,-125.329133,537.399436),Base.Rotation(-0.188367,0.315067,0.000000,0.930189))
App.ActiveDocument.addObject("Part::Cylinder","C430")
App.ActiveDocument.C430.Radius=0.750000
App.ActiveDocument.C430.Height=15.00
App.ActiveDocument.C430.Angle=360.00 
App.ActiveDocument.C430.Placement=Base.Placement(Base.Vector(-0.576640,-122.913070,535.848798),Base.Rotation(-0.230493,0.324539,0.000000,0.917359))
App.ActiveDocument.addObject("Part::Cylinder","C431")
App.ActiveDocument.C431.Radius=0.750000
App.ActiveDocument.C431.Height=15.00
App.ActiveDocument.C431.Angle=360.00 
App.ActiveDocument.C431.Placement=Base.Placement(Base.Vector(-0.638535,-120.530956,534.215568),Base.Rotation(-0.278719,0.328492,0.000000,0.902446))
App.ActiveDocument.addObject("Part::Cylinder","C432")
App.ActiveDocument.C432.Radius=0.750000
App.ActiveDocument.C432.Height=15.00
App.ActiveDocument.C432.Angle=360.00 
App.ActiveDocument.C432.Placement=Base.Placement(Base.Vector(-0.794145,-118.394028,532.438428),Base.Rotation(-0.325638,0.333798,0.000000,0.884612))
App.ActiveDocument.addObject("Part::Cylinder","C433")
App.ActiveDocument.C433.Radius=0.750000
App.ActiveDocument.C433.Height=15.00
App.ActiveDocument.C433.Angle=360.00 
App.ActiveDocument.C433.Placement=Base.Placement(Base.Vector(-0.667259,-116.695144,530.361246),Base.Rotation(-0.366816,0.344184,0.000000,0.864282))
App.ActiveDocument.addObject("Part::Cylinder","C434")
App.ActiveDocument.C434.Radius=0.750000
App.ActiveDocument.C434.Height=15.00
App.ActiveDocument.C434.Angle=360.00 
App.ActiveDocument.C434.Placement=Base.Placement(Base.Vector(-0.583524,-115.181213,528.069542),Base.Rotation(-0.406636,0.350721,0.000000,0.843589))
App.ActiveDocument.addObject("Part::Cylinder","C435")
App.ActiveDocument.C435.Radius=0.750000
App.ActiveDocument.C435.Height=15.00
App.ActiveDocument.C435.Angle=360.00 
App.ActiveDocument.C435.Placement=Base.Placement(Base.Vector(-0.656872,-113.840390,525.690201),Base.Rotation(-0.448531,0.359052,0.000000,0.818476))
App.ActiveDocument.addObject("Part::Cylinder","C436")
App.ActiveDocument.C436.Radius=0.750000
App.ActiveDocument.C436.Height=15.00
App.ActiveDocument.C436.Angle=360.00 
App.ActiveDocument.C436.Placement=Base.Placement(Base.Vector(-0.629924,-112.791811,523.079820),Base.Rotation(-0.481525,0.368796,0.000000,0.795062))
App.ActiveDocument.addObject("Part::Cylinder","C437")
App.ActiveDocument.C437.Radius=0.750000
App.ActiveDocument.C437.Height=15.00
App.ActiveDocument.C437.Angle=360.00 
App.ActiveDocument.C437.Placement=Base.Placement(Base.Vector(-0.605587,-111.993147,520.281495),Base.Rotation(-0.509503,0.385133,0.000000,0.769467))
App.ActiveDocument.addObject("Part::Cylinder","C438")
App.ActiveDocument.C438.Radius=0.750000
App.ActiveDocument.C438.Height=15.00
App.ActiveDocument.C438.Angle=360.00 
App.ActiveDocument.C438.Placement=Base.Placement(Base.Vector(-0.638565,-111.450338,517.545870),Base.Rotation(-0.531438,0.398408,0.000000,0.747559))
App.ActiveDocument.addObject("Part::Cylinder","C439")
App.ActiveDocument.C439.Radius=0.750000
App.ActiveDocument.C439.Height=15.00
App.ActiveDocument.C439.Angle=360.00 
App.ActiveDocument.C439.Placement=Base.Placement(Base.Vector(-0.707541,-111.124445,514.709979),Base.Rotation(-0.555741,0.412825,0.000000,0.721614))
App.ActiveDocument.addObject("Part::Cylinder","C440")
App.ActiveDocument.C440.Radius=0.750000
App.ActiveDocument.C440.Height=15.00
App.ActiveDocument.C440.Angle=360.00 
App.ActiveDocument.C440.Placement=Base.Placement(Base.Vector(-0.810550,-111.013193,511.998277),Base.Rotation(-0.571914,0.428998,0.000000,0.699196))
App.ActiveDocument.addObject("Part::Cylinder","C441")
App.ActiveDocument.C441.Radius=0.750000
App.ActiveDocument.C441.Height=15.00
App.ActiveDocument.C441.Angle=360.00 
App.ActiveDocument.C441.Placement=Base.Placement(Base.Vector(-0.981089,-111.079398,509.152396),Base.Rotation(-0.584740,0.447503,0.000000,0.676624))
App.ActiveDocument.addObject("Part::Cylinder","C442")
App.ActiveDocument.C442.Radius=0.750000
App.ActiveDocument.C442.Height=15.00
App.ActiveDocument.C442.Angle=360.00 
App.ActiveDocument.C442.Placement=Base.Placement(Base.Vector(-1.101456,-111.413972,506.261054),Base.Rotation(-0.592647,0.471428,0.000000,0.653089))
App.ActiveDocument.addObject("Part::Cylinder","C443")
App.ActiveDocument.C443.Radius=0.750000
App.ActiveDocument.C443.Height=15.00
App.ActiveDocument.C443.Angle=360.00 
App.ActiveDocument.C443.Placement=Base.Placement(Base.Vector(-1.345505,-111.874998,503.353943),Base.Rotation(-0.600397,0.490389,0.000000,0.631698))
App.ActiveDocument.addObject("Part::Cylinder","C444")
App.ActiveDocument.C444.Radius=0.750000
App.ActiveDocument.C444.Height=15.00
App.ActiveDocument.C444.Angle=360.00 
App.ActiveDocument.C444.Placement=Base.Placement(Base.Vector(-1.575724,-112.583831,500.438780),Base.Rotation(-0.602456,0.515053,0.000000,0.609727))
App.ActiveDocument.addObject("Part::Cylinder","C445")
App.ActiveDocument.C445.Radius=0.750000
App.ActiveDocument.C445.Height=15.00
App.ActiveDocument.C445.Angle=360.00 
App.ActiveDocument.C445.Placement=Base.Placement(Base.Vector(-1.835843,-113.413645,497.731063),Base.Rotation(-0.601115,0.541310,0.000000,0.587915))
App.ActiveDocument.addObject("Part::Cylinder","C446")
App.ActiveDocument.C446.Radius=0.750000
App.ActiveDocument.C446.Height=15.00
App.ActiveDocument.C446.Angle=360.00 
App.ActiveDocument.C446.Placement=Base.Placement(Base.Vector(-2.037960,-114.472777,495.115643),Base.Rotation(-0.595164,0.567655,0.000000,0.568813))
App.ActiveDocument.addObject("Part::Cylinder","C447")
App.ActiveDocument.C447.Radius=0.750000
App.ActiveDocument.C447.Height=15.00
App.ActiveDocument.C447.Angle=360.00 
App.ActiveDocument.C447.Placement=Base.Placement(Base.Vector(-2.248713,-115.713203,492.571640),Base.Rotation(-0.582854,0.598665,0.000000,0.549438))
App.ActiveDocument.addObject("Part::Cylinder","C448")
App.ActiveDocument.C448.Radius=0.750000
App.ActiveDocument.C448.Height=15.00
App.ActiveDocument.C448.Angle=360.00 
App.ActiveDocument.C448.Placement=Base.Placement(Base.Vector(-2.617318,-117.043142,490.013330),Base.Rotation(-0.574591,0.624150,0.000000,0.529417))
App.ActiveDocument.addObject("Part::Cylinder","C449")
App.ActiveDocument.C449.Radius=0.750000
App.ActiveDocument.C449.Height=15.00
App.ActiveDocument.C449.Angle=360.00 
App.ActiveDocument.C449.Placement=Base.Placement(Base.Vector(-2.881531,-118.593775,487.656443),Base.Rotation(-0.558607,0.653945,0.000000,0.510210))
App.ActiveDocument.addObject("Part::Cylinder","C450")
App.ActiveDocument.C450.Radius=0.750000
App.ActiveDocument.C450.Height=15.00
App.ActiveDocument.C450.Angle=360.00 
App.ActiveDocument.C450.Placement=Base.Placement(Base.Vector(-3.205391,-120.166522,485.502931),Base.Rotation(-0.537594,0.685834,0.000000,0.490535))
App.ActiveDocument.addObject("Part::Cylinder","C451")
App.ActiveDocument.C451.Radius=0.750000
App.ActiveDocument.C451.Height=15.00
App.ActiveDocument.C451.Angle=360.00 
App.ActiveDocument.C451.Placement=Base.Placement(Base.Vector(-3.480066,-121.963341,483.467017),Base.Rotation(-0.508545,0.720090,0.000000,0.472074))
App.ActiveDocument.addObject("Part::Cylinder","C452")
App.ActiveDocument.C452.Radius=0.750000
App.ActiveDocument.C452.Height=15.00
App.ActiveDocument.C452.Angle=360.00 
App.ActiveDocument.C452.Placement=Base.Placement(Base.Vector(-3.981499,-123.822280,481.379392),Base.Rotation(-0.480829,0.751236,0.000000,0.452158))
App.ActiveDocument.addObject("Part::Cylinder","C453")
App.ActiveDocument.C453.Radius=0.750000
App.ActiveDocument.C453.Height=15.00
App.ActiveDocument.C453.Angle=360.00 
App.ActiveDocument.C453.Placement=Base.Placement(Base.Vector(-4.592371,-125.830500,479.339372),Base.Rotation(-0.452294,0.779991,0.000000,0.432486))
App.ActiveDocument.addObject("Part::Cylinder","C454")
App.ActiveDocument.C454.Radius=0.750000
App.ActiveDocument.C454.Height=15.00
App.ActiveDocument.C454.Angle=360.00 
App.ActiveDocument.C454.Placement=Base.Placement(Base.Vector(-5.316589,-127.762369,477.485356),Base.Rotation(-0.420961,0.807807,0.000000,0.412601))
App.ActiveDocument.addObject("Part::Cylinder","C455")
App.ActiveDocument.C455.Radius=0.750000
App.ActiveDocument.C455.Height=15.00
App.ActiveDocument.C455.Angle=360.00 
App.ActiveDocument.C455.Placement=Base.Placement(Base.Vector(-6.467235,-129.837378,475.408635),Base.Rotation(-0.381217,0.839911,0.000000,0.386294))
App.ActiveDocument.addObject("Part::Cylinder","C456")
App.ActiveDocument.C456.Radius=0.750000
App.ActiveDocument.C456.Height=15.00
App.ActiveDocument.C456.Angle=360.00 
App.ActiveDocument.C456.Placement=Base.Placement(Base.Vector(-8.193296,-131.584181,473.241735),Base.Rotation(-0.345834,0.867122,0.000000,0.358467))
App.ActiveDocument.addObject("Part::Cylinder","C457")
App.ActiveDocument.C457.Radius=0.750000
App.ActiveDocument.C457.Height=15.00
App.ActiveDocument.C457.Angle=360.00 
App.ActiveDocument.C457.Placement=Base.Placement(Base.Vector(1.943356,-137.641040,538.308152),Base.Rotation(-0.032832,0.347271,0.000000,0.937190))
App.ActiveDocument.addObject("Part::Cylinder","C458")
App.ActiveDocument.C458.Radius=0.750000
App.ActiveDocument.C458.Height=15.00
App.ActiveDocument.C458.Angle=360.00 
App.ActiveDocument.C458.Placement=Base.Placement(Base.Vector(1.683290,-134.408238,538.136388),Base.Rotation(-0.066580,0.345275,0.000000,0.936137))
App.ActiveDocument.addObject("Part::Cylinder","C459")
App.ActiveDocument.C459.Radius=0.750000
App.ActiveDocument.C459.Height=15.00
App.ActiveDocument.C459.Angle=360.00 
App.ActiveDocument.C459.Placement=Base.Placement(Base.Vector(1.829088,-131.223465,537.320819),Base.Rotation(-0.106086,0.352170,0.000000,0.929904))
App.ActiveDocument.addObject("Part::Cylinder","C460")
App.ActiveDocument.C460.Radius=0.750000
App.ActiveDocument.C460.Height=15.00
App.ActiveDocument.C460.Angle=360.00 
App.ActiveDocument.C460.Placement=Base.Placement(Base.Vector(1.854833,-128.206746,536.306151),Base.Rotation(-0.149066,0.356927,0.000000,0.922162))
App.ActiveDocument.addObject("Part::Cylinder","C461")
App.ActiveDocument.C461.Radius=0.750000
App.ActiveDocument.C461.Height=15.00
App.ActiveDocument.C461.Angle=360.00 
App.ActiveDocument.C461.Placement=Base.Placement(Base.Vector(1.685913,-125.511700,535.239301),Base.Rotation(-0.196001,0.361313,0.000000,0.911612))
App.ActiveDocument.addObject("Part::Cylinder","C462")
App.ActiveDocument.C462.Radius=0.750000
App.ActiveDocument.C462.Height=15.00
App.ActiveDocument.C462.Angle=360.00 
App.ActiveDocument.C462.Placement=Base.Placement(Base.Vector(1.845524,-123.037990,533.571864),Base.Rotation(-0.236287,0.369851,0.000000,0.898543))
App.ActiveDocument.addObject("Part::Cylinder","C463")
App.ActiveDocument.C463.Radius=0.750000
App.ActiveDocument.C463.Height=15.00
App.ActiveDocument.C463.Angle=360.00 
App.ActiveDocument.C463.Placement=Base.Placement(Base.Vector(1.754027,-120.809664,531.907364),Base.Rotation(-0.285974,0.376600,0.000000,0.881130))
App.ActiveDocument.addObject("Part::Cylinder","C464")
App.ActiveDocument.C464.Radius=0.750000
App.ActiveDocument.C464.Height=15.00
App.ActiveDocument.C464.Angle=360.00 
App.ActiveDocument.C464.Placement=Base.Placement(Base.Vector(1.750560,-118.957109,530.039991),Base.Rotation(-0.326980,0.384523,0.000000,0.863265))
App.ActiveDocument.addObject("Part::Cylinder","C465")
App.ActiveDocument.C465.Radius=0.750000
App.ActiveDocument.C465.Height=15.00
App.ActiveDocument.C465.Angle=360.00 
App.ActiveDocument.C465.Placement=Base.Placement(Base.Vector(1.797366,-117.428472,528.000421),Base.Rotation(-0.364764,0.395509,0.000000,0.842923))
App.ActiveDocument.addObject("Part::Cylinder","C466")
App.ActiveDocument.C466.Radius=0.750000
App.ActiveDocument.C466.Height=15.00
App.ActiveDocument.C466.Angle=360.00 
App.ActiveDocument.C466.Placement=Base.Placement(Base.Vector(1.796622,-116.052479,525.712591),Base.Rotation(-0.403331,0.404919,0.000000,0.820588))
App.ActiveDocument.addObject("Part::Cylinder","C467")
App.ActiveDocument.C467.Radius=0.750000
App.ActiveDocument.C467.Height=15.00
App.ActiveDocument.C467.Angle=360.00 
App.ActiveDocument.C467.Placement=Base.Placement(Base.Vector(1.793405,-114.950215,523.303526),Base.Rotation(-0.437955,0.418081,0.000000,0.795867))
App.ActiveDocument.addObject("Part::Cylinder","C468")
App.ActiveDocument.C468.Radius=0.750000
App.ActiveDocument.C468.Height=15.00
App.ActiveDocument.C468.Angle=360.00 
App.ActiveDocument.C468.Placement=Base.Placement(Base.Vector(1.793647,-114.106863,520.734396),Base.Rotation(-0.466818,0.432241,0.000000,0.771523))
App.ActiveDocument.addObject("Part::Cylinder","C469")
App.ActiveDocument.C469.Radius=0.750000
App.ActiveDocument.C469.Height=15.00
App.ActiveDocument.C469.Angle=360.00 
App.ActiveDocument.C469.Placement=Base.Placement(Base.Vector(1.831672,-113.564261,518.038016),Base.Rotation(-0.488801,0.450118,0.000000,0.747307))
App.ActiveDocument.addObject("Part::Cylinder","C470")
App.ActiveDocument.C470.Radius=0.750000
App.ActiveDocument.C470.Height=15.00
App.ActiveDocument.C470.Angle=360.00 
App.ActiveDocument.C470.Placement=Base.Placement(Base.Vector(1.739217,-113.184225,515.387485),Base.Rotation(-0.511935,0.463059,0.000000,0.723532))
App.ActiveDocument.addObject("Part::Cylinder","C471")
App.ActiveDocument.C471.Radius=0.750000
App.ActiveDocument.C471.Height=15.00
App.ActiveDocument.C471.Angle=360.00 
App.ActiveDocument.C471.Placement=Base.Placement(Base.Vector(1.648638,-113.046421,512.671581),Base.Rotation(-0.525501,0.482343,0.000000,0.700852))
App.ActiveDocument.addObject("Part::Cylinder","C472")
App.ActiveDocument.C472.Radius=0.750000
App.ActiveDocument.C472.Height=15.00
App.ActiveDocument.C472.Angle=360.00 
App.ActiveDocument.C472.Placement=Base.Placement(Base.Vector(1.531566,-113.111323,510.016730),Base.Rotation(-0.538375,0.499693,0.000000,0.678572))
App.ActiveDocument.addObject("Part::Cylinder","C473")
App.ActiveDocument.C473.Radius=0.750000
App.ActiveDocument.C473.Height=15.00
App.ActiveDocument.C473.Angle=360.00 
App.ActiveDocument.C473.Placement=Base.Placement(Base.Vector(1.314730,-113.310806,507.290672),Base.Rotation(-0.546835,0.518050,0.000000,0.657720))
App.ActiveDocument.addObject("Part::Cylinder","C474")
App.ActiveDocument.C474.Radius=0.750000
App.ActiveDocument.C474.Height=15.00
App.ActiveDocument.C474.Angle=360.00 
App.ActiveDocument.C474.Placement=Base.Placement(Base.Vector(1.121012,-113.757246,504.551993),Base.Rotation(-0.549921,0.543483,0.000000,0.634203))
App.ActiveDocument.addObject("Part::Cylinder","C475")
App.ActiveDocument.C475.Radius=0.750000
App.ActiveDocument.C475.Height=15.00
App.ActiveDocument.C475.Angle=360.00 
App.ActiveDocument.C475.Placement=Base.Placement(Base.Vector(0.914428,-114.424499,501.788874),Base.Rotation(-0.551573,0.564050,0.000000,0.614504))
App.ActiveDocument.addObject("Part::Cylinder","C476")
App.ActiveDocument.C476.Radius=0.750000
App.ActiveDocument.C476.Height=15.00
App.ActiveDocument.C476.Angle=360.00 
App.ActiveDocument.C476.Placement=Base.Placement(Base.Vector(0.666296,-115.304252,498.983006),Base.Rotation(-0.549941,0.585236,0.000000,0.595872))
App.ActiveDocument.addObject("Part::Cylinder","C477")
App.ActiveDocument.C477.Radius=0.750000
App.ActiveDocument.C477.Height=15.00
App.ActiveDocument.C477.Angle=360.00 
App.ActiveDocument.C477.Placement=Base.Placement(Base.Vector(0.462061,-116.335134,496.471177),Base.Rotation(-0.543884,0.612480,0.000000,0.573636))
App.ActiveDocument.addObject("Part::Cylinder","C478")
App.ActiveDocument.C478.Radius=0.750000
App.ActiveDocument.C478.Height=15.00
App.ActiveDocument.C478.Angle=360.00 
App.ActiveDocument.C478.Placement=Base.Placement(Base.Vector(0.244497,-117.569454,493.984090),Base.Rotation(-0.532546,0.639398,0.000000,0.554585))
App.ActiveDocument.addObject("Part::Cylinder","C479")
App.ActiveDocument.C479.Radius=0.750000
App.ActiveDocument.C479.Height=15.00
App.ActiveDocument.C479.Angle=360.00 
App.ActiveDocument.C479.Placement=Base.Placement(Base.Vector(-0.176338,-118.807781,491.494738),Base.Rotation(-0.520154,0.665653,0.000000,0.535113))
App.ActiveDocument.addObject("Part::Cylinder","C480")
App.ActiveDocument.C480.Radius=0.750000
App.ActiveDocument.C480.Height=15.00
App.ActiveDocument.C480.Angle=360.00 
App.ActiveDocument.C480.Placement=Base.Placement(Base.Vector(-0.488571,-120.273086,489.218107),Base.Rotation(-0.504703,0.691028,0.000000,0.517451))
App.ActiveDocument.addObject("Part::Cylinder","C481")
App.ActiveDocument.C481.Radius=0.750000
App.ActiveDocument.C481.Height=15.00
App.ActiveDocument.C481.Angle=360.00 
App.ActiveDocument.C481.Placement=Base.Placement(Base.Vector(-0.730008,-121.971709,487.096752),Base.Rotation(-0.484584,0.717914,0.000000,0.499778))
App.ActiveDocument.addObject("Part::Cylinder","C482")
App.ActiveDocument.C482.Radius=0.750000
App.ActiveDocument.C482.Height=15.00
App.ActiveDocument.C482.Angle=360.00 
App.ActiveDocument.C482.Placement=Base.Placement(Base.Vector(-1.056488,-123.695005,485.107929),Base.Rotation(-0.456898,0.748325,0.000000,0.480889))
App.ActiveDocument.addObject("Part::Cylinder","C483")
App.ActiveDocument.C483.Radius=0.750000
App.ActiveDocument.C483.Height=15.00
App.ActiveDocument.C483.Angle=360.00 
App.ActiveDocument.C483.Placement=Base.Placement(Base.Vector(-1.422084,-125.578734,483.195355),Base.Rotation(-0.430011,0.774814,0.000000,0.463414))
App.ActiveDocument.addObject("Part::Cylinder","C484")
App.ActiveDocument.C484.Radius=0.750000
App.ActiveDocument.C484.Height=15.00
App.ActiveDocument.C484.Angle=360.00 
App.ActiveDocument.C484.Placement=Base.Placement(Base.Vector(-2.028905,-127.522498,481.197308),Base.Rotation(-0.404541,0.798165,0.000000,0.446408))
App.ActiveDocument.addObject("Part::Cylinder","C485")
App.ActiveDocument.C485.Radius=0.750000
App.ActiveDocument.C485.Height=15.00
App.ActiveDocument.C485.Angle=360.00 
App.ActiveDocument.C485.Placement=Base.Placement(Base.Vector(-2.679584,-129.443552,479.406213),Base.Rotation(-0.369471,0.824732,0.000000,0.428144))
App.ActiveDocument.addObject("Part::Cylinder","C486")
App.ActiveDocument.C486.Radius=0.750000
App.ActiveDocument.C486.Height=15.00
App.ActiveDocument.C486.Angle=360.00 
App.ActiveDocument.C486.Placement=Base.Placement(Base.Vector(-3.732888,-131.243826,477.469622),Base.Rotation(-0.343912,0.847187,0.000000,0.404968))
App.ActiveDocument.addObject("Part::Cylinder","C487")
App.ActiveDocument.C487.Radius=0.750000
App.ActiveDocument.C487.Height=15.00
App.ActiveDocument.C487.Angle=360.00 
App.ActiveDocument.C487.Placement=Base.Placement(Base.Vector(-5.015692,-133.244724,475.480654),Base.Rotation(-0.307686,0.872398,0.000000,0.379804))
App.ActiveDocument.addObject("Part::Cylinder","C488")
App.ActiveDocument.C488.Radius=0.750000
App.ActiveDocument.C488.Height=15.00
App.ActiveDocument.C488.Angle=360.00 
App.ActiveDocument.C488.Placement=Base.Placement(Base.Vector(-6.930798,-134.883042,473.329574),Base.Rotation(-0.273177,0.897166,0.000000,0.347083))
App.ActiveDocument.addObject("Part::Cylinder","C489")
App.ActiveDocument.C489.Radius=0.750000
App.ActiveDocument.C489.Height=15.00
App.ActiveDocument.C489.Angle=360.00 
App.ActiveDocument.C489.Placement=Base.Placement(Base.Vector(4.141859,-137.644720,536.222270),Base.Rotation(-0.033470,0.392501,0.000000,0.919142))
App.ActiveDocument.addObject("Part::Cylinder","C490")
App.ActiveDocument.C490.Radius=0.750000
App.ActiveDocument.C490.Height=15.00
App.ActiveDocument.C490.Angle=360.00 
App.ActiveDocument.C490.Placement=Base.Placement(Base.Vector(3.942641,-134.354177,535.987200),Base.Rotation(-0.068542,0.390718,0.000000,0.917955))
App.ActiveDocument.addObject("Part::Cylinder","C491")
App.ActiveDocument.C491.Radius=0.750000
App.ActiveDocument.C491.Height=15.00
App.ActiveDocument.C491.Angle=360.00 
App.ActiveDocument.C491.Placement=Base.Placement(Base.Vector(4.061110,-131.261436,535.118616),Base.Rotation(-0.108154,0.397810,0.000000,0.911071))
App.ActiveDocument.addObject("Part::Cylinder","C492")
App.ActiveDocument.C492.Radius=0.750000
App.ActiveDocument.C492.Height=15.00
App.ActiveDocument.C492.Angle=360.00 
App.ActiveDocument.C492.Placement=Base.Placement(Base.Vector(4.024383,-128.336443,534.092886),Base.Rotation(-0.150084,0.403291,0.000000,0.902680))
App.ActiveDocument.addObject("Part::Cylinder","C493")
App.ActiveDocument.C493.Radius=0.750000
App.ActiveDocument.C493.Height=15.00
App.ActiveDocument.C493.Angle=360.00 
App.ActiveDocument.C493.Placement=Base.Placement(Base.Vector(3.930208,-125.727562,532.886645),Base.Rotation(-0.194527,0.408701,0.000000,0.891697))
App.ActiveDocument.addObject("Part::Cylinder","C494")
App.ActiveDocument.C494.Radius=0.750000
App.ActiveDocument.C494.Height=15.00
App.ActiveDocument.C494.Angle=360.00 
App.ActiveDocument.C494.Placement=Base.Placement(Base.Vector(3.966478,-123.380642,531.237402),Base.Rotation(-0.240900,0.419945,0.000000,0.874993))
App.ActiveDocument.addObject("Part::Cylinder","C495")
App.ActiveDocument.C495.Radius=0.750000
App.ActiveDocument.C495.Height=15.00
App.ActiveDocument.C495.Angle=360.00 
App.ActiveDocument.C495.Placement=Base.Placement(Base.Vector(3.960526,-121.332333,529.405425),Base.Rotation(-0.282553,0.428822,0.000000,0.858065))
App.ActiveDocument.addObject("Part::Cylinder","C496")
App.ActiveDocument.C496.Radius=0.750000
App.ActiveDocument.C496.Height=15.00
App.ActiveDocument.C496.Angle=360.00 
App.ActiveDocument.C496.Placement=Base.Placement(Base.Vector(4.036679,-119.694299,527.357099),Base.Rotation(-0.320937,0.444961,0.000000,0.836068))
App.ActiveDocument.addObject("Part::Cylinder","C497")
App.ActiveDocument.C497.Radius=0.750000
App.ActiveDocument.C497.Height=15.00
App.ActiveDocument.C497.Angle=360.00 
App.ActiveDocument.C497.Placement=Base.Placement(Base.Vector(4.015207,-118.276659,525.202513),Base.Rotation(-0.360667,0.454244,0.000000,0.814605))
App.ActiveDocument.addObject("Part::Cylinder","C498")
App.ActiveDocument.C498.Radius=0.750000
App.ActiveDocument.C498.Height=15.00
App.ActiveDocument.C498.Angle=360.00 
App.ActiveDocument.C498.Placement=Base.Placement(Base.Vector(3.958073,-117.100107,522.906238),Base.Rotation(-0.391563,0.468729,0.000000,0.791816))
App.ActiveDocument.addObject("Part::Cylinder","C499")
App.ActiveDocument.C499.Radius=0.750000
App.ActiveDocument.C499.Height=15.00
App.ActiveDocument.C499.Angle=360.00 
App.ActiveDocument.C499.Placement=Base.Placement(Base.Vector(3.992249,-116.319190,520.496297),Base.Rotation(-0.417738,0.484230,0.000000,0.768776))
App.ActiveDocument.addObject("Part::Cylinder","C500")
App.ActiveDocument.C500.Radius=0.750000
App.ActiveDocument.C500.Height=15.00
App.ActiveDocument.C500.Angle=360.00 
App.ActiveDocument.C500.Placement=Base.Placement(Base.Vector(3.919403,-115.688394,518.039570),Base.Rotation(-0.442351,0.499577,0.000000,0.744815))
App.ActiveDocument.addObject("Part::Cylinder","C501")
App.ActiveDocument.C501.Radius=0.750000
App.ActiveDocument.C501.Height=15.00
App.ActiveDocument.C501.Angle=360.00 
App.ActiveDocument.C501.Placement=Base.Placement(Base.Vector(3.891109,-115.357608,515.363804),Base.Rotation(-0.459057,0.517840,0.000000,0.721878))
App.ActiveDocument.addObject("Part::Cylinder","C502")
App.ActiveDocument.C502.Radius=0.750000
App.ActiveDocument.C502.Height=15.00
App.ActiveDocument.C502.Angle=360.00 
App.ActiveDocument.C502.Placement=Base.Placement(Base.Vector(3.727533,-115.143653,512.752809),Base.Rotation(-0.476469,0.535419,0.000000,0.697355))
App.ActiveDocument.addObject("Part::Cylinder","C503")
App.ActiveDocument.C503.Radius=0.750000
App.ActiveDocument.C503.Height=15.00
App.ActiveDocument.C503.Angle=360.00 
App.ActiveDocument.C503.Placement=Base.Placement(Base.Vector(3.677023,-115.298768,510.155685),Base.Rotation(-0.486707,0.551179,0.000000,0.677730))
App.ActiveDocument.addObject("Part::Cylinder","C504")
App.ActiveDocument.C504.Radius=0.750000
App.ActiveDocument.C504.Height=15.00
App.ActiveDocument.C504.Angle=360.00 
App.ActiveDocument.C504.Placement=Base.Placement(Base.Vector(3.504307,-115.541999,507.572401),Base.Rotation(-0.495727,0.567812,0.000000,0.657149))
App.ActiveDocument.addObject("Part::Cylinder","C505")
App.ActiveDocument.C505.Radius=0.750000
App.ActiveDocument.C505.Height=15.00
App.ActiveDocument.C505.Angle=360.00 
App.ActiveDocument.C505.Placement=Base.Placement(Base.Vector(3.284353,-115.895289,505.174217),Base.Rotation(-0.499123,0.588097,0.000000,0.636410))
App.ActiveDocument.addObject("Part::Cylinder","C506")
App.ActiveDocument.C506.Radius=0.750000
App.ActiveDocument.C506.Height=15.00
App.ActiveDocument.C506.Angle=360.00 
App.ActiveDocument.C506.Placement=Base.Placement(Base.Vector(3.117320,-116.580343,502.574363),Base.Rotation(-0.496963,0.610983,0.000000,0.616220))
App.ActiveDocument.addObject("Part::Cylinder","C507")
App.ActiveDocument.C507.Radius=0.750000
App.ActiveDocument.C507.Height=15.00
App.ActiveDocument.C507.Angle=360.00 
App.ActiveDocument.C507.Placement=Base.Placement(Base.Vector(2.845609,-117.394838,499.929324),Base.Rotation(-0.494831,0.630762,0.000000,0.597730))
App.ActiveDocument.addObject("Part::Cylinder","C508")
App.ActiveDocument.C508.Radius=0.750000
App.ActiveDocument.C508.Height=15.00
App.ActiveDocument.C508.Angle=360.00 
App.ActiveDocument.C508.Placement=Base.Placement(Base.Vector(2.652099,-118.484390,497.423830),Base.Rotation(-0.486986,0.654333,0.000000,0.578526))
App.ActiveDocument.addObject("Part::Cylinder","C509")
App.ActiveDocument.C509.Radius=0.750000
App.ActiveDocument.C509.Height=15.00
App.ActiveDocument.C509.Angle=360.00 
App.ActiveDocument.C509.Placement=Base.Placement(Base.Vector(2.408520,-119.626250,495.122084),Base.Rotation(-0.476215,0.677011,0.000000,0.561138))
App.ActiveDocument.addObject("Part::Cylinder","C510")
App.ActiveDocument.C510.Radius=0.750000
App.ActiveDocument.C510.Height=15.00
App.ActiveDocument.C510.Angle=360.00 
App.ActiveDocument.C510.Placement=Base.Placement(Base.Vector(2.097334,-120.908880,492.822584),Base.Rotation(-0.460959,0.701832,0.000000,0.543092))
App.ActiveDocument.addObject("Part::Cylinder","C511")
App.ActiveDocument.C511.Radius=0.750000
App.ActiveDocument.C511.Height=15.00
App.ActiveDocument.C511.Angle=360.00 
App.ActiveDocument.C511.Placement=Base.Placement(Base.Vector(1.673605,-122.344382,490.453164),Base.Rotation(-0.446163,0.725287,0.000000,0.524307))
App.ActiveDocument.addObject("Part::Cylinder","C512")
App.ActiveDocument.C512.Radius=0.750000
App.ActiveDocument.C512.Height=15.00
App.ActiveDocument.C512.Angle=360.00 
App.ActiveDocument.C512.Placement=Base.Placement(Base.Vector(1.294810,-123.953331,488.288760),Base.Rotation(-0.425030,0.749501,0.000000,0.507542))
App.ActiveDocument.addObject("Part::Cylinder","C513")
App.ActiveDocument.C513.Radius=0.750000
App.ActiveDocument.C513.Height=15.00
App.ActiveDocument.C513.Angle=360.00 
App.ActiveDocument.C513.Placement=Base.Placement(Base.Vector(1.041408,-125.698112,486.466305),Base.Rotation(-0.399789,0.773116,0.000000,0.492403))
App.ActiveDocument.addObject("Part::Cylinder","C514")
App.ActiveDocument.C514.Radius=0.750000
App.ActiveDocument.C514.Height=15.00
App.ActiveDocument.C514.Angle=360.00 
App.ActiveDocument.C514.Placement=Base.Placement(Base.Vector(0.711966,-127.504214,484.719971),Base.Rotation(-0.371449,0.796276,0.000000,0.477462))
App.ActiveDocument.addObject("Part::Cylinder","C515")
App.ActiveDocument.C515.Radius=0.750000
App.ActiveDocument.C515.Height=15.00
App.ActiveDocument.C515.Angle=360.00 
App.ActiveDocument.C515.Placement=Base.Placement(Base.Vector(0.150939,-129.379562,482.842198),Base.Rotation(-0.341427,0.819335,0.000000,0.460562))
App.ActiveDocument.addObject("Part::Cylinder","C516")
App.ActiveDocument.C516.Radius=0.750000
App.ActiveDocument.C516.Height=15.00
App.ActiveDocument.C516.Angle=360.00 
App.ActiveDocument.C516.Placement=Base.Placement(Base.Vector(-0.390279,-131.422451,481.134431),Base.Rotation(-0.307511,0.841879,0.000000,0.443482))
App.ActiveDocument.addObject("Part::Cylinder","C517")
App.ActiveDocument.C517.Radius=0.750000
App.ActiveDocument.C517.Height=15.00
App.ActiveDocument.C517.Angle=360.00 
App.ActiveDocument.C517.Placement=Base.Placement(Base.Vector(-1.435693,-133.295921,479.131474),Base.Rotation(-0.271715,0.864142,0.000000,0.423591))
App.ActiveDocument.addObject("Part::Cylinder","C518")
App.ActiveDocument.C518.Radius=0.750000
App.ActiveDocument.C518.Height=15.00
App.ActiveDocument.C518.Angle=360.00 
App.ActiveDocument.C518.Placement=Base.Placement(Base.Vector(-2.584138,-135.131636,477.276183),Base.Rotation(-0.237104,0.884099,0.000000,0.402679))
App.ActiveDocument.addObject("Part::Cylinder","C519")
App.ActiveDocument.C519.Radius=0.750000
App.ActiveDocument.C519.Height=15.00
App.ActiveDocument.C519.Angle=360.00 
App.ActiveDocument.C519.Placement=Base.Placement(Base.Vector(-4.182564,-136.726580,475.287198),Base.Rotation(-0.206097,0.902969,0.000000,0.377056))
App.ActiveDocument.addObject("Part::Cylinder","C520")
App.ActiveDocument.C520.Radius=0.750000
App.ActiveDocument.C520.Height=15.00
App.ActiveDocument.C520.Angle=360.00 
App.ActiveDocument.C520.Placement=Base.Placement(Base.Vector(-6.209912,-138.151414,473.232413),Base.Rotation(-0.170359,0.924028,0.000000,0.342272))
App.ActiveDocument.addObject("Part::Cylinder","C521")
App.ActiveDocument.C521.Radius=0.750000
App.ActiveDocument.C521.Height=15.00
App.ActiveDocument.C521.Angle=360.00 
App.ActiveDocument.C521.Placement=Base.Placement(Base.Vector(6.069374,-137.675494,533.997681),Base.Rotation(-0.033102,0.438810,0.000000,0.897970))
App.ActiveDocument.addObject("Part::Cylinder","C522")
App.ActiveDocument.C522.Radius=0.750000
App.ActiveDocument.C522.Height=15.00
App.ActiveDocument.C522.Angle=360.00 
App.ActiveDocument.C522.Placement=Base.Placement(Base.Vector(5.909898,-134.454272,533.720272),Base.Rotation(-0.069544,0.439645,0.000000,0.895475))
App.ActiveDocument.addObject("Part::Cylinder","C523")
App.ActiveDocument.C523.Radius=0.750000
App.ActiveDocument.C523.Height=15.00
App.ActiveDocument.C523.Angle=360.00 
App.ActiveDocument.C523.Placement=Base.Placement(Base.Vector(5.982617,-131.383449,532.799588),Base.Rotation(-0.109749,0.446300,0.000000,0.888128))
App.ActiveDocument.addObject("Part::Cylinder","C524")
App.ActiveDocument.C524.Radius=0.750000
App.ActiveDocument.C524.Height=15.00
App.ActiveDocument.C524.Angle=360.00 
App.ActiveDocument.C524.Placement=Base.Placement(Base.Vector(5.929897,-128.525015,531.698224),Base.Rotation(-0.153433,0.453752,0.000000,0.877820))
App.ActiveDocument.addObject("Part::Cylinder","C525")
App.ActiveDocument.C525.Radius=0.750000
App.ActiveDocument.C525.Height=15.00
App.ActiveDocument.C525.Angle=360.00 
App.ActiveDocument.C525.Placement=Base.Placement(Base.Vector(5.848605,-125.997902,530.356942),Base.Rotation(-0.194121,0.462609,0.000000,0.865049))
App.ActiveDocument.addObject("Part::Cylinder","C526")
App.ActiveDocument.C526.Radius=0.750000
App.ActiveDocument.C526.Height=15.00
App.ActiveDocument.C526.Angle=360.00 
App.ActiveDocument.C526.Placement=Base.Placement(Base.Vector(5.866451,-123.834780,528.608904),Base.Rotation(-0.238122,0.474748,0.000000,0.847297))
App.ActiveDocument.addObject("Part::Cylinder","C527")
App.ActiveDocument.C527.Radius=0.750000
App.ActiveDocument.C527.Height=15.00
App.ActiveDocument.C527.Angle=360.00 
App.ActiveDocument.C527.Placement=Base.Placement(Base.Vector(5.908441,-122.088999,526.676119),Base.Rotation(-0.275005,0.490725,0.000000,0.826778))
App.ActiveDocument.addObject("Part::Cylinder","C528")
App.ActiveDocument.C528.Radius=0.750000
App.ActiveDocument.C528.Height=15.00
App.ActiveDocument.C528.Angle=360.00 
App.ActiveDocument.C528.Placement=Base.Placement(Base.Vector(5.887864,-120.536762,524.474385),Base.Rotation(-0.313456,0.505313,0.000000,0.803992))
App.ActiveDocument.addObject("Part::Cylinder","C529")
App.ActiveDocument.C529.Radius=0.750000
App.ActiveDocument.C529.Height=15.00
App.ActiveDocument.C529.Angle=360.00 
App.ActiveDocument.C529.Placement=Base.Placement(Base.Vector(5.865193,-119.388136,522.259563),Base.Rotation(-0.346018,0.517884,0.000000,0.782347))
App.ActiveDocument.addObject("Part::Cylinder","C530")
App.ActiveDocument.C530.Radius=0.750000
App.ActiveDocument.C530.Height=15.00
App.ActiveDocument.C530.Angle=360.00 
App.ActiveDocument.C530.Placement=Base.Placement(Base.Vector(5.833984,-118.516601,519.869259),Base.Rotation(-0.372746,0.533503,0.000000,0.759233))
App.ActiveDocument.addObject("Part::Cylinder","C531")
App.ActiveDocument.C531.Radius=0.750000
App.ActiveDocument.C531.Height=15.00
App.ActiveDocument.C531.Angle=360.00 
App.ActiveDocument.C531.Placement=Base.Placement(Base.Vector(5.729688,-117.855380,517.424547),Base.Rotation(-0.396901,0.546224,0.000000,0.737638))
App.ActiveDocument.addObject("Part::Cylinder","C532")
App.ActiveDocument.C532.Radius=0.750000
App.ActiveDocument.C532.Height=15.00
App.ActiveDocument.C532.Angle=360.00 
App.ActiveDocument.C532.Placement=Base.Placement(Base.Vector(5.765904,-117.672283,515.042372),Base.Rotation(-0.408232,0.567146,0.000000,0.715327))
App.ActiveDocument.addObject("Part::Cylinder","C533")
App.ActiveDocument.C533.Radius=0.750000
App.ActiveDocument.C533.Height=15.00
App.ActiveDocument.C533.Angle=360.00 
App.ActiveDocument.C533.Placement=Base.Placement(Base.Vector(5.672503,-117.564601,512.562263),Base.Rotation(-0.420141,0.583125,0.000000,0.695304))
App.ActiveDocument.addObject("Part::Cylinder","C534")
App.ActiveDocument.C534.Radius=0.750000
App.ActiveDocument.C534.Height=15.00
App.ActiveDocument.C534.Angle=360.00 
App.ActiveDocument.C534.Placement=Base.Placement(Base.Vector(5.543043,-117.641272,510.129553),Base.Rotation(-0.433968,0.596559,0.000000,0.675122))
App.ActiveDocument.addObject("Part::Cylinder","C535")
App.ActiveDocument.C535.Radius=0.750000
App.ActiveDocument.C535.Height=15.00
App.ActiveDocument.C535.Angle=360.00 
App.ActiveDocument.C535.Placement=Base.Placement(Base.Vector(5.343262,-117.889581,507.530039),Base.Rotation(-0.438528,0.615037,0.000000,0.655304))
App.ActiveDocument.addObject("Part::Cylinder","C536")
App.ActiveDocument.C536.Radius=0.750000
App.ActiveDocument.C536.Height=15.00
App.ActiveDocument.C536.Angle=360.00 
App.ActiveDocument.C536.Placement=Base.Placement(Base.Vector(5.156459,-118.323198,505.177265),Base.Rotation(-0.442340,0.632779,0.000000,0.635552))
App.ActiveDocument.addObject("Part::Cylinder","C537")
App.ActiveDocument.C537.Radius=0.750000
App.ActiveDocument.C537.Height=15.00
App.ActiveDocument.C537.Angle=360.00 
App.ActiveDocument.C537.Placement=Base.Placement(Base.Vector(5.025277,-118.997808,502.941934),Base.Rotation(-0.439156,0.652074,0.000000,0.618014))
App.ActiveDocument.addObject("Part::Cylinder","C538")
App.ActiveDocument.C538.Radius=0.750000
App.ActiveDocument.C538.Height=15.00
App.ActiveDocument.C538.Angle=360.00 
App.ActiveDocument.C538.Placement=Base.Placement(Base.Vector(4.662887,-119.636676,500.487707),Base.Rotation(-0.434323,0.672296,0.000000,0.599484))
App.ActiveDocument.addObject("Part::Cylinder","C539")
App.ActiveDocument.C539.Radius=0.750000
App.ActiveDocument.C539.Height=15.00
App.ActiveDocument.C539.Angle=360.00 
App.ActiveDocument.C539.Placement=Base.Placement(Base.Vector(4.533999,-120.758126,498.235406),Base.Rotation(-0.427362,0.690908,0.000000,0.583102))
App.ActiveDocument.addObject("Part::Cylinder","C540")
App.ActiveDocument.C540.Radius=0.750000
App.ActiveDocument.C540.Height=15.00
App.ActiveDocument.C540.Angle=360.00 
App.ActiveDocument.C540.Placement=Base.Placement(Base.Vector(4.315544,-121.900138,496.087258),Base.Rotation(-0.415076,0.712450,0.000000,0.565797))
App.ActiveDocument.addObject("Part::Cylinder","C541")
App.ActiveDocument.C541.Radius=0.750000
App.ActiveDocument.C541.Height=15.00
App.ActiveDocument.C541.Angle=360.00 
App.ActiveDocument.C541.Placement=Base.Placement(Base.Vector(4.023840,-123.205854,493.883233),Base.Rotation(-0.397399,0.733063,0.000000,0.551989))
App.ActiveDocument.addObject("Part::Cylinder","C542")
App.ActiveDocument.C542.Radius=0.750000
App.ActiveDocument.C542.Height=15.00
App.ActiveDocument.C542.Angle=360.00 
App.ActiveDocument.C542.Placement=Base.Placement(Base.Vector(3.614039,-124.456171,491.787655),Base.Rotation(-0.386249,0.752180,0.000000,0.533888))
App.ActiveDocument.addObject("Part::Cylinder","C543")
App.ActiveDocument.C543.Radius=0.750000
App.ActiveDocument.C543.Height=15.00
App.ActiveDocument.C543.Angle=360.00 
App.ActiveDocument.C543.Placement=Base.Placement(Base.Vector(3.274965,-126.045575,489.768524),Base.Rotation(-0.364086,0.773423,0.000000,0.518900))
App.ActiveDocument.addObject("Part::Cylinder","C544")
App.ActiveDocument.C544.Radius=0.750000
App.ActiveDocument.C544.Height=15.00
App.ActiveDocument.C544.Angle=360.00 
App.ActiveDocument.C544.Placement=Base.Placement(Base.Vector(2.998315,-127.885402,487.920517),Base.Rotation(-0.333874,0.795260,0.000000,0.506053))
App.ActiveDocument.addObject("Part::Cylinder","C545")
App.ActiveDocument.C545.Radius=0.750000
App.ActiveDocument.C545.Height=15.00
App.ActiveDocument.C545.Angle=360.00 
App.ActiveDocument.C545.Placement=Base.Placement(Base.Vector(2.456224,-129.609649,485.975718),Base.Rotation(-0.299923,0.819058,0.000000,0.489070))
App.ActiveDocument.addObject("Part::Cylinder","C546")
App.ActiveDocument.C546.Radius=0.750000
App.ActiveDocument.C546.Height=15.00
App.ActiveDocument.C546.Angle=360.00 
App.ActiveDocument.C546.Placement=Base.Placement(Base.Vector(1.997082,-131.561785,484.275536),Base.Rotation(-0.268014,0.837736,0.000000,0.475779))
App.ActiveDocument.addObject("Part::Cylinder","C547")
App.ActiveDocument.C547.Radius=0.750000
App.ActiveDocument.C547.Height=15.00
App.ActiveDocument.C547.Angle=360.00 
App.ActiveDocument.C547.Placement=Base.Placement(Base.Vector(1.295521,-133.387840,482.518145),Base.Rotation(-0.224514,0.858511,0.000000,0.461034))
App.ActiveDocument.addObject("Part::Cylinder","C548")
App.ActiveDocument.C548.Radius=0.750000
App.ActiveDocument.C548.Height=15.00
App.ActiveDocument.C548.Angle=360.00 
App.ActiveDocument.C548.Placement=Base.Placement(Base.Vector(0.423464,-135.301275,480.742474),Base.Rotation(-0.186477,0.875741,0.000000,0.445313))
App.ActiveDocument.addObject("Part::Cylinder","C549")
App.ActiveDocument.C549.Radius=0.750000
App.ActiveDocument.C549.Height=15.00
App.ActiveDocument.C549.Angle=360.00 
App.ActiveDocument.C549.Placement=Base.Placement(Base.Vector(-0.736149,-137.024368,478.899311),Base.Rotation(-0.135640,0.893508,0.000000,0.428071))
App.ActiveDocument.addObject("Part::Cylinder","C550")
App.ActiveDocument.C550.Radius=0.750000
App.ActiveDocument.C550.Height=15.00
App.ActiveDocument.C550.Angle=360.00 
App.ActiveDocument.C550.Placement=Base.Placement(Base.Vector(-2.088807,-138.477718,477.124695),Base.Rotation(-0.099914,0.909471,0.000000,0.403584))
App.ActiveDocument.addObject("Part::Cylinder","C551")
App.ActiveDocument.C551.Radius=0.750000
App.ActiveDocument.C551.Height=15.00
App.ActiveDocument.C551.Angle=360.00 
App.ActiveDocument.C551.Placement=Base.Placement(Base.Vector(-3.787667,-138.962539,475.293637),Base.Rotation(-0.096503,0.919897,0.000000,0.380100))
App.ActiveDocument.addObject("Part::Cylinder","C552")
App.ActiveDocument.C552.Radius=0.750000
App.ActiveDocument.C552.Height=15.00
App.ActiveDocument.C552.Angle=360.00 
App.ActiveDocument.C552.Placement=Base.Placement(Base.Vector(7.723914,-137.692374,531.602309),Base.Rotation(-0.033754,0.488755,0.000000,0.871768))
App.ActiveDocument.addObject("Part::Cylinder","C553")
App.ActiveDocument.C553.Radius=0.750000
App.ActiveDocument.C553.Height=15.00
App.ActiveDocument.C553.Angle=360.00 
App.ActiveDocument.C553.Placement=Base.Placement(Base.Vector(7.552655,-134.411454,531.307940),Base.Rotation(-0.070537,0.489177,0.000000,0.869327))
App.ActiveDocument.addObject("Part::Cylinder","C554")
App.ActiveDocument.C554.Radius=0.750000
App.ActiveDocument.C554.Height=15.00
App.ActiveDocument.C554.Angle=360.00 
App.ActiveDocument.C554.Placement=Base.Placement(Base.Vector(7.622907,-131.465656,530.263383),Base.Rotation(-0.109573,0.502326,0.000000,0.857708))
App.ActiveDocument.addObject("Part::Cylinder","C555")
App.ActiveDocument.C555.Radius=0.750000
App.ActiveDocument.C555.Height=15.00
App.ActiveDocument.C555.Angle=360.00 
App.ActiveDocument.C555.Placement=Base.Placement(Base.Vector(7.536136,-128.721929,529.091138),Base.Rotation(-0.150119,0.507504,0.000000,0.848472))
App.ActiveDocument.addObject("Part::Cylinder","C556")
App.ActiveDocument.C556.Radius=0.750000
App.ActiveDocument.C556.Height=15.00
App.ActiveDocument.C556.Angle=360.00 
App.ActiveDocument.C556.Placement=Base.Placement(Base.Vector(7.509466,-126.446774,527.566909),Base.Rotation(-0.191859,0.517251,0.000000,0.834051))
App.ActiveDocument.addObject("Part::Cylinder","C557")
App.ActiveDocument.C557.Radius=0.750000
App.ActiveDocument.C557.Height=15.00
App.ActiveDocument.C557.Angle=360.00 
App.ActiveDocument.C557.Placement=Base.Placement(Base.Vector(7.526084,-124.534448,525.682884),Base.Rotation(-0.228756,0.534373,0.000000,0.813705))
App.ActiveDocument.addObject("Part::Cylinder","C558")
App.ActiveDocument.C558.Radius=0.750000
App.ActiveDocument.C558.Height=15.00
App.ActiveDocument.C558.Angle=360.00 
App.ActiveDocument.C558.Placement=Base.Placement(Base.Vector(7.542749,-123.045353,523.631038),Base.Rotation(-0.262466,0.548066,0.000000,0.794189))
App.ActiveDocument.addObject("Part::Cylinder","C559")
App.ActiveDocument.C559.Radius=0.750000
App.ActiveDocument.C559.Height=15.00
App.ActiveDocument.C559.Angle=360.00 
App.ActiveDocument.C559.Placement=Base.Placement(Base.Vector(7.538335,-121.851210,521.363413),Base.Rotation(-0.291658,0.564181,0.000000,0.772422))
App.ActiveDocument.addObject("Part::Cylinder","C560")
App.ActiveDocument.C560.Radius=0.750000
App.ActiveDocument.C560.Height=15.00
App.ActiveDocument.C560.Angle=360.00 
App.ActiveDocument.C560.Placement=Base.Placement(Base.Vector(7.405362,-120.828606,519.113130),Base.Rotation(-0.320766,0.575766,0.000000,0.752065))
App.ActiveDocument.addObject("Part::Cylinder","C561")
App.ActiveDocument.C561.Radius=0.750000
App.ActiveDocument.C561.Height=15.00
App.ActiveDocument.C561.Angle=360.00 
App.ActiveDocument.C561.Placement=Base.Placement(Base.Vector(7.346924,-120.255867,516.725476),Base.Rotation(-0.341510,0.591631,0.000000,0.730304))
App.ActiveDocument.addObject("Part::Cylinder","C562")
App.ActiveDocument.C562.Radius=0.750000
App.ActiveDocument.C562.Height=15.00
App.ActiveDocument.C562.Angle=360.00 
App.ActiveDocument.C562.Placement=Base.Placement(Base.Vector(7.318078,-120.035591,514.314809),Base.Rotation(-0.361927,0.606634,0.000000,0.707817))
App.ActiveDocument.addObject("Part::Cylinder","C563")
App.ActiveDocument.C563.Radius=0.750000
App.ActiveDocument.C563.Height=15.00
App.ActiveDocument.C563.Angle=360.00 
App.ActiveDocument.C563.Placement=Base.Placement(Base.Vector(7.151304,-119.871250,511.846551),Base.Rotation(-0.369557,0.622903,0.000000,0.689506))
App.ActiveDocument.addObject("Part::Cylinder","C564")
App.ActiveDocument.C564.Radius=0.750000
App.ActiveDocument.C564.Height=15.00
App.ActiveDocument.C564.Angle=360.00 
App.ActiveDocument.C564.Placement=Base.Placement(Base.Vector(6.962614,-119.928679,509.450883),Base.Rotation(-0.377113,0.641438,0.000000,0.668090))
App.ActiveDocument.addObject("Part::Cylinder","C565")
App.ActiveDocument.C565.Radius=0.750000
App.ActiveDocument.C565.Height=15.00
App.ActiveDocument.C565.Angle=360.00 
App.ActiveDocument.C565.Placement=Base.Placement(Base.Vector(7.005995,-120.823981,506.528996),Base.Rotation(-0.373044,0.667004,0.000000,0.644937))
App.ActiveDocument.addObject("Part::Cylinder","C566")
App.ActiveDocument.C566.Radius=0.750000
App.ActiveDocument.C566.Height=15.00
App.ActiveDocument.C566.Angle=360.00 
App.ActiveDocument.C566.Placement=Base.Placement(Base.Vector(6.783192,-121.561456,503.718065),Base.Rotation(-0.373685,0.686360,0.000000,0.623914))
App.ActiveDocument.addObject("Part::Cylinder","C567")
App.ActiveDocument.C567.Radius=0.750000
App.ActiveDocument.C567.Height=15.00
App.ActiveDocument.C567.Angle=360.00 
App.ActiveDocument.C567.Placement=Base.Placement(Base.Vector(6.360625,-122.198163,501.057469),Base.Rotation(-0.372596,0.703877,0.000000,0.604755))
App.ActiveDocument.addObject("Part::Cylinder","C568")
App.ActiveDocument.C568.Radius=0.750000
App.ActiveDocument.C568.Height=15.00
App.ActiveDocument.C568.Angle=360.00 
App.ActiveDocument.C568.Placement=Base.Placement(Base.Vector(6.080234,-123.138637,498.803480),Base.Rotation(-0.360686,0.723145,0.000000,0.589039))
App.ActiveDocument.addObject("Part::Cylinder","C569")
App.ActiveDocument.C569.Radius=0.750000
App.ActiveDocument.C569.Height=15.00
App.ActiveDocument.C569.Angle=360.00 
App.ActiveDocument.C569.Placement=Base.Placement(Base.Vector(5.825836,-124.352612,496.614243),Base.Rotation(-0.347259,0.743823,0.000000,0.571086))
App.ActiveDocument.addObject("Part::Cylinder","C570")
App.ActiveDocument.C570.Radius=0.750000
App.ActiveDocument.C570.Height=15.00
App.ActiveDocument.C570.Angle=360.00 
App.ActiveDocument.C570.Placement=Base.Placement(Base.Vector(5.542665,-125.651666,494.573485),Base.Rotation(-0.332230,0.761135,0.000000,0.557044))
App.ActiveDocument.addObject("Part::Cylinder","C571")
App.ActiveDocument.C571.Radius=0.750000
App.ActiveDocument.C571.Height=15.00
App.ActiveDocument.C571.Angle=360.00 
App.ActiveDocument.C571.Placement=Base.Placement(Base.Vector(5.240380,-127.629840,492.216618),Base.Rotation(-0.302492,0.785411,0.000000,0.540026))
App.ActiveDocument.addObject("Part::Cylinder","C572")
App.ActiveDocument.C572.Radius=0.750000
App.ActiveDocument.C572.Height=15.00
App.ActiveDocument.C572.Angle=360.00 
App.ActiveDocument.C572.Placement=Base.Placement(Base.Vector(4.837243,-129.535132,490.083550),Base.Rotation(-0.264990,0.808601,0.000000,0.525305))
App.ActiveDocument.addObject("Part::Cylinder","C573")
App.ActiveDocument.C573.Radius=0.750000
App.ActiveDocument.C573.Height=15.00
App.ActiveDocument.C573.Angle=360.00 
App.ActiveDocument.C573.Placement=Base.Placement(Base.Vector(4.253085,-131.520200,487.916220),Base.Rotation(-0.230014,0.829382,0.000000,0.509135))
App.ActiveDocument.addObject("Part::Cylinder","C574")
App.ActiveDocument.C574.Radius=0.750000
App.ActiveDocument.C574.Height=15.00
App.ActiveDocument.C574.Angle=360.00 
App.ActiveDocument.C574.Placement=Base.Placement(Base.Vector(3.652887,-133.411248,486.074262),Base.Rotation(-0.184990,0.847806,0.000000,0.496995))
App.ActiveDocument.addObject("Part::Cylinder","C575")
App.ActiveDocument.C575.Radius=0.750000
App.ActiveDocument.C575.Height=15.00
App.ActiveDocument.C575.Angle=360.00 
App.ActiveDocument.C575.Placement=Base.Placement(Base.Vector(2.999594,-135.266755,484.429613),Base.Rotation(-0.146325,0.863005,0.000000,0.483540))
App.ActiveDocument.addObject("Part::Cylinder","C576")
App.ActiveDocument.C576.Radius=0.750000
App.ActiveDocument.C576.Height=15.00
App.ActiveDocument.C576.Angle=360.00 
App.ActiveDocument.C576.Placement=Base.Placement(Base.Vector(2.159400,-137.160911,482.744553),Base.Rotation(-0.097593,0.877181,0.000000,0.470138))
App.ActiveDocument.addObject("Part::Cylinder","C577")
App.ActiveDocument.C577.Radius=0.750000
App.ActiveDocument.C577.Height=15.00
App.ActiveDocument.C577.Angle=360.00 
App.ActiveDocument.C577.Placement=Base.Placement(Base.Vector(0.945055,-138.703395,480.826496),Base.Rotation(-0.060588,0.889871,0.000000,0.452171))
App.ActiveDocument.addObject("Part::Cylinder","C578")
App.ActiveDocument.C578.Radius=0.750000
App.ActiveDocument.C578.Height=15.00
App.ActiveDocument.C578.Angle=360.00 
App.ActiveDocument.C578.Placement=Base.Placement(Base.Vector(9.056787,-137.747152,529.120173),Base.Rotation(-0.033638,0.535934,0.000000,0.843590))
App.ActiveDocument.addObject("Part::Cylinder","C579")
App.ActiveDocument.C579.Radius=0.750000
App.ActiveDocument.C579.Height=15.00
App.ActiveDocument.C579.Angle=360.00 
App.ActiveDocument.C579.Placement=Base.Placement(Base.Vector(8.964280,-134.594574,528.669240),Base.Rotation(-0.070429,0.538168,0.000000,0.839890))
App.ActiveDocument.addObject("Part::Cylinder","C580")
App.ActiveDocument.C580.Radius=0.750000
App.ActiveDocument.C580.Height=15.00
App.ActiveDocument.C580.Angle=360.00 
App.ActiveDocument.C580.Placement=Base.Placement(Base.Vector(9.003730,-131.726383,527.498797),Base.Rotation(-0.108742,0.547931,0.000000,0.829425))
App.ActiveDocument.addObject("Part::Cylinder","C581")
App.ActiveDocument.C581.Radius=0.750000
App.ActiveDocument.C581.Height=15.00
App.ActiveDocument.C581.Angle=360.00 
App.ActiveDocument.C581.Placement=Base.Placement(Base.Vector(8.921452,-129.187609,526.211050),Base.Rotation(-0.148146,0.556322,0.000000,0.817654))
App.ActiveDocument.addObject("Part::Cylinder","C582")
App.ActiveDocument.C582.Radius=0.750000
App.ActiveDocument.C582.Height=15.00
App.ActiveDocument.C582.Angle=360.00 
App.ActiveDocument.C582.Placement=Base.Placement(Base.Vector(8.918947,-127.198276,524.507648),Base.Rotation(-0.180519,0.572028,0.000000,0.800123))
App.ActiveDocument.addObject("Part::Cylinder","C583")
App.ActiveDocument.C583.Radius=0.750000
App.ActiveDocument.C583.Height=15.00
App.ActiveDocument.C583.Angle=360.00 
App.ActiveDocument.C583.Placement=Base.Placement(Base.Vector(8.959288,-125.663347,522.446800),Base.Rotation(-0.213540,0.586259,0.000000,0.781474))
App.ActiveDocument.addObject("Part::Cylinder","C584")
App.ActiveDocument.C584.Radius=0.750000
App.ActiveDocument.C584.Height=15.00
App.ActiveDocument.C584.Angle=360.00 
App.ActiveDocument.C584.Placement=Base.Placement(Base.Vector(8.934518,-124.449805,520.322151),Base.Rotation(-0.242863,0.601931,0.000000,0.760721))
App.ActiveDocument.addObject("Part::Cylinder","C585")
App.ActiveDocument.C585.Radius=0.750000
App.ActiveDocument.C585.Height=15.00
App.ActiveDocument.C585.Angle=360.00 
App.ActiveDocument.C585.Placement=Base.Placement(Base.Vector(8.755580,-123.238123,517.901393),Base.Rotation(-0.270560,0.615245,0.000000,0.740453))
App.ActiveDocument.addObject("Part::Cylinder","C586")
App.ActiveDocument.C586.Radius=0.750000
App.ActiveDocument.C586.Height=15.00
App.ActiveDocument.C586.Angle=360.00 
App.ActiveDocument.C586.Placement=Base.Placement(Base.Vector(8.602077,-122.533390,515.563598),Base.Rotation(-0.294886,0.630578,0.000000,0.717923))
App.ActiveDocument.addObject("Part::Cylinder","C587")
App.ActiveDocument.C587.Radius=0.750000
App.ActiveDocument.C587.Height=15.00
App.ActiveDocument.C587.Angle=360.00 
App.ActiveDocument.C587.Placement=Base.Placement(Base.Vector(8.697294,-122.776973,512.505544),Base.Rotation(-0.300748,0.654409,0.000000,0.693757))
App.ActiveDocument.addObject("Part::Cylinder","C588")
App.ActiveDocument.C588.Radius=0.750000
App.ActiveDocument.C588.Height=15.00
App.ActiveDocument.C588.Angle=360.00 
App.ActiveDocument.C588.Placement=Base.Placement(Base.Vector(8.477423,-122.748623,509.741071),Base.Rotation(-0.312599,0.672266,0.000000,0.671074))
App.ActiveDocument.addObject("Part::Cylinder","C589")
App.ActiveDocument.C589.Radius=0.750000
App.ActiveDocument.C589.Height=15.00
App.ActiveDocument.C589.Angle=360.00 
App.ActiveDocument.C589.Placement=Base.Placement(Base.Vector(8.422860,-123.660675,506.603495),Base.Rotation(-0.300456,0.700513,0.000000,0.647308))
App.ActiveDocument.addObject("Part::Cylinder","C590")
App.ActiveDocument.C590.Radius=0.750000
App.ActiveDocument.C590.Height=15.00
App.ActiveDocument.C590.Angle=360.00 
App.ActiveDocument.C590.Placement=Base.Placement(Base.Vector(8.099239,-124.468129,503.466283),Base.Rotation(-0.302639,0.720485,0.000000,0.623948))
App.ActiveDocument.addObject("Part::Cylinder","C591")
App.ActiveDocument.C591.Radius=0.750000
App.ActiveDocument.C591.Height=15.00
App.ActiveDocument.C591.Angle=360.00 
App.ActiveDocument.C591.Placement=Base.Placement(Base.Vector(7.744752,-125.551227,500.575132),Base.Rotation(-0.292919,0.742854,0.000000,0.601968))
App.ActiveDocument.addObject("Part::Cylinder","C592")
App.ActiveDocument.C592.Radius=0.750000
App.ActiveDocument.C592.Height=15.00
App.ActiveDocument.C592.Angle=360.00 
App.ActiveDocument.C592.Placement=Base.Placement(Base.Vector(7.390372,-126.750284,498.106430),Base.Rotation(-0.276654,0.762290,0.000000,0.585129))
App.ActiveDocument.addObject("Part::Cylinder","C593")
App.ActiveDocument.C593.Radius=0.750000
App.ActiveDocument.C593.Height=15.00
App.ActiveDocument.C593.Angle=360.00 
App.ActiveDocument.C593.Placement=Base.Placement(Base.Vector(6.988442,-128.131074,495.755532),Base.Rotation(-0.260012,0.779707,0.000000,0.569605))
App.ActiveDocument.addObject("Part::Cylinder","C594")
App.ActiveDocument.C594.Radius=0.750000
App.ActiveDocument.C594.Height=15.00
App.ActiveDocument.C594.Angle=360.00 
App.ActiveDocument.C594.Placement=Base.Placement(Base.Vector(6.660764,-130.335140,493.392318),Base.Rotation(-0.218327,0.804400,0.000000,0.552517))
App.ActiveDocument.addObject("Part::Cylinder","C595")
App.ActiveDocument.C595.Radius=0.750000
App.ActiveDocument.C595.Height=15.00
App.ActiveDocument.C595.Angle=360.00 
App.ActiveDocument.C595.Placement=Base.Placement(Base.Vector(6.127754,-132.489803,491.072709),Base.Rotation(-0.176152,0.824267,0.000000,0.538102))
App.ActiveDocument.addObject("Part::Cylinder","C596")
App.ActiveDocument.C596.Radius=0.750000
App.ActiveDocument.C596.Height=15.00
App.ActiveDocument.C596.Angle=360.00 
App.ActiveDocument.C596.Placement=Base.Placement(Base.Vector(5.442562,-134.549896,488.907224),Base.Rotation(-0.137242,0.841180,0.000000,0.523049))
App.ActiveDocument.addObject("Part::Cylinder","C597")
App.ActiveDocument.C597.Radius=0.750000
App.ActiveDocument.C597.Height=15.00
App.ActiveDocument.C597.Angle=360.00 
App.ActiveDocument.C597.Placement=Base.Placement(Base.Vector(4.712916,-136.790126,486.988301),Base.Rotation(-0.085971,0.856607,0.000000,0.508756))
App.ActiveDocument.addObject("Part::Cylinder","C598")
App.ActiveDocument.C598.Radius=0.750000
App.ActiveDocument.C598.Height=15.00
App.ActiveDocument.C598.Angle=360.00 
App.ActiveDocument.C598.Placement=Base.Placement(Base.Vector(3.996466,-138.617773,485.476215),Base.Rotation(-0.047869,0.866372,0.000000,0.497100))
App.ActiveDocument.addObject("Part::Cylinder","C599")
App.ActiveDocument.C599.Radius=0.750000
App.ActiveDocument.C599.Height=15.00
App.ActiveDocument.C599.Angle=360.00 
App.ActiveDocument.C599.Placement=Base.Placement(Base.Vector(10.171469,-137.790525,526.373654),Base.Rotation(-0.033766,0.579009,0.000000,0.814621))
App.ActiveDocument.addObject("Part::Cylinder","C600")
App.ActiveDocument.C600.Radius=0.750000
App.ActiveDocument.C600.Height=15.00
App.ActiveDocument.C600.Angle=360.00 
App.ActiveDocument.C600.Placement=Base.Placement(Base.Vector(10.097296,-134.690975,525.788160),Base.Rotation(-0.070009,0.582974,0.000000,0.809469))
App.ActiveDocument.addObject("Part::Cylinder","C601")
App.ActiveDocument.C601.Radius=0.750000
App.ActiveDocument.C601.Height=15.00
App.ActiveDocument.C601.Angle=360.00 
App.ActiveDocument.C601.Placement=Base.Placement(Base.Vector(10.085951,-131.944875,524.497349),Base.Rotation(-0.107311,0.592746,0.000000,0.798208))
App.ActiveDocument.addObject("Part::Cylinder","C602")
App.ActiveDocument.C602.Radius=0.750000
App.ActiveDocument.C602.Height=15.00
App.ActiveDocument.C602.Angle=360.00 
App.ActiveDocument.C602.Placement=Base.Placement(Base.Vector(10.081757,-129.752082,522.809365),Base.Rotation(-0.138534,0.608111,0.000000,0.781671))
App.ActiveDocument.addObject("Part::Cylinder","C603")
App.ActiveDocument.C603.Radius=0.750000
App.ActiveDocument.C603.Height=15.00
App.ActiveDocument.C603.Angle=360.00 
App.ActiveDocument.C603.Placement=Base.Placement(Base.Vector(10.081053,-128.178862,520.909819),Base.Rotation(-0.169772,0.620968,0.000000,0.765230))
App.ActiveDocument.addObject("Part::Cylinder","C604")
App.ActiveDocument.C604.Radius=0.750000
App.ActiveDocument.C604.Height=15.00
App.ActiveDocument.C604.Angle=360.00 
App.ActiveDocument.C604.Placement=Base.Placement(Base.Vector(10.049871,-126.960192,518.746781),Base.Rotation(-0.197723,0.636147,0.000000,0.745803))
App.ActiveDocument.addObject("Part::Cylinder","C605")
App.ActiveDocument.C605.Radius=0.750000
App.ActiveDocument.C605.Height=15.00
App.ActiveDocument.C605.Angle=360.00 
App.ActiveDocument.C605.Placement=Base.Placement(Base.Vector(9.859727,-125.780002,516.604238),Base.Rotation(-0.225181,0.647907,0.000000,0.727674))
App.ActiveDocument.addObject("Part::Cylinder","C606")
App.ActiveDocument.C606.Radius=0.750000
App.ActiveDocument.C606.Height=15.00
App.ActiveDocument.C606.Angle=360.00 
App.ActiveDocument.C606.Placement=Base.Placement(Base.Vector(9.690254,-125.091129,514.256514),Base.Rotation(-0.245181,0.661499,0.000000,0.708735))
App.ActiveDocument.addObject("Part::Cylinder","C607")
App.ActiveDocument.C607.Radius=0.750000
App.ActiveDocument.C607.Height=15.00
App.ActiveDocument.C607.Angle=360.00 
App.ActiveDocument.C607.Placement=Base.Placement(Base.Vector(9.804447,-125.714184,511.300880),Base.Rotation(-0.238710,0.688191,0.000000,0.685135))
App.ActiveDocument.addObject("Part::Cylinder","C608")
App.ActiveDocument.C608.Radius=0.750000
App.ActiveDocument.C608.Height=15.00
App.ActiveDocument.C608.Angle=360.00 
App.ActiveDocument.C608.Placement=Base.Placement(Base.Vector(9.657617,-126.050862,508.566586),Base.Rotation(-0.243512,0.708517,0.000000,0.662349))
App.ActiveDocument.addObject("Part::Cylinder","C609")
App.ActiveDocument.C609.Radius=0.750000
App.ActiveDocument.C609.Height=15.00
App.ActiveDocument.C609.Angle=360.00 
App.ActiveDocument.C609.Placement=Base.Placement(Base.Vector(9.468532,-126.892336,505.653036),Base.Rotation(-0.236830,0.729880,0.000000,0.641239))
App.ActiveDocument.addObject("Part::Cylinder","C610")
App.ActiveDocument.C610.Radius=0.750000
App.ActiveDocument.C610.Height=15.00
App.ActiveDocument.C610.Angle=360.00 
App.ActiveDocument.C610.Placement=Base.Placement(Base.Vector(9.106858,-127.726382,502.784218),Base.Rotation(-0.227892,0.750042,0.000000,0.620888))
App.ActiveDocument.addObject("Part::Cylinder","C611")
App.ActiveDocument.C611.Radius=0.750000
App.ActiveDocument.C611.Height=15.00
App.ActiveDocument.C611.Angle=360.00 
App.ActiveDocument.C611.Placement=Base.Placement(Base.Vector(8.804426,-129.089072,500.200940),Base.Rotation(-0.209752,0.769740,0.000000,0.602914))
App.ActiveDocument.addObject("Part::Cylinder","C612")
App.ActiveDocument.C612.Radius=0.750000
App.ActiveDocument.C612.Height=15.00
App.ActiveDocument.C612.Angle=360.00 
App.ActiveDocument.C612.Placement=Base.Placement(Base.Vector(8.375392,-130.467178,497.723665),Base.Rotation(-0.195092,0.786830,0.000000,0.585523))
App.ActiveDocument.addObject("Part::Cylinder","C613")
App.ActiveDocument.C613.Radius=0.750000
App.ActiveDocument.C613.Height=15.00
App.ActiveDocument.C613.Angle=360.00 
App.ActiveDocument.C613.Placement=Base.Placement(Base.Vector(7.992755,-132.172537,495.599761),Base.Rotation(-0.163622,0.803781,0.000000,0.571982))
App.ActiveDocument.addObject("Part::Cylinder","C614")
App.ActiveDocument.C614.Radius=0.750000
App.ActiveDocument.C614.Height=15.00
App.ActiveDocument.C614.Angle=360.00 
App.ActiveDocument.C614.Placement=Base.Placement(Base.Vector(7.631066,-134.144576,493.801068),Base.Rotation(-0.122815,0.819192,0.000000,0.560214))
App.ActiveDocument.addObject("Part::Cylinder","C615")
App.ActiveDocument.C615.Radius=0.750000
App.ActiveDocument.C615.Height=15.00
App.ActiveDocument.C615.Angle=360.00 
App.ActiveDocument.C615.Placement=Base.Placement(Base.Vector(6.977628,-136.179453,491.667712),Base.Rotation(-0.086852,0.834088,0.000000,0.544751))
App.ActiveDocument.addObject("Part::Cylinder","C616")
App.ActiveDocument.C616.Radius=0.750000
App.ActiveDocument.C616.Height=15.00
App.ActiveDocument.C616.Angle=360.00 
App.ActiveDocument.C616.Placement=Base.Placement(Base.Vector(6.263749,-138.220218,489.776162),Base.Rotation(-0.047834,0.845042,0.000000,0.532556))
App.ActiveDocument.addObject("Part::Cylinder","C617")
App.ActiveDocument.C617.Radius=0.750000
App.ActiveDocument.C617.Height=15.00
App.ActiveDocument.C617.Angle=360.00 
App.ActiveDocument.C617.Placement=Base.Placement(Base.Vector(11.035443,-137.824109,523.424637),Base.Rotation(-0.033094,0.618063,0.000000,0.785431))
App.ActiveDocument.addObject("Part::Cylinder","C618")
App.ActiveDocument.C618.Radius=0.750000
App.ActiveDocument.C618.Height=15.00
App.ActiveDocument.C618.Angle=360.00 
App.ActiveDocument.C618.Placement=Base.Placement(Base.Vector(10.968963,-134.804603,522.643333),Base.Rotation(-0.069641,0.623237,0.000000,0.778926))
App.ActiveDocument.addObject("Part::Cylinder","C619")
App.ActiveDocument.C619.Radius=0.750000
App.ActiveDocument.C619.Height=15.00
App.ActiveDocument.C619.Angle=360.00 
App.ActiveDocument.C619.Placement=Base.Placement(Base.Vector(10.978619,-132.443697,520.987305),Base.Rotation(-0.103225,0.636827,0.000000,0.764065))
App.ActiveDocument.addObject("Part::Cylinder","C620")
App.ActiveDocument.C620.Radius=0.750000
App.ActiveDocument.C620.Height=15.00
App.ActiveDocument.C620.Angle=360.00 
App.ActiveDocument.C620.Placement=Base.Placement(Base.Vector(10.941847,-130.611417,518.986258),Base.Rotation(-0.134932,0.649883,0.000000,0.747961))
App.ActiveDocument.addObject("Part::Cylinder","C621")
App.ActiveDocument.C621.Radius=0.750000
App.ActiveDocument.C621.Height=15.00
App.ActiveDocument.C621.Angle=360.00 
App.ActiveDocument.C621.Placement=Base.Placement(Base.Vector(10.854536,-129.346832,517.028678),Base.Rotation(-0.158625,0.664295,0.000000,0.730445))
App.ActiveDocument.addObject("Part::Cylinder","C622")
App.ActiveDocument.C622.Radius=0.750000
App.ActiveDocument.C622.Height=15.00
App.ActiveDocument.C622.Angle=360.00 
App.ActiveDocument.C622.Placement=Base.Placement(Base.Vector(10.678711,-128.265193,514.904816),Base.Rotation(-0.177686,0.679533,0.000000,0.711802))
App.ActiveDocument.addObject("Part::Cylinder","C623")
App.ActiveDocument.C623.Radius=0.750000
App.ActiveDocument.C623.Height=15.00
App.ActiveDocument.C623.Angle=360.00 
App.ActiveDocument.C623.Placement=Base.Placement(Base.Vector(10.706331,-128.487089,512.358107),Base.Rotation(-0.177533,0.697715,0.000000,0.694028))
App.ActiveDocument.addObject("Part::Cylinder","C624")
App.ActiveDocument.C624.Radius=0.750000
App.ActiveDocument.C624.Height=15.00
App.ActiveDocument.C624.Angle=360.00 
App.ActiveDocument.C624.Placement=Base.Placement(Base.Vector(10.668161,-129.148173,509.569309),Base.Rotation(-0.174397,0.720144,0.000000,0.671549))
App.ActiveDocument.addObject("Part::Cylinder","C625")
App.ActiveDocument.C625.Radius=0.750000
App.ActiveDocument.C625.Height=15.00
App.ActiveDocument.C625.Angle=360.00 
App.ActiveDocument.C625.Placement=Base.Placement(Base.Vector(10.463492,-129.727186,506.879875),Base.Rotation(-0.172847,0.736866,0.000000,0.653569))
App.ActiveDocument.addObject("Part::Cylinder","C626")
App.ActiveDocument.C626.Radius=0.750000
App.ActiveDocument.C626.Height=15.00
App.ActiveDocument.C626.Angle=360.00 
App.ActiveDocument.C626.Placement=Base.Placement(Base.Vector(10.140773,-130.462548,504.207565),Base.Rotation(-0.162699,0.756842,0.000000,0.633023))
App.ActiveDocument.addObject("Part::Cylinder","C627")
App.ActiveDocument.C627.Radius=0.750000
App.ActiveDocument.C627.Height=15.00
App.ActiveDocument.C627.Angle=360.00 
App.ActiveDocument.C627.Placement=Base.Placement(Base.Vector(9.820021,-131.628141,501.775717),Base.Rotation(-0.149462,0.774196,0.000000,0.615046))
App.ActiveDocument.addObject("Part::Cylinder","C628")
App.ActiveDocument.C628.Radius=0.750000
App.ActiveDocument.C628.Height=15.00
App.ActiveDocument.C628.Angle=360.00 
App.ActiveDocument.C628.Placement=Base.Placement(Base.Vector(9.426534,-133.040751,499.435498),Base.Rotation(-0.125768,0.789922,0.000000,0.600171))
App.ActiveDocument.addObject("Part::Cylinder","C629")
App.ActiveDocument.C629.Radius=0.750000
App.ActiveDocument.C629.Height=15.00
App.ActiveDocument.C629.Angle=360.00 
App.ActiveDocument.C629.Placement=Base.Placement(Base.Vector(9.027890,-134.547327,497.458964),Base.Rotation(-0.102304,0.802878,0.000000,0.587299))
App.ActiveDocument.addObject("Part::Cylinder","C630")
App.ActiveDocument.C630.Radius=0.750000
App.ActiveDocument.C630.Height=15.00
App.ActiveDocument.C630.Angle=360.00 
App.ActiveDocument.C630.Placement=Base.Placement(Base.Vector(8.558447,-137.130449,495.395775),Base.Rotation(-0.059569,0.816974,0.000000,0.573589))
App.ActiveDocument.addObject("Part::Cylinder","C631")
App.ActiveDocument.C631.Radius=0.750000
App.ActiveDocument.C631.Height=15.00
App.ActiveDocument.C631.Angle=360.00 
App.ActiveDocument.C631.Placement=Base.Placement(Base.Vector(7.702072,-138.220627,492.994994),Base.Rotation(-0.042866,0.829479,0.000000,0.556891))
App.ActiveDocument.addObject("Part::Cylinder","C632")
App.ActiveDocument.C632.Radius=0.750000
App.ActiveDocument.C632.Height=15.00
App.ActiveDocument.C632.Angle=360.00 
App.ActiveDocument.C632.Placement=Base.Placement(Base.Vector(11.641693,-137.889090,520.316524),Base.Rotation(-0.033752,0.651839,0.000000,0.757606))
App.ActiveDocument.addObject("Part::Cylinder","C633")
App.ActiveDocument.C633.Radius=0.750000
App.ActiveDocument.C633.Height=15.00
App.ActiveDocument.C633.Angle=360.00 
App.ActiveDocument.C633.Placement=Base.Placement(Base.Vector(11.599268,-135.166794,519.125570),Base.Rotation(-0.066850,0.660579,0.000000,0.747774))
App.ActiveDocument.addObject("Part::Cylinder","C634")
App.ActiveDocument.C634.Radius=0.750000
App.ActiveDocument.C634.Height=15.00
App.ActiveDocument.C634.Angle=360.00 
App.ActiveDocument.C634.Placement=Base.Placement(Base.Vector(11.561806,-133.177015,517.000347),Base.Rotation(-0.094022,0.676057,0.000000,0.730826))
App.ActiveDocument.addObject("Part::Cylinder","C635")
App.ActiveDocument.C635.Radius=0.750000
App.ActiveDocument.C635.Height=15.00
App.ActiveDocument.C635.Angle=360.00 
App.ActiveDocument.C635.Placement=Base.Placement(Base.Vector(11.413757,-131.666746,514.989111),Base.Rotation(-0.118728,0.689560,0.000000,0.714430))
App.ActiveDocument.addObject("Part::Cylinder","C636")
App.ActiveDocument.C636.Radius=0.750000
App.ActiveDocument.C636.Height=15.00
App.ActiveDocument.C636.Angle=360.00 
App.ActiveDocument.C636.Placement=Base.Placement(Base.Vector(11.400744,-131.708490,512.533741),Base.Rotation(-0.122384,0.707828,0.000000,0.695702))
App.ActiveDocument.addObject("Part::Cylinder","C637")
App.ActiveDocument.C637.Radius=0.750000
App.ActiveDocument.C637.Height=15.00
App.ActiveDocument.C637.Angle=360.00 
App.ActiveDocument.C637.Placement=Base.Placement(Base.Vector(11.309942,-132.515731,509.408936),Base.Rotation(-0.114053,0.731773,0.000000,0.671938))
App.ActiveDocument.addObject("Part::Cylinder","C638")
App.ActiveDocument.C638.Radius=0.750000
App.ActiveDocument.C638.Height=15.00
App.ActiveDocument.C638.Angle=360.00 
App.ActiveDocument.C638.Placement=Base.Placement(Base.Vector(11.013775,-133.205537,506.345864),Base.Rotation(-0.107344,0.752613,0.000000,0.649654))
App.ActiveDocument.addObject("Part::Cylinder","C639")
App.ActiveDocument.C639.Radius=0.750000
App.ActiveDocument.C639.Height=15.00
App.ActiveDocument.C639.Angle=360.00 
App.ActiveDocument.C639.Placement=Base.Placement(Base.Vector(10.687311,-134.362522,503.736510),Base.Rotation(-0.092512,0.769758,0.000000,0.631596))
App.ActiveDocument.addObject("Part::Cylinder","C640")
App.ActiveDocument.C640.Radius=0.750000
App.ActiveDocument.C640.Height=15.00
App.ActiveDocument.C640.Angle=360.00 
App.ActiveDocument.C640.Placement=Base.Placement(Base.Vector(10.260254,-135.519648,501.335422),Base.Rotation(-0.076344,0.784869,0.000000,0.614941))
App.ActiveDocument.addObject("Part::Cylinder","C641")
App.ActiveDocument.C641.Radius=0.750000
App.ActiveDocument.C641.Height=15.00
App.ActiveDocument.C641.Angle=360.00 
App.ActiveDocument.C641.Placement=Base.Placement(Base.Vector(9.825903,-137.274782,499.218421),Base.Rotation(-0.051174,0.797886,0.000000,0.600632))
App.ActiveDocument.addObject("Part::Cylinder","C642")
App.ActiveDocument.C642.Radius=0.750000
App.ActiveDocument.C642.Height=15.00
App.ActiveDocument.C642.Angle=360.00 
App.ActiveDocument.C642.Placement=Base.Placement(Base.Vector(12.003642,-138.103126,516.981584),Base.Rotation(-0.031343,0.683050,0.000000,0.729699))
App.ActiveDocument.addObject("Part::Cylinder","C643")
App.ActiveDocument.C643.Radius=0.750000
App.ActiveDocument.C643.Height=15.00
App.ActiveDocument.C643.Angle=360.00 
App.ActiveDocument.C643.Placement=Base.Placement(Base.Vector(11.948284,-135.934097,515.132771),Base.Rotation(-0.059076,0.697852,0.000000,0.713802))
App.ActiveDocument.addObject("Part::Cylinder","C644")
App.ActiveDocument.C644.Radius=0.750000
App.ActiveDocument.C644.Height=15.00
App.ActiveDocument.C644.Angle=360.00 
App.ActiveDocument.C644.Placement=Base.Placement(Base.Vector(11.776780,-134.243894,512.980324),Base.Rotation(-0.083544,0.710182,0.000000,0.699044))
App.ActiveDocument.addObject("Part::Cylinder","C645")
App.ActiveDocument.C645.Radius=0.750000
App.ActiveDocument.C645.Height=15.00
App.ActiveDocument.C645.Angle=360.00 
App.ActiveDocument.C645.Placement=Base.Placement(Base.Vector(11.825649,-135.663075,510.961504),Base.Rotation(-0.064461,0.727680,0.000000,0.682881))
App.ActiveDocument.addObject("Part::Cylinder","C646")
App.ActiveDocument.C646.Radius=0.750000
App.ActiveDocument.C646.Height=15.00
App.ActiveDocument.C646.Angle=360.00 
App.ActiveDocument.C646.Placement=Base.Placement(Base.Vector(11.601645,-136.279390,508.121829),Base.Rotation(-0.057778,0.746875,0.000000,0.662450))
App.ActiveDocument.addObject("Part::Cylinder","C647")
App.ActiveDocument.C647.Radius=0.750000
App.ActiveDocument.C647.Height=15.00
App.ActiveDocument.C647.Angle=360.00 
App.ActiveDocument.C647.Placement=Base.Placement(Base.Vector(11.277931,-137.290961,505.466969),Base.Rotation(-0.046385,0.763755,0.000000,0.643838))
App.ActiveDocument.addObject("Part::Cylinder","C648")
App.ActiveDocument.C648.Radius=0.750000
App.ActiveDocument.C648.Height=15.00
App.ActiveDocument.C648.Angle=360.00 
App.ActiveDocument.C648.Placement=Base.Placement(Base.Vector(10.837638,-138.374221,502.958197),Base.Rotation(-0.033196,0.778523,0.000000,0.626738))
App.ActiveDocument.addObject("Part::Cylinder","C649")
App.ActiveDocument.C649.Radius=0.750000
App.ActiveDocument.C649.Height=15.00
App.ActiveDocument.C649.Angle=360.00 
App.ActiveDocument.C649.Placement=Base.Placement(Base.Vector(12.095751,-138.408173,513.220365),Base.Rotation(-0.028989,0.714104,0.000000,0.699439))
App.ActiveDocument.addObject("Part::Cylinder","C650")
App.ActiveDocument.C650.Radius=0.750000
App.ActiveDocument.C650.Height=15.00
App.ActiveDocument.C650.Angle=360.00 
App.ActiveDocument.C650.Placement=Base.Placement(Base.Vector(11.982616,-138.429303,510.702985),Base.Rotation(-0.028916,0.731887,0.000000,0.680813))
App.ActiveDocument.addObject("Part::Cylinder","C651")
App.ActiveDocument.C651.Radius=0.750000
App.ActiveDocument.C651.Height=15.00
App.ActiveDocument.C651.Angle=360.00 
App.ActiveDocument.C651.Placement=Base.Placement(Base.Vector(11.702112,-138.784153,507.803140),Base.Rotation(-0.025333,0.750290,0.000000,0.660624))
App.ActiveDocument.addObject("Part::Cylinder","C652")
App.ActiveDocument.C652.Radius=0.750000
App.ActiveDocument.C652.Height=15.00
App.ActiveDocument.C652.Angle=360.00 
App.ActiveDocument.C652.Placement=Base.Placement(Base.Vector(-28.605020,-144.187297,548.752244),Base.Rotation(0.032848,-0.005585,0.000000,0.999445))
App.ActiveDocument.addObject("Part::Cylinder","C653")
App.ActiveDocument.C653.Radius=0.750000
App.ActiveDocument.C653.Height=15.00
App.ActiveDocument.C653.Angle=360.00 
App.ActiveDocument.C653.Placement=Base.Placement(Base.Vector(-28.636237,-147.634755,548.423559),Base.Rotation(0.062941,-0.001479,0.000000,0.998016))
App.ActiveDocument.addObject("Part::Cylinder","C654")
App.ActiveDocument.C654.Radius=0.750000
App.ActiveDocument.C654.Height=15.00
App.ActiveDocument.C654.Angle=360.00 
App.ActiveDocument.C654.Placement=Base.Placement(Base.Vector(-28.704517,-150.884555,547.907957),Base.Rotation(0.095654,0.002156,0.000000,0.995412))
App.ActiveDocument.addObject("Part::Cylinder","C655")
App.ActiveDocument.C655.Radius=0.750000
App.ActiveDocument.C655.Height=15.00
App.ActiveDocument.C655.Angle=360.00 
App.ActiveDocument.C655.Placement=Base.Placement(Base.Vector(-28.809068,-154.038878,547.189963),Base.Rotation(0.127174,0.004076,0.000000,0.991872))
App.ActiveDocument.addObject("Part::Cylinder","C656")
App.ActiveDocument.C656.Radius=0.750000
App.ActiveDocument.C656.Height=15.00
App.ActiveDocument.C656.Angle=360.00 
App.ActiveDocument.C656.Placement=Base.Placement(Base.Vector(-28.806663,-157.033562,546.273334),Base.Rotation(0.165656,0.008822,0.000000,0.986144))
App.ActiveDocument.addObject("Part::Cylinder","C657")
App.ActiveDocument.C657.Radius=0.750000
App.ActiveDocument.C657.Height=15.00
App.ActiveDocument.C657.Angle=360.00 
App.ActiveDocument.C657.Placement=Base.Placement(Base.Vector(-28.898648,-159.912602,545.140255),Base.Rotation(0.207042,0.008934,0.000000,0.978291))
App.ActiveDocument.addObject("Part::Cylinder","C658")
App.ActiveDocument.C658.Radius=0.750000
App.ActiveDocument.C658.Height=15.00
App.ActiveDocument.C658.Angle=360.00 
App.ActiveDocument.C658.Placement=Base.Placement(Base.Vector(-28.899855,-162.686745,543.765102),Base.Rotation(0.250241,0.010934,0.000000,0.968122))
App.ActiveDocument.addObject("Part::Cylinder","C659")
App.ActiveDocument.C659.Radius=0.750000
App.ActiveDocument.C659.Height=15.00
App.ActiveDocument.C659.Angle=360.00 
App.ActiveDocument.C659.Placement=Base.Placement(Base.Vector(-28.980105,-165.271725,542.185422),Base.Rotation(0.292308,0.009894,0.000000,0.956273))
App.ActiveDocument.addObject("Part::Cylinder","C660")
App.ActiveDocument.C660.Radius=0.750000
App.ActiveDocument.C660.Height=15.00
App.ActiveDocument.C660.Angle=360.00 
App.ActiveDocument.C660.Placement=Base.Placement(Base.Vector(-28.907310,-167.699843,540.371696),Base.Rotation(0.336256,0.008869,0.000000,0.941729))
App.ActiveDocument.addObject("Part::Cylinder","C661")
App.ActiveDocument.C661.Radius=0.750000
App.ActiveDocument.C661.Height=15.00
App.ActiveDocument.C661.Angle=360.00 
App.ActiveDocument.C661.Placement=Base.Placement(Base.Vector(-28.940709,-169.908916,538.375349),Base.Rotation(0.380599,0.006766,0.000000,0.924715))
App.ActiveDocument.addObject("Part::Cylinder","C662")
App.ActiveDocument.C662.Radius=0.750000
App.ActiveDocument.C662.Height=15.00
App.ActiveDocument.C662.Angle=360.00 
App.ActiveDocument.C662.Placement=Base.Placement(Base.Vector(-28.833952,-171.979642,536.118740),Base.Rotation(0.421350,0.004878,0.000000,0.906885))
App.ActiveDocument.addObject("Part::Cylinder","C663")
App.ActiveDocument.C663.Radius=0.750000
App.ActiveDocument.C663.Height=15.00
App.ActiveDocument.C663.Angle=360.00 
App.ActiveDocument.C663.Placement=Base.Placement(Base.Vector(-28.676279,-173.811833,533.712673),Base.Rotation(0.463770,0.004980,0.000000,0.885942))
App.ActiveDocument.addObject("Part::Cylinder","C664")
App.ActiveDocument.C664.Radius=0.750000
App.ActiveDocument.C664.Height=15.00
App.ActiveDocument.C664.Angle=360.00 
App.ActiveDocument.C664.Placement=Base.Placement(Base.Vector(-28.822851,-175.454001,531.097751),Base.Rotation(0.503276,0.004777,0.000000,0.864112))
App.ActiveDocument.addObject("Part::Cylinder","C665")
App.ActiveDocument.C665.Radius=0.750000
App.ActiveDocument.C665.Height=15.00
App.ActiveDocument.C665.Angle=360.00 
App.ActiveDocument.C665.Placement=Base.Placement(Base.Vector(-28.884446,-176.864957,528.344119),Base.Rotation(0.540045,0.009152,0.000000,0.841587))
App.ActiveDocument.addObject("Part::Cylinder","C666")
App.ActiveDocument.C666.Radius=0.750000
App.ActiveDocument.C666.Height=15.00
App.ActiveDocument.C666.Angle=360.00 
App.ActiveDocument.C666.Placement=Base.Placement(Base.Vector(-28.886402,-178.043336,525.477993),Base.Rotation(0.573130,0.015836,0.000000,0.819311))
App.ActiveDocument.addObject("Part::Cylinder","C667")
App.ActiveDocument.C667.Radius=0.750000
App.ActiveDocument.C667.Height=15.00
App.ActiveDocument.C667.Angle=360.00 
App.ActiveDocument.C667.Placement=Base.Placement(Base.Vector(-29.124434,-179.010808,522.484849),Base.Rotation(0.603872,0.021990,0.000000,0.796778))
App.ActiveDocument.addObject("Part::Cylinder","C668")
App.ActiveDocument.C668.Radius=0.750000
App.ActiveDocument.C668.Height=15.00
App.ActiveDocument.C668.Angle=360.00 
App.ActiveDocument.C668.Placement=Base.Placement(Base.Vector(-29.198628,-179.757951,519.378849),Base.Rotation(0.632191,0.031136,0.000000,0.774187))
App.ActiveDocument.addObject("Part::Cylinder","C669")
App.ActiveDocument.C669.Radius=0.750000
App.ActiveDocument.C669.Height=15.00
App.ActiveDocument.C669.Angle=360.00 
App.ActiveDocument.C669.Placement=Base.Placement(Base.Vector(-29.367951,-180.291943,516.210838),Base.Rotation(0.658403,0.040633,0.000000,0.751568))
App.ActiveDocument.addObject("Part::Cylinder","C670")
App.ActiveDocument.C670.Radius=0.750000
App.ActiveDocument.C670.Height=15.00
App.ActiveDocument.C670.Angle=360.00 
App.ActiveDocument.C670.Placement=Base.Placement(Base.Vector(-29.522229,-180.618707,512.994810),Base.Rotation(0.681619,0.047407,0.000000,0.730170))
App.ActiveDocument.addObject("Part::Cylinder","C671")
App.ActiveDocument.C671.Radius=0.750000
App.ActiveDocument.C671.Height=15.00
App.ActiveDocument.C671.Angle=360.00 
App.ActiveDocument.C671.Placement=Base.Placement(Base.Vector(-29.649169,-180.750708,509.613429),Base.Rotation(0.702568,0.054293,0.000000,0.709542))
App.ActiveDocument.addObject("Part::Cylinder","C672")
App.ActiveDocument.C672.Radius=0.750000
App.ActiveDocument.C672.Height=15.00
App.ActiveDocument.C672.Angle=360.00 
App.ActiveDocument.C672.Placement=Base.Placement(Base.Vector(-29.701033,-180.669340,506.137227),Base.Rotation(0.723473,0.064951,0.000000,0.687290))
App.ActiveDocument.addObject("Part::Cylinder","C673")
App.ActiveDocument.C673.Radius=0.750000
App.ActiveDocument.C673.Height=15.00
App.ActiveDocument.C673.Angle=360.00 
App.ActiveDocument.C673.Placement=Base.Placement(Base.Vector(-29.755884,-180.394116,502.752988),Base.Rotation(0.741114,0.072760,0.000000,0.667425))
App.ActiveDocument.addObject("Part::Cylinder","C674")
App.ActiveDocument.C674.Radius=0.750000
App.ActiveDocument.C674.Height=15.00
App.ActiveDocument.C674.Angle=360.00 
App.ActiveDocument.C674.Placement=Base.Placement(Base.Vector(-29.792976,-179.934882,499.395750),Base.Rotation(0.758279,0.080579,0.000000,0.646931))
App.ActiveDocument.addObject("Part::Cylinder","C675")
App.ActiveDocument.C675.Radius=0.750000
App.ActiveDocument.C675.Height=15.00
App.ActiveDocument.C675.Angle=360.00 
App.ActiveDocument.C675.Placement=Base.Placement(Base.Vector(-29.907348,-179.295653,496.015454),Base.Rotation(0.774014,0.089611,0.000000,0.626796))
App.ActiveDocument.addObject("Part::Cylinder","C676")
App.ActiveDocument.C676.Radius=0.750000
App.ActiveDocument.C676.Height=15.00
App.ActiveDocument.C676.Angle=360.00 
App.ActiveDocument.C676.Placement=Base.Placement(Base.Vector(-30.043158,-178.481763,492.675977),Base.Rotation(0.788949,0.097912,0.000000,0.606607))
App.ActiveDocument.addObject("Part::Cylinder","C677")
App.ActiveDocument.C677.Radius=0.750000
App.ActiveDocument.C677.Height=15.00
App.ActiveDocument.C677.Angle=360.00 
App.ActiveDocument.C677.Placement=Base.Placement(Base.Vector(-30.098824,-177.497240,489.421897),Base.Rotation(0.802745,0.107140,0.000000,0.586618))
App.ActiveDocument.addObject("Part::Cylinder","C678")
App.ActiveDocument.C678.Radius=0.750000
App.ActiveDocument.C678.Height=15.00
App.ActiveDocument.C678.Angle=360.00 
App.ActiveDocument.C678.Placement=Base.Placement(Base.Vector(-30.160208,-176.349378,486.241282),Base.Rotation(0.816489,0.123782,0.000000,0.563935))
App.ActiveDocument.addObject("Part::Cylinder","C679")
App.ActiveDocument.C679.Radius=0.750000
App.ActiveDocument.C679.Height=15.00
App.ActiveDocument.C679.Angle=360.00 
App.ActiveDocument.C679.Placement=Base.Placement(Base.Vector(-30.283014,-175.024537,483.074847),Base.Rotation(0.828821,0.133853,0.000000,0.543267))
App.ActiveDocument.addObject("Part::Cylinder","C680")
App.ActiveDocument.C680.Radius=0.750000
App.ActiveDocument.C680.Height=15.00
App.ActiveDocument.C680.Angle=360.00 
App.ActiveDocument.C680.Placement=Base.Placement(Base.Vector(-30.383741,-173.508968,479.956229),Base.Rotation(0.841702,0.147843,0.000000,0.519308))
App.ActiveDocument.addObject("Part::Cylinder","C681")
App.ActiveDocument.C681.Radius=0.750000
App.ActiveDocument.C681.Height=15.00
App.ActiveDocument.C681.Angle=360.00 
App.ActiveDocument.C681.Placement=Base.Placement(Base.Vector(-30.423684,-171.851828,477.011738),Base.Rotation(0.852160,0.169940,0.000000,0.494918))
App.ActiveDocument.addObject("Part::Cylinder","C682")
App.ActiveDocument.C682.Radius=0.750000
App.ActiveDocument.C682.Height=15.00
App.ActiveDocument.C682.Angle=360.00 
App.ActiveDocument.C682.Placement=Base.Placement(Base.Vector(-30.516666,-170.048181,474.193443),Base.Rotation(0.863053,0.187482,0.000000,0.469031))
App.ActiveDocument.addObject("Part::Cylinder","C683")
App.ActiveDocument.C683.Radius=0.750000
App.ActiveDocument.C683.Height=15.00
App.ActiveDocument.C683.Angle=360.00 
App.ActiveDocument.C683.Placement=Base.Placement(Base.Vector(-30.669666,-168.096188,471.516728),Base.Rotation(0.872158,0.213611,0.000000,0.440125))
App.ActiveDocument.addObject("Part::Cylinder","C684")
App.ActiveDocument.C684.Radius=0.750000
App.ActiveDocument.C684.Height=15.00
App.ActiveDocument.C684.Angle=360.00 
App.ActiveDocument.C684.Placement=Base.Placement(Base.Vector(-30.829260,-166.050621,469.089699),Base.Rotation(0.878100,0.250237,0.000000,0.407825))
App.ActiveDocument.addObject("Part::Cylinder","C685")
App.ActiveDocument.C685.Radius=0.750000
App.ActiveDocument.C685.Height=15.00
App.ActiveDocument.C685.Angle=360.00 
App.ActiveDocument.C685.Placement=Base.Placement(Base.Vector(-25.238342,-144.215558,548.675344),Base.Rotation(0.035347,0.026832,0.000000,0.999015))
App.ActiveDocument.addObject("Part::Cylinder","C686")
App.ActiveDocument.C686.Radius=0.750000
App.ActiveDocument.C686.Height=15.00
App.ActiveDocument.C686.Angle=360.00 
App.ActiveDocument.C686.Placement=Base.Placement(Base.Vector(-25.195046,-147.651248,548.327723),Base.Rotation(0.064786,0.026934,0.000000,0.997536))
App.ActiveDocument.addObject("Part::Cylinder","C687")
App.ActiveDocument.C687.Radius=0.750000
App.ActiveDocument.C687.Height=15.00
App.ActiveDocument.C687.Angle=360.00 
App.ActiveDocument.C687.Placement=Base.Placement(Base.Vector(-25.170107,-150.960519,547.785288),Base.Rotation(0.097513,0.025888,0.000000,0.994897))
App.ActiveDocument.addObject("Part::Cylinder","C688")
App.ActiveDocument.C688.Radius=0.750000
App.ActiveDocument.C688.Height=15.00
App.ActiveDocument.C688.Angle=360.00 
App.ActiveDocument.C688.Placement=Base.Placement(Base.Vector(-25.156933,-154.088877,547.056275),Base.Rotation(0.131147,0.025588,0.000000,0.991033))
App.ActiveDocument.addObject("Part::Cylinder","C689")
App.ActiveDocument.C689.Radius=0.750000
App.ActiveDocument.C689.Height=15.00
App.ActiveDocument.C689.Angle=360.00 
App.ActiveDocument.C689.Placement=Base.Placement(Base.Vector(-25.135331,-157.182361,546.092341),Base.Rotation(0.169186,0.023193,0.000000,0.985311))
App.ActiveDocument.addObject("Part::Cylinder","C690")
App.ActiveDocument.C690.Radius=0.750000
App.ActiveDocument.C690.Height=15.00
App.ActiveDocument.C690.Angle=360.00 
App.ActiveDocument.C690.Placement=Base.Placement(Base.Vector(-25.164653,-160.120941,544.915186),Base.Rotation(0.209010,0.022623,0.000000,0.977652))
App.ActiveDocument.addObject("Part::Cylinder","C691")
App.ActiveDocument.C691.Radius=0.750000
App.ActiveDocument.C691.Height=15.00
App.ActiveDocument.C691.Angle=360.00 
App.ActiveDocument.C691.Placement=Base.Placement(Base.Vector(-25.045461,-162.946326,543.485945),Base.Rotation(0.253590,0.022306,0.000000,0.967054))
App.ActiveDocument.addObject("Part::Cylinder","C692")
App.ActiveDocument.C692.Radius=0.750000
App.ActiveDocument.C692.Height=15.00
App.ActiveDocument.C692.Angle=360.00 
App.ActiveDocument.C692.Placement=Base.Placement(Base.Vector(-25.159895,-165.591965,541.839495),Base.Rotation(0.298210,0.020570,0.000000,0.954278))
App.ActiveDocument.addObject("Part::Cylinder","C693")
App.ActiveDocument.C693.Radius=0.750000
App.ActiveDocument.C693.Height=15.00
App.ActiveDocument.C693.Angle=360.00 
App.ActiveDocument.C693.Placement=Base.Placement(Base.Vector(-25.055885,-167.993950,540.000688),Base.Rotation(0.343064,0.021774,0.000000,0.939060))
App.ActiveDocument.addObject("Part::Cylinder","C694")
App.ActiveDocument.C694.Radius=0.750000
App.ActiveDocument.C694.Height=15.00
App.ActiveDocument.C694.Angle=360.00 
App.ActiveDocument.C694.Placement=Base.Placement(Base.Vector(-25.239182,-170.183476,537.982950),Base.Rotation(0.386514,0.022646,0.000000,0.922006))
App.ActiveDocument.addObject("Part::Cylinder","C695")
App.ActiveDocument.C695.Radius=0.750000
App.ActiveDocument.C695.Height=15.00
App.ActiveDocument.C695.Angle=360.00 
App.ActiveDocument.C695.Placement=Base.Placement(Base.Vector(-25.111515,-172.190526,535.724548),Base.Rotation(0.429428,0.027226,0.000000,0.902690))
App.ActiveDocument.addObject("Part::Cylinder","C696")
App.ActiveDocument.C696.Radius=0.750000
App.ActiveDocument.C696.Height=15.00
App.ActiveDocument.C696.Angle=360.00 
App.ActiveDocument.C696.Placement=Base.Placement(Base.Vector(-25.252214,-173.991999,533.274488),Base.Rotation(0.472753,0.032290,0.000000,0.880603))
App.ActiveDocument.addObject("Part::Cylinder","C697")
App.ActiveDocument.C697.Radius=0.750000
App.ActiveDocument.C697.Height=15.00
App.ActiveDocument.C697.Angle=360.00 
App.ActiveDocument.C697.Placement=Base.Placement(Base.Vector(-25.398867,-175.547646,530.688427),Base.Rotation(0.512134,0.039399,0.000000,0.858001))
App.ActiveDocument.addObject("Part::Cylinder","C698")
App.ActiveDocument.C698.Radius=0.750000
App.ActiveDocument.C698.Height=15.00
App.ActiveDocument.C698.Angle=360.00 
App.ActiveDocument.C698.Placement=Base.Placement(Base.Vector(-25.536887,-176.901361,527.895887),Base.Rotation(0.549119,0.049927,0.000000,0.834252))
App.ActiveDocument.addObject("Part::Cylinder","C699")
App.ActiveDocument.C699.Radius=0.750000
App.ActiveDocument.C699.Height=15.00
App.ActiveDocument.C699.Angle=360.00 
App.ActiveDocument.C699.Placement=Base.Placement(Base.Vector(-25.535705,-178.000780,525.000160),Base.Rotation(0.582000,0.060601,0.000000,0.810927))
App.ActiveDocument.addObject("Part::Cylinder","C700")
App.ActiveDocument.C700.Radius=0.750000
App.ActiveDocument.C700.Height=15.00
App.ActiveDocument.C700.Angle=360.00 
App.ActiveDocument.C700.Placement=Base.Placement(Base.Vector(-25.786346,-178.912570,521.958475),Base.Rotation(0.612431,0.064496,0.000000,0.787888))
App.ActiveDocument.addObject("Part::Cylinder","C701")
App.ActiveDocument.C701.Radius=0.750000
App.ActiveDocument.C701.Height=15.00
App.ActiveDocument.C701.Angle=360.00 
App.ActiveDocument.C701.Placement=Base.Placement(Base.Vector(-25.849635,-179.591247,518.790693),Base.Rotation(0.639852,0.073077,0.000000,0.765016))
App.ActiveDocument.addObject("Part::Cylinder","C702")
App.ActiveDocument.C702.Radius=0.750000
App.ActiveDocument.C702.Height=15.00
App.ActiveDocument.C702.Angle=360.00 
App.ActiveDocument.C702.Placement=Base.Placement(Base.Vector(-25.916732,-180.052338,515.572558),Base.Rotation(0.663205,0.078990,0.000000,0.744258))
App.ActiveDocument.addObject("Part::Cylinder","C703")
App.ActiveDocument.C703.Radius=0.750000
App.ActiveDocument.C703.Height=15.00
App.ActiveDocument.C703.Angle=360.00 
App.ActiveDocument.C703.Placement=Base.Placement(Base.Vector(-26.135893,-180.328176,512.264883),Base.Rotation(0.686284,0.085789,0.000000,0.722257))
App.ActiveDocument.addObject("Part::Cylinder","C704")
App.ActiveDocument.C704.Radius=0.750000
App.ActiveDocument.C704.Height=15.00
App.ActiveDocument.C704.Angle=360.00 
App.ActiveDocument.C704.Placement=Base.Placement(Base.Vector(-26.173968,-180.379129,508.895269),Base.Rotation(0.706816,0.094607,0.000000,0.701043))
App.ActiveDocument.addObject("Part::Cylinder","C705")
App.ActiveDocument.C705.Radius=0.750000
App.ActiveDocument.C705.Height=15.00
App.ActiveDocument.C705.Angle=360.00 
App.ActiveDocument.C705.Placement=Base.Placement(Base.Vector(-26.186227,-180.227491,505.528038),Base.Rotation(0.725484,0.102556,0.000000,0.680555))
App.ActiveDocument.addObject("Part::Cylinder","C706")
App.ActiveDocument.C706.Radius=0.750000
App.ActiveDocument.C706.Height=15.00
App.ActiveDocument.C706.Angle=360.00 
App.ActiveDocument.C706.Placement=Base.Placement(Base.Vector(-26.238054,-179.892711,502.182179),Base.Rotation(0.742416,0.111311,0.000000,0.660627))
App.ActiveDocument.addObject("Part::Cylinder","C707")
App.ActiveDocument.C707.Radius=0.750000
App.ActiveDocument.C707.Height=15.00
App.ActiveDocument.C707.Angle=360.00 
App.ActiveDocument.C707.Placement=Base.Placement(Base.Vector(-26.388466,-179.382084,498.801113),Base.Rotation(0.758825,0.119612,0.000000,0.640216))
App.ActiveDocument.addObject("Part::Cylinder","C708")
App.ActiveDocument.C708.Radius=0.750000
App.ActiveDocument.C708.Height=15.00
App.ActiveDocument.C708.Angle=360.00 
App.ActiveDocument.C708.Placement=Base.Placement(Base.Vector(-26.425442,-178.680335,495.493542),Base.Rotation(0.773515,0.129700,0.000000,0.620365))
App.ActiveDocument.addObject("Part::Cylinder","C709")
App.ActiveDocument.C709.Radius=0.750000
App.ActiveDocument.C709.Height=15.00
App.ActiveDocument.C709.Angle=360.00 
App.ActiveDocument.C709.Placement=Base.Placement(Base.Vector(-26.522801,-177.817333,492.226101),Base.Rotation(0.787226,0.141507,0.000000,0.600209))
App.ActiveDocument.addObject("Part::Cylinder","C710")
App.ActiveDocument.C710.Radius=0.750000
App.ActiveDocument.C710.Height=15.00
App.ActiveDocument.C710.Angle=360.00 
App.ActiveDocument.C710.Placement=Base.Placement(Base.Vector(-26.656537,-176.777855,488.974132),Base.Rotation(0.800916,0.154426,0.000000,0.578521))
App.ActiveDocument.addObject("Part::Cylinder","C711")
App.ActiveDocument.C711.Radius=0.750000
App.ActiveDocument.C711.Height=15.00
App.ActiveDocument.C711.Angle=360.00 
App.ActiveDocument.C711.Placement=Base.Placement(Base.Vector(-26.723218,-175.551678,485.775825),Base.Rotation(0.813540,0.168124,0.000000,0.556675))
App.ActiveDocument.addObject("Part::Cylinder","C712")
App.ActiveDocument.C712.Radius=0.750000
App.ActiveDocument.C712.Height=15.00
App.ActiveDocument.C712.Angle=360.00 
App.ActiveDocument.C712.Placement=Base.Placement(Base.Vector(-26.777253,-174.151364,482.651886),Base.Rotation(0.824618,0.185121,0.000000,0.534543))
App.ActiveDocument.addObject("Part::Cylinder","C713")
App.ActiveDocument.C713.Radius=0.750000
App.ActiveDocument.C713.Height=15.00
App.ActiveDocument.C713.Angle=360.00 
App.ActiveDocument.C713.Placement=Base.Placement(Base.Vector(-26.927221,-172.627943,479.664474),Base.Rotation(0.835000,0.202566,0.000000,0.511606))
App.ActiveDocument.addObject("Part::Cylinder","C714")
App.ActiveDocument.C714.Radius=0.750000
App.ActiveDocument.C714.Height=15.00
App.ActiveDocument.C714.Angle=360.00 
App.ActiveDocument.C714.Placement=Base.Placement(Base.Vector(-27.008846,-170.932484,476.795606),Base.Rotation(0.843942,0.225925,0.000000,0.486539))
App.ActiveDocument.addObject("Part::Cylinder","C715")
App.ActiveDocument.C715.Radius=0.750000
App.ActiveDocument.C715.Height=15.00
App.ActiveDocument.C715.Angle=360.00 
App.ActiveDocument.C715.Placement=Base.Placement(Base.Vector(-27.108965,-169.149748,474.156999),Base.Rotation(0.849228,0.256599,0.000000,0.461486))
App.ActiveDocument.addObject("Part::Cylinder","C716")
App.ActiveDocument.C716.Radius=0.750000
App.ActiveDocument.C716.Height=15.00
App.ActiveDocument.C716.Angle=360.00 
App.ActiveDocument.C716.Placement=Base.Placement(Base.Vector(-27.344016,-167.203221,471.604131),Base.Rotation(0.854368,0.290408,0.000000,0.430951))
App.ActiveDocument.addObject("Part::Cylinder","C717")
App.ActiveDocument.C717.Radius=0.750000
App.ActiveDocument.C717.Height=15.00
App.ActiveDocument.C717.Angle=360.00 
App.ActiveDocument.C717.Placement=Base.Placement(Base.Vector(-27.641867,-165.074363,469.185822),Base.Rotation(0.853992,0.335672,0.000000,0.397520))
App.ActiveDocument.addObject("Part::Cylinder","C718")
App.ActiveDocument.C718.Radius=0.750000
App.ActiveDocument.C718.Height=15.00
App.ActiveDocument.C718.Angle=360.00 
App.ActiveDocument.C718.Placement=Base.Placement(Base.Vector(-21.870353,-144.229242,548.385289),Base.Rotation(0.032169,0.058855,0.000000,0.997748))
App.ActiveDocument.addObject("Part::Cylinder","C719")
App.ActiveDocument.C719.Radius=0.750000
App.ActiveDocument.C719.Height=15.00
App.ActiveDocument.C719.Angle=360.00 
App.ActiveDocument.C719.Placement=Base.Placement(Base.Vector(-21.867721,-147.574913,548.067490),Base.Rotation(0.061650,0.055158,0.000000,0.996573))
App.ActiveDocument.addObject("Part::Cylinder","C720")
App.ActiveDocument.C720.Radius=0.750000
App.ActiveDocument.C720.Height=15.00
App.ActiveDocument.C720.Angle=360.00 
App.ActiveDocument.C720.Placement=Base.Placement(Base.Vector(-21.723698,-150.863305,547.534837),Base.Rotation(0.094185,0.052633,0.000000,0.994162))
App.ActiveDocument.addObject("Part::Cylinder","C721")
App.ActiveDocument.C721.Radius=0.750000
App.ActiveDocument.C721.Height=15.00
App.ActiveDocument.C721.Angle=360.00 
App.ActiveDocument.C721.Placement=Base.Placement(Base.Vector(-21.665646,-154.063882,546.799699),Base.Rotation(0.129153,0.051473,0.000000,0.990288))
App.ActiveDocument.addObject("Part::Cylinder","C722")
App.ActiveDocument.C722.Radius=0.750000
App.ActiveDocument.C722.Height=15.00
App.ActiveDocument.C722.Angle=360.00 
App.ActiveDocument.C722.Placement=Base.Placement(Base.Vector(-21.686841,-157.113067,545.864395),Base.Rotation(0.166165,0.049231,0.000000,0.984868))
App.ActiveDocument.addObject("Part::Cylinder","C723")
App.ActiveDocument.C723.Radius=0.750000
App.ActiveDocument.C723.Height=15.00
App.ActiveDocument.C723.Angle=360.00 
App.ActiveDocument.C723.Placement=Base.Placement(Base.Vector(-21.717978,-160.028316,544.708782),Base.Rotation(0.207518,0.048185,0.000000,0.977044))
App.ActiveDocument.addObject("Part::Cylinder","C724")
App.ActiveDocument.C724.Radius=0.750000
App.ActiveDocument.C724.Height=15.00
App.ActiveDocument.C724.Angle=360.00 
App.ActiveDocument.C724.Placement=Base.Placement(Base.Vector(-21.581637,-162.796823,543.304668),Base.Rotation(0.251297,0.051823,0.000000,0.966522))
App.ActiveDocument.addObject("Part::Cylinder","C725")
App.ActiveDocument.C725.Radius=0.750000
App.ActiveDocument.C725.Height=15.00
App.ActiveDocument.C725.Angle=360.00 
App.ActiveDocument.C725.Placement=Base.Placement(Base.Vector(-21.788138,-165.351983,541.738917),Base.Rotation(0.295377,0.048727,0.000000,0.954137))
App.ActiveDocument.addObject("Part::Cylinder","C726")
App.ActiveDocument.C726.Radius=0.750000
App.ActiveDocument.C726.Height=15.00
App.ActiveDocument.C726.Angle=360.00 
App.ActiveDocument.C726.Placement=Base.Placement(Base.Vector(-21.760092,-167.752724,539.903529),Base.Rotation(0.342086,0.057527,0.000000,0.937906))
App.ActiveDocument.addObject("Part::Cylinder","C727")
App.ActiveDocument.C727.Radius=0.750000
App.ActiveDocument.C727.Height=15.00
App.ActiveDocument.C727.Angle=360.00 
App.ActiveDocument.C727.Placement=Base.Placement(Base.Vector(-22.013101,-169.914528,537.923907),Base.Rotation(0.388561,0.060094,0.000000,0.919461))
App.ActiveDocument.addObject("Part::Cylinder","C728")
App.ActiveDocument.C728.Radius=0.750000
App.ActiveDocument.C728.Height=15.00
App.ActiveDocument.C728.Angle=360.00 
App.ActiveDocument.C728.Placement=Base.Placement(Base.Vector(-21.957616,-171.886659,535.671952),Base.Rotation(0.432955,0.069907,0.000000,0.898701))
App.ActiveDocument.addObject("Part::Cylinder","C729")
App.ActiveDocument.C729.Radius=0.750000
App.ActiveDocument.C729.Height=15.00
App.ActiveDocument.C729.Angle=360.00 
App.ActiveDocument.C729.Placement=Base.Placement(Base.Vector(-22.094115,-173.662353,533.222886),Base.Rotation(0.475166,0.076456,0.000000,0.876568))
App.ActiveDocument.addObject("Part::Cylinder","C730")
App.ActiveDocument.C730.Radius=0.750000
App.ActiveDocument.C730.Height=15.00
App.ActiveDocument.C730.Angle=360.00 
App.ActiveDocument.C730.Placement=Base.Placement(Base.Vector(-22.241504,-175.208265,530.605407),Base.Rotation(0.512143,0.082595,0.000000,0.854919))
App.ActiveDocument.addObject("Part::Cylinder","C731")
App.ActiveDocument.C731.Radius=0.750000
App.ActiveDocument.C731.Height=15.00
App.ActiveDocument.C731.Angle=360.00 
App.ActiveDocument.C731.Placement=Base.Placement(Base.Vector(-22.244186,-176.495381,527.855527),Base.Rotation(0.547024,0.092409,0.000000,0.832001))
App.ActiveDocument.addObject("Part::Cylinder","C732")
App.ActiveDocument.C732.Radius=0.750000
App.ActiveDocument.C732.Height=15.00
App.ActiveDocument.C732.Angle=360.00 
App.ActiveDocument.C732.Placement=Base.Placement(Base.Vector(-22.203748,-177.563913,524.940192),Base.Rotation(0.581564,0.099332,0.000000,0.807413))
App.ActiveDocument.addObject("Part::Cylinder","C733")
App.ActiveDocument.C733.Radius=0.750000
App.ActiveDocument.C733.Height=15.00
App.ActiveDocument.C733.Angle=360.00 
App.ActiveDocument.C733.Placement=Base.Placement(Base.Vector(-22.476657,-178.469880,521.889472),Base.Rotation(0.611195,0.102293,0.000000,0.784842))
App.ActiveDocument.addObject("Part::Cylinder","C734")
App.ActiveDocument.C734.Radius=0.750000
App.ActiveDocument.C734.Height=15.00
App.ActiveDocument.C734.Angle=360.00 
App.ActiveDocument.C734.Placement=Base.Placement(Base.Vector(-22.470637,-179.120285,518.701268),Base.Rotation(0.637877,0.108205,0.000000,0.762499))
App.ActiveDocument.addObject("Part::Cylinder","C735")
App.ActiveDocument.C735.Radius=0.750000
App.ActiveDocument.C735.Height=15.00
App.ActiveDocument.C735.Angle=360.00 
App.ActiveDocument.C735.Placement=Base.Placement(Base.Vector(-22.504344,-179.563534,515.383351),Base.Rotation(0.663029,0.116904,0.000000,0.739409))
App.ActiveDocument.addObject("Part::Cylinder","C736")
App.ActiveDocument.C736.Radius=0.750000
App.ActiveDocument.C736.Height=15.00
App.ActiveDocument.C736.Angle=360.00 
App.ActiveDocument.C736.Placement=Base.Placement(Base.Vector(-22.679239,-179.809873,512.053852),Base.Rotation(0.684871,0.123620,0.000000,0.718102))
App.ActiveDocument.addObject("Part::Cylinder","C737")
App.ActiveDocument.C737.Radius=0.750000
App.ActiveDocument.C737.Height=15.00
App.ActiveDocument.C737.Angle=360.00 
App.ActiveDocument.C737.Placement=Base.Placement(Base.Vector(-22.732500,-179.826589,508.663511),Base.Rotation(0.704793,0.129456,0.000000,0.697502))
App.ActiveDocument.addObject("Part::Cylinder","C738")
App.ActiveDocument.C738.Radius=0.750000
App.ActiveDocument.C738.Height=15.00
App.ActiveDocument.C738.Angle=360.00 
App.ActiveDocument.C738.Placement=Base.Placement(Base.Vector(-22.673122,-179.616035,505.257598),Base.Rotation(0.724145,0.139110,0.000000,0.675471))
App.ActiveDocument.addObject("Part::Cylinder","C739")
App.ActiveDocument.C739.Radius=0.750000
App.ActiveDocument.C739.Height=15.00
App.ActiveDocument.C739.Angle=360.00 
App.ActiveDocument.C739.Placement=Base.Placement(Base.Vector(-22.814119,-179.232839,501.765084),Base.Rotation(0.741806,0.149297,0.000000,0.653784))
App.ActiveDocument.addObject("Part::Cylinder","C740")
App.ActiveDocument.C740.Radius=0.750000
App.ActiveDocument.C740.Height=15.00
App.ActiveDocument.C740.Angle=360.00 
App.ActiveDocument.C740.Placement=Base.Placement(Base.Vector(-22.992803,-178.677730,498.393515),Base.Rotation(0.757055,0.158447,0.000000,0.633847))
App.ActiveDocument.addObject("Part::Cylinder","C741")
App.ActiveDocument.C741.Radius=0.750000
App.ActiveDocument.C741.Height=15.00
App.ActiveDocument.C741.Angle=360.00 
App.ActiveDocument.C741.Placement=Base.Placement(Base.Vector(-22.875283,-177.864840,495.027684),Base.Rotation(0.770762,0.175328,0.000000,0.612524))
App.ActiveDocument.addObject("Part::Cylinder","C742")
App.ActiveDocument.C742.Radius=0.750000
App.ActiveDocument.C742.Height=15.00
App.ActiveDocument.C742.Angle=360.00 
App.ActiveDocument.C742.Placement=Base.Placement(Base.Vector(-23.070738,-176.938020,491.710504),Base.Rotation(0.784166,0.185579,0.000000,0.592152))
App.ActiveDocument.addObject("Part::Cylinder","C743")
App.ActiveDocument.C743.Radius=0.750000
App.ActiveDocument.C743.Height=15.00
App.ActiveDocument.C743.Angle=360.00 
App.ActiveDocument.C743.Placement=Base.Placement(Base.Vector(-23.217748,-175.846074,488.509464),Base.Rotation(0.796195,0.200666,0.000000,0.570795))
App.ActiveDocument.addObject("Part::Cylinder","C744")
App.ActiveDocument.C744.Radius=0.750000
App.ActiveDocument.C744.Height=15.00
App.ActiveDocument.C744.Angle=360.00 
App.ActiveDocument.C744.Placement=Base.Placement(Base.Vector(-23.302275,-174.570435,485.385243),Base.Rotation(0.806995,0.219113,0.000000,0.548406))
App.ActiveDocument.addObject("Part::Cylinder","C745")
App.ActiveDocument.C745.Radius=0.750000
App.ActiveDocument.C745.Height=15.00
App.ActiveDocument.C745.Angle=360.00 
App.ActiveDocument.C745.Placement=Base.Placement(Base.Vector(-23.394342,-173.120452,482.333064),Base.Rotation(0.816032,0.239412,0.000000,0.526092))
App.ActiveDocument.addObject("Part::Cylinder","C746")
App.ActiveDocument.C746.Radius=0.750000
App.ActiveDocument.C746.Height=15.00
App.ActiveDocument.C746.Angle=360.00 
App.ActiveDocument.C746.Placement=Base.Placement(Base.Vector(-23.533778,-171.536059,479.421754),Base.Rotation(0.823540,0.265824,0.000000,0.501118))
App.ActiveDocument.addObject("Part::Cylinder","C747")
App.ActiveDocument.C747.Radius=0.750000
App.ActiveDocument.C747.Height=15.00
App.ActiveDocument.C747.Angle=360.00 
App.ActiveDocument.C747.Placement=Base.Placement(Base.Vector(-23.717650,-169.825217,476.670056),Base.Rotation(0.828039,0.293716,0.000000,0.477579))
App.ActiveDocument.addObject("Part::Cylinder","C748")
App.ActiveDocument.C748.Radius=0.750000
App.ActiveDocument.C748.Height=15.00
App.ActiveDocument.C748.Angle=360.00 
App.ActiveDocument.C748.Placement=Base.Placement(Base.Vector(-23.896714,-167.974845,474.088638),Base.Rotation(0.827916,0.336014,0.000000,0.449055))
App.ActiveDocument.addObject("Part::Cylinder","C749")
App.ActiveDocument.C749.Radius=0.750000
App.ActiveDocument.C749.Height=15.00
App.ActiveDocument.C749.Angle=360.00 
App.ActiveDocument.C749.Placement=Base.Placement(Base.Vector(-24.222630,-165.959570,471.596791),Base.Rotation(0.825884,0.375766,0.000000,0.420375))
App.ActiveDocument.addObject("Part::Cylinder","C750")
App.ActiveDocument.C750.Radius=0.750000
App.ActiveDocument.C750.Height=15.00
App.ActiveDocument.C750.Angle=360.00 
App.ActiveDocument.C750.Placement=Base.Placement(Base.Vector(-24.734583,-163.819353,469.255554),Base.Rotation(0.815934,0.431358,0.000000,0.384944))
App.ActiveDocument.addObject("Part::Cylinder","C751")
App.ActiveDocument.C751.Radius=0.750000
App.ActiveDocument.C751.Height=15.00
App.ActiveDocument.C751.Angle=360.00 
App.ActiveDocument.C751.Placement=Base.Placement(Base.Vector(-18.590016,-144.316020,547.876063),Base.Rotation(0.029062,0.093315,0.000000,0.995212))
App.ActiveDocument.addObject("Part::Cylinder","C752")
App.ActiveDocument.C752.Radius=0.750000
App.ActiveDocument.C752.Height=15.00
App.ActiveDocument.C752.Angle=360.00 
App.ActiveDocument.C752.Placement=Base.Placement(Base.Vector(-18.650325,-147.723217,547.580305),Base.Rotation(0.059783,0.090015,0.000000,0.994145))
App.ActiveDocument.addObject("Part::Cylinder","C753")
App.ActiveDocument.C753.Radius=0.750000
App.ActiveDocument.C753.Height=15.00
App.ActiveDocument.C753.Angle=360.00 
App.ActiveDocument.C753.Placement=Base.Placement(Base.Vector(-18.535471,-151.031755,547.043714),Base.Rotation(0.093237,0.090163,0.000000,0.991553))
App.ActiveDocument.addObject("Part::Cylinder","C754")
App.ActiveDocument.C754.Radius=0.750000
App.ActiveDocument.C754.Height=15.00
App.ActiveDocument.C754.Angle=360.00 
App.ActiveDocument.C754.Placement=Base.Placement(Base.Vector(-18.427819,-154.180684,546.300638),Base.Rotation(0.131270,0.091726,0.000000,0.987094))
App.ActiveDocument.addObject("Part::Cylinder","C755")
App.ActiveDocument.C755.Radius=0.750000
App.ActiveDocument.C755.Height=15.00
App.ActiveDocument.C755.Angle=360.00 
App.ActiveDocument.C755.Placement=Base.Placement(Base.Vector(-18.513271,-157.231349,545.364703),Base.Rotation(0.169828,0.091876,0.000000,0.981181))
App.ActiveDocument.addObject("Part::Cylinder","C756")
App.ActiveDocument.C756.Radius=0.750000
App.ActiveDocument.C756.Height=15.00
App.ActiveDocument.C756.Angle=360.00 
App.ActiveDocument.C756.Placement=Base.Placement(Base.Vector(-18.592092,-160.150760,544.188009),Base.Rotation(0.212634,0.091640,0.000000,0.972825))
App.ActiveDocument.addObject("Part::Cylinder","C757")
App.ActiveDocument.C757.Radius=0.750000
App.ActiveDocument.C757.Height=15.00
App.ActiveDocument.C757.Angle=360.00 
App.ActiveDocument.C757.Placement=Base.Placement(Base.Vector(-18.459456,-162.873113,542.746004),Base.Rotation(0.256914,0.098026,0.000000,0.961450))
App.ActiveDocument.addObject("Part::Cylinder","C758")
App.ActiveDocument.C758.Radius=0.750000
App.ActiveDocument.C758.Height=15.00
App.ActiveDocument.C758.Angle=360.00 
App.ActiveDocument.C758.Placement=Base.Placement(Base.Vector(-18.793643,-165.417671,541.170594),Base.Rotation(0.303649,0.099339,0.000000,0.947591))
App.ActiveDocument.addObject("Part::Cylinder","C759")
App.ActiveDocument.C759.Radius=0.750000
App.ActiveDocument.C759.Height=15.00
App.ActiveDocument.C759.Angle=360.00 
App.ActiveDocument.C759.Placement=Base.Placement(Base.Vector(-18.668878,-167.725898,539.296502),Base.Rotation(0.349672,0.105797,0.000000,0.930880))
App.ActiveDocument.addObject("Part::Cylinder","C760")
App.ActiveDocument.C760.Radius=0.750000
App.ActiveDocument.C760.Height=15.00
App.ActiveDocument.C760.Angle=360.00 
App.ActiveDocument.C760.Placement=Base.Placement(Base.Vector(-18.888580,-169.883562,537.242119),Base.Rotation(0.395918,0.108639,0.000000,0.911837))
App.ActiveDocument.addObject("Part::Cylinder","C761")
App.ActiveDocument.C761.Radius=0.750000
App.ActiveDocument.C761.Height=15.00
App.ActiveDocument.C761.Angle=360.00 
App.ActiveDocument.C761.Placement=Base.Placement(Base.Vector(-18.769733,-171.802678,534.893755),Base.Rotation(0.440939,0.114777,0.000000,0.890168))
App.ActiveDocument.addObject("Part::Cylinder","C762")
App.ActiveDocument.C762.Radius=0.750000
App.ActiveDocument.C762.Height=15.00
App.ActiveDocument.C762.Angle=360.00 
App.ActiveDocument.C762.Placement=Base.Placement(Base.Vector(-18.904059,-173.497060,532.434110),Base.Rotation(0.480893,0.118496,0.000000,0.868735))
App.ActiveDocument.addObject("Part::Cylinder","C763")
App.ActiveDocument.C763.Radius=0.750000
App.ActiveDocument.C763.Height=15.00
App.ActiveDocument.C763.Angle=360.00 
App.ActiveDocument.C763.Placement=Base.Placement(Base.Vector(-18.966918,-174.978693,529.752018),Base.Rotation(0.519664,0.124252,0.000000,0.845288))
App.ActiveDocument.addObject("Part::Cylinder","C764")
App.ActiveDocument.C764.Radius=0.750000
App.ActiveDocument.C764.Height=15.00
App.ActiveDocument.C764.Angle=360.00 
App.ActiveDocument.C764.Placement=Base.Placement(Base.Vector(-18.883024,-176.178355,526.959578),Base.Rotation(0.551740,0.129158,0.000000,0.823954))
App.ActiveDocument.addObject("Part::Cylinder","C765")
App.ActiveDocument.C765.Radius=0.750000
App.ActiveDocument.C765.Height=15.00
App.ActiveDocument.C765.Angle=360.00 
App.ActiveDocument.C765.Placement=Base.Placement(Base.Vector(-18.810434,-177.169779,524.005587),Base.Rotation(0.584935,0.135881,0.000000,0.799617))
App.ActiveDocument.addObject("Part::Cylinder","C766")
App.ActiveDocument.C766.Radius=0.750000
App.ActiveDocument.C766.Height=15.00
App.ActiveDocument.C766.Angle=360.00 
App.ActiveDocument.C766.Placement=Base.Placement(Base.Vector(-19.073239,-178.015811,520.945889),Base.Rotation(0.613954,0.138990,0.000000,0.777009))
App.ActiveDocument.addObject("Part::Cylinder","C767")
App.ActiveDocument.C767.Radius=0.750000
App.ActiveDocument.C767.Height=15.00
App.ActiveDocument.C767.Angle=360.00 
App.ActiveDocument.C767.Placement=Base.Placement(Base.Vector(-19.089832,-178.582559,517.823138),Base.Rotation(0.639194,0.146309,0.000000,0.755000))
App.ActiveDocument.addObject("Part::Cylinder","C768")
App.ActiveDocument.C768.Radius=0.750000
App.ActiveDocument.C768.Height=15.00
App.ActiveDocument.C768.Angle=360.00 
App.ActiveDocument.C768.Placement=Base.Placement(Base.Vector(-19.143010,-178.954391,514.555194),Base.Rotation(0.663127,0.152229,0.000000,0.732864))
App.ActiveDocument.addObject("Part::Cylinder","C769")
App.ActiveDocument.C769.Radius=0.750000
App.ActiveDocument.C769.Height=15.00
App.ActiveDocument.C769.Angle=360.00 
App.ActiveDocument.C769.Placement=Base.Placement(Base.Vector(-19.265906,-179.125493,511.248160),Base.Rotation(0.684582,0.159089,0.000000,0.711364))
App.ActiveDocument.addObject("Part::Cylinder","C770")
App.ActiveDocument.C770.Radius=0.750000
App.ActiveDocument.C770.Height=15.00
App.ActiveDocument.C770.Angle=360.00 
App.ActiveDocument.C770.Placement=Base.Placement(Base.Vector(-19.282420,-179.067648,507.944653),Base.Rotation(0.703690,0.168977,0.000000,0.690121))
App.ActiveDocument.addObject("Part::Cylinder","C771")
App.ActiveDocument.C771.Radius=0.750000
App.ActiveDocument.C771.Height=15.00
App.ActiveDocument.C771.Angle=360.00 
App.ActiveDocument.C771.Placement=Base.Placement(Base.Vector(-19.322513,-178.811234,504.596336),Base.Rotation(0.721648,0.178974,0.000000,0.668725))
App.ActiveDocument.addObject("Part::Cylinder","C772")
App.ActiveDocument.C772.Radius=0.750000
App.ActiveDocument.C772.Height=15.00
App.ActiveDocument.C772.Angle=360.00 
App.ActiveDocument.C772.Placement=Base.Placement(Base.Vector(-19.409641,-178.365365,501.219793),Base.Rotation(0.738024,0.190362,0.000000,0.647366))
App.ActiveDocument.addObject("Part::Cylinder","C773")
App.ActiveDocument.C773.Radius=0.750000
App.ActiveDocument.C773.Height=15.00
App.ActiveDocument.C773.Angle=360.00 
App.ActiveDocument.C773.Placement=Base.Placement(Base.Vector(-19.533625,-177.735702,497.862175),Base.Rotation(0.752441,0.203364,0.000000,0.626479))
App.ActiveDocument.addObject("Part::Cylinder","C774")
App.ActiveDocument.C774.Radius=0.750000
App.ActiveDocument.C774.Height=15.00
App.ActiveDocument.C774.Angle=360.00 
App.ActiveDocument.C774.Placement=Base.Placement(Base.Vector(-19.466709,-176.868675,494.564755),Base.Rotation(0.764886,0.218192,0.000000,0.606087))
App.ActiveDocument.addObject("Part::Cylinder","C775")
App.ActiveDocument.C775.Radius=0.750000
App.ActiveDocument.C775.Height=15.00
App.ActiveDocument.C775.Angle=360.00 
App.ActiveDocument.C775.Placement=Base.Placement(Base.Vector(-19.711456,-175.913145,491.332153),Base.Rotation(0.777425,0.232787,0.000000,0.584312))
App.ActiveDocument.addObject("Part::Cylinder","C776")
App.ActiveDocument.C776.Radius=0.750000
App.ActiveDocument.C776.Height=15.00
App.ActiveDocument.C776.Angle=360.00 
App.ActiveDocument.C776.Placement=Base.Placement(Base.Vector(-19.889173,-174.780486,488.207637),Base.Rotation(0.787617,0.249510,0.000000,0.563386))
App.ActiveDocument.addObject("Part::Cylinder","C777")
App.ActiveDocument.C777.Radius=0.750000
App.ActiveDocument.C777.Height=15.00
App.ActiveDocument.C777.Angle=360.00 
App.ActiveDocument.C777.Placement=Base.Placement(Base.Vector(-19.944025,-173.452265,485.194188),Base.Rotation(0.794383,0.275046,0.000000,0.541576))
App.ActiveDocument.addObject("Part::Cylinder","C778")
App.ActiveDocument.C778.Radius=0.750000
App.ActiveDocument.C778.Height=15.00
App.ActiveDocument.C778.Angle=360.00 
App.ActiveDocument.C778.Placement=Base.Placement(Base.Vector(-20.162005,-171.970244,482.200100),Base.Rotation(0.800398,0.304116,0.000000,0.516601))
App.ActiveDocument.addObject("Part::Cylinder","C779")
App.ActiveDocument.C779.Radius=0.750000
App.ActiveDocument.C779.Height=15.00
App.ActiveDocument.C779.Angle=360.00 
App.ActiveDocument.C779.Placement=Base.Placement(Base.Vector(-20.311283,-170.303692,479.352626),Base.Rotation(0.803214,0.337246,0.000000,0.491032))
App.ActiveDocument.addObject("Part::Cylinder","C780")
App.ActiveDocument.C780.Radius=0.750000
App.ActiveDocument.C780.Height=15.00
App.ActiveDocument.C780.Angle=360.00 
App.ActiveDocument.C780.Placement=Base.Placement(Base.Vector(-20.613307,-168.518750,476.624656),Base.Rotation(0.802213,0.375553,0.000000,0.464127))
App.ActiveDocument.addObject("Part::Cylinder","C781")
App.ActiveDocument.C781.Radius=0.750000
App.ActiveDocument.C781.Height=15.00
App.ActiveDocument.C781.Angle=360.00 
App.ActiveDocument.C781.Placement=Base.Placement(Base.Vector(-20.806256,-166.592491,474.152664),Base.Rotation(0.793137,0.421781,0.000000,0.439357))
App.ActiveDocument.addObject("Part::Cylinder","C782")
App.ActiveDocument.C782.Radius=0.750000
App.ActiveDocument.C782.Height=15.00
App.ActiveDocument.C782.Angle=360.00 
App.ActiveDocument.C782.Placement=Base.Placement(Base.Vector(-21.285373,-164.548661,471.742356),Base.Rotation(0.781120,0.472513,0.000000,0.408146))
App.ActiveDocument.addObject("Part::Cylinder","C783")
App.ActiveDocument.C783.Radius=0.750000
App.ActiveDocument.C783.Height=15.00
App.ActiveDocument.C783.Angle=360.00 
App.ActiveDocument.C783.Placement=Base.Placement(Base.Vector(-21.932663,-162.357535,469.456886),Base.Rotation(0.760208,0.531006,0.000000,0.374321))
App.ActiveDocument.addObject("Part::Cylinder","C784")
App.ActiveDocument.C784.Radius=0.750000
App.ActiveDocument.C784.Height=15.00
App.ActiveDocument.C784.Angle=360.00 
App.ActiveDocument.C784.Placement=Base.Placement(Base.Vector(-15.324458,-144.345404,547.129113),Base.Rotation(0.027450,0.129377,0.000000,0.991215))
App.ActiveDocument.addObject("Part::Cylinder","C785")
App.ActiveDocument.C785.Radius=0.750000
App.ActiveDocument.C785.Height=15.00
App.ActiveDocument.C785.Angle=360.00 
App.ActiveDocument.C785.Placement=Base.Placement(Base.Vector(-15.474211,-147.781631,546.864247),Base.Rotation(0.059134,0.128146,0.000000,0.989991))
App.ActiveDocument.addObject("Part::Cylinder","C786")
App.ActiveDocument.C786.Radius=0.750000
App.ActiveDocument.C786.Height=15.00
App.ActiveDocument.C786.Angle=360.00 
App.ActiveDocument.C786.Placement=Base.Placement(Base.Vector(-15.411793,-151.046139,546.332393),Base.Rotation(0.092967,0.129044,0.000000,0.987271))
App.ActiveDocument.addObject("Part::Cylinder","C787")
App.ActiveDocument.C787.Radius=0.750000
App.ActiveDocument.C787.Height=15.00
App.ActiveDocument.C787.Angle=360.00 
App.ActiveDocument.C787.Placement=Base.Placement(Base.Vector(-15.285122,-154.203549,545.559041),Base.Rotation(0.131032,0.131446,0.000000,0.982625))
App.ActiveDocument.addObject("Part::Cylinder","C788")
App.ActiveDocument.C788.Radius=0.750000
App.ActiveDocument.C788.Height=15.00
App.ActiveDocument.C788.Angle=360.00 
App.ActiveDocument.C788.Placement=Base.Placement(Base.Vector(-15.422940,-157.215201,544.628622),Base.Rotation(0.169809,0.132054,0.000000,0.976589))
App.ActiveDocument.addObject("Part::Cylinder","C789")
App.ActiveDocument.C789.Radius=0.750000
App.ActiveDocument.C789.Height=15.00
App.ActiveDocument.C789.Angle=360.00 
App.ActiveDocument.C789.Placement=Base.Placement(Base.Vector(-15.482304,-160.052744,543.453612),Base.Rotation(0.214683,0.134019,0.000000,0.967445))
App.ActiveDocument.addObject("Part::Cylinder","C790")
App.ActiveDocument.C790.Radius=0.750000
App.ActiveDocument.C790.Height=15.00
App.ActiveDocument.C790.Angle=360.00 
App.ActiveDocument.C790.Placement=Base.Placement(Base.Vector(-15.389645,-162.760887,541.974529),Base.Rotation(0.260748,0.139879,0.000000,0.955220))
App.ActiveDocument.addObject("Part::Cylinder","C791")
App.ActiveDocument.C791.Radius=0.750000
App.ActiveDocument.C791.Height=15.00
App.ActiveDocument.C791.Angle=360.00 
App.ActiveDocument.C791.Placement=Base.Placement(Base.Vector(-15.616483,-165.292364,540.347804),Base.Rotation(0.306328,0.140807,0.000000,0.941455))
App.ActiveDocument.addObject("Part::Cylinder","C792")
App.ActiveDocument.C792.Radius=0.750000
App.ActiveDocument.C792.Height=15.00
App.ActiveDocument.C792.Angle=360.00 
App.ActiveDocument.C792.Placement=Base.Placement(Base.Vector(-15.484113,-167.587699,538.385329),Base.Rotation(0.353624,0.146625,0.000000,0.923824))
App.ActiveDocument.addObject("Part::Cylinder","C793")
App.ActiveDocument.C793.Radius=0.750000
App.ActiveDocument.C793.Height=15.00
App.ActiveDocument.C793.Angle=360.00 
App.ActiveDocument.C793.Placement=Base.Placement(Base.Vector(-15.669889,-169.674845,536.315861),Base.Rotation(0.400500,0.146463,0.000000,0.904516))
App.ActiveDocument.addObject("Part::Cylinder","C794")
App.ActiveDocument.C794.Radius=0.750000
App.ActiveDocument.C794.Height=15.00
App.ActiveDocument.C794.Angle=360.00 
App.ActiveDocument.C794.Placement=Base.Placement(Base.Vector(-15.521066,-171.493236,533.958027),Base.Rotation(0.443703,0.153543,0.000000,0.882922))
App.ActiveDocument.addObject("Part::Cylinder","C795")
App.ActiveDocument.C795.Radius=0.750000
App.ActiveDocument.C795.Height=15.00
App.ActiveDocument.C795.Angle=360.00 
App.ActiveDocument.C795.Placement=Base.Placement(Base.Vector(-15.664631,-173.150361,531.460095),Base.Rotation(0.483933,0.155600,0.000000,0.861160))
App.ActiveDocument.addObject("Part::Cylinder","C796")
App.ActiveDocument.C796.Radius=0.750000
App.ActiveDocument.C796.Height=15.00
App.ActiveDocument.C796.Angle=360.00 
App.ActiveDocument.C796.Placement=Base.Placement(Base.Vector(-15.611120,-174.538654,528.749203),Base.Rotation(0.524280,0.162344,0.000000,0.835928))
App.ActiveDocument.addObject("Part::Cylinder","C797")
App.ActiveDocument.C797.Radius=0.750000
App.ActiveDocument.C797.Height=15.00
App.ActiveDocument.C797.Angle=360.00 
App.ActiveDocument.C797.Placement=Base.Placement(Base.Vector(-15.464779,-175.661801,525.898515),Base.Rotation(0.556365,0.167447,0.000000,0.813892))
App.ActiveDocument.addObject("Part::Cylinder","C798")
App.ActiveDocument.C798.Radius=0.750000
App.ActiveDocument.C798.Height=15.00
App.ActiveDocument.C798.Angle=360.00 
App.ActiveDocument.C798.Placement=Base.Placement(Base.Vector(-15.477729,-176.601484,522.925251),Base.Rotation(0.585754,0.172884,0.000000,0.791835))
App.ActiveDocument.addObject("Part::Cylinder","C799")
App.ActiveDocument.C799.Radius=0.750000
App.ActiveDocument.C799.Height=15.00
App.ActiveDocument.C799.Angle=360.00 
App.ActiveDocument.C799.Placement=Base.Placement(Base.Vector(-15.725755,-177.377605,519.867068),Base.Rotation(0.615551,0.175916,0.000000,0.768213))
App.ActiveDocument.addObject("Part::Cylinder","C800")
App.ActiveDocument.C800.Radius=0.750000
App.ActiveDocument.C800.Height=15.00
App.ActiveDocument.C800.Angle=360.00 
App.ActiveDocument.C800.Placement=Base.Placement(Base.Vector(-15.732534,-177.869292,516.700775),Base.Rotation(0.640899,0.185415,0.000000,0.744896))
App.ActiveDocument.addObject("Part::Cylinder","C801")
App.ActiveDocument.C801.Radius=0.750000
App.ActiveDocument.C801.Height=15.00
App.ActiveDocument.C801.Angle=360.00 
App.ActiveDocument.C801.Placement=Base.Placement(Base.Vector(-15.805405,-178.158811,513.478323),Base.Rotation(0.662069,0.190769,0.000000,0.724756))
App.ActiveDocument.addObject("Part::Cylinder","C802")
App.ActiveDocument.C802.Radius=0.750000
App.ActiveDocument.C802.Height=15.00
App.ActiveDocument.C802.Angle=360.00 
App.ActiveDocument.C802.Placement=Base.Placement(Base.Vector(-15.943138,-178.257140,510.293393),Base.Rotation(0.683341,0.198718,0.000000,0.702535))
App.ActiveDocument.addObject("Part::Cylinder","C803")
App.ActiveDocument.C803.Radius=0.750000
App.ActiveDocument.C803.Height=15.00
App.ActiveDocument.C803.Angle=360.00 
App.ActiveDocument.C803.Placement=Base.Placement(Base.Vector(-15.897544,-178.102149,507.057337),Base.Rotation(0.701073,0.209847,0.000000,0.681514))
App.ActiveDocument.addObject("Part::Cylinder","C804")
App.ActiveDocument.C804.Radius=0.750000
App.ActiveDocument.C804.Height=15.00
App.ActiveDocument.C804.Angle=360.00 
App.ActiveDocument.C804.Placement=Base.Placement(Base.Vector(-15.950891,-177.775653,503.774854),Base.Rotation(0.717473,0.222339,0.000000,0.660150))
App.ActiveDocument.addObject("Part::Cylinder","C805")
App.ActiveDocument.C805.Radius=0.750000
App.ActiveDocument.C805.Height=15.00
App.ActiveDocument.C805.Angle=360.00 
App.ActiveDocument.C805.Placement=Base.Placement(Base.Vector(-16.051602,-177.266913,500.489815),Base.Rotation(0.732363,0.234950,0.000000,0.639095))
App.ActiveDocument.addObject("Part::Cylinder","C806")
App.ActiveDocument.C806.Radius=0.750000
App.ActiveDocument.C806.Height=15.00
App.ActiveDocument.C806.Angle=360.00 
App.ActiveDocument.C806.Placement=Base.Placement(Base.Vector(-16.174635,-176.584496,497.266732),Base.Rotation(0.744909,0.250473,0.000000,0.618363))
App.ActiveDocument.addObject("Part::Cylinder","C807")
App.ActiveDocument.C807.Radius=0.750000
App.ActiveDocument.C807.Height=15.00
App.ActiveDocument.C807.Angle=360.00 
App.ActiveDocument.C807.Placement=Base.Placement(Base.Vector(-16.214399,-175.667026,494.014912),Base.Rotation(0.756265,0.268707,0.000000,0.596540))
App.ActiveDocument.addObject("Part::Cylinder","C808")
App.ActiveDocument.C808.Radius=0.750000
App.ActiveDocument.C808.Height=15.00
App.ActiveDocument.C808.Angle=360.00 
App.ActiveDocument.C808.Placement=Base.Placement(Base.Vector(-16.470451,-174.662424,490.884371),Base.Rotation(0.765770,0.287370,0.000000,0.575339))
App.ActiveDocument.addObject("Part::Cylinder","C809")
App.ActiveDocument.C809.Radius=0.750000
App.ActiveDocument.C809.Height=15.00
App.ActiveDocument.C809.Angle=360.00 
App.ActiveDocument.C809.Placement=Base.Placement(Base.Vector(-16.648940,-173.482170,487.896008),Base.Rotation(0.772517,0.311913,0.000000,0.553107))
App.ActiveDocument.addObject("Part::Cylinder","C810")
App.ActiveDocument.C810.Radius=0.750000
App.ActiveDocument.C810.Height=15.00
App.ActiveDocument.C810.Angle=360.00 
App.ActiveDocument.C810.Placement=Base.Placement(Base.Vector(-16.810599,-172.071705,484.894724),Base.Rotation(0.776292,0.340215,0.000000,0.530684))
App.ActiveDocument.addObject("Part::Cylinder","C811")
App.ActiveDocument.C811.Radius=0.750000
App.ActiveDocument.C811.Height=15.00
App.ActiveDocument.C811.Angle=360.00 
App.ActiveDocument.C811.Placement=Base.Placement(Base.Vector(-17.054055,-170.569877,482.085669),Base.Rotation(0.776769,0.373343,0.000000,0.507194))
App.ActiveDocument.addObject("Part::Cylinder","C812")
App.ActiveDocument.C812.Radius=0.750000
App.ActiveDocument.C812.Height=15.00
App.ActiveDocument.C812.Angle=360.00 
App.ActiveDocument.C812.Placement=Base.Placement(Base.Vector(-17.285334,-168.845592,479.329853),Base.Rotation(0.771377,0.416754,0.000000,0.480930))
App.ActiveDocument.addObject("Part::Cylinder","C813")
App.ActiveDocument.C813.Radius=0.750000
App.ActiveDocument.C813.Height=15.00
App.ActiveDocument.C813.Angle=360.00 
App.ActiveDocument.C813.Placement=Base.Placement(Base.Vector(-17.584090,-167.018588,476.768061),Base.Rotation(0.765455,0.453033,0.000000,0.456990))
App.ActiveDocument.addObject("Part::Cylinder","C814")
App.ActiveDocument.C814.Radius=0.750000
App.ActiveDocument.C814.Height=15.00
App.ActiveDocument.C814.Angle=360.00 
App.ActiveDocument.C814.Placement=Base.Placement(Base.Vector(-17.841313,-165.021781,474.396704),Base.Rotation(0.745274,0.508306,0.000000,0.431500))
App.ActiveDocument.addObject("Part::Cylinder","C815")
App.ActiveDocument.C815.Radius=0.750000
App.ActiveDocument.C815.Height=15.00
App.ActiveDocument.C815.Angle=360.00 
App.ActiveDocument.C815.Placement=Base.Placement(Base.Vector(-18.473884,-163.007409,472.095108),Base.Rotation(0.722291,0.564338,0.000000,0.399773))
App.ActiveDocument.addObject("Part::Cylinder","C816")
App.ActiveDocument.C816.Radius=0.750000
App.ActiveDocument.C816.Height=15.00
App.ActiveDocument.C816.Angle=360.00 
App.ActiveDocument.C816.Placement=Base.Placement(Base.Vector(-19.217994,-160.761166,469.873383),Base.Rotation(0.689970,0.623154,0.000000,0.368266))
App.ActiveDocument.addObject("Part::Cylinder","C817")
App.ActiveDocument.C817.Radius=0.750000
App.ActiveDocument.C817.Height=15.00
App.ActiveDocument.C817.Angle=360.00 
App.ActiveDocument.C817.Placement=Base.Placement(Base.Vector(-12.145917,-144.336469,546.167286),Base.Rotation(0.027304,0.162963,0.000000,0.986254))
App.ActiveDocument.addObject("Part::Cylinder","C818")
App.ActiveDocument.C818.Radius=0.750000
App.ActiveDocument.C818.Height=15.00
App.ActiveDocument.C818.Angle=360.00 
App.ActiveDocument.C818.Placement=Base.Placement(Base.Vector(-12.382626,-147.657700,545.948287),Base.Rotation(0.058559,0.161792,0.000000,0.985086))
App.ActiveDocument.addObject("Part::Cylinder","C819")
App.ActiveDocument.C819.Radius=0.750000
App.ActiveDocument.C819.Height=15.00
App.ActiveDocument.C819.Angle=360.00 
App.ActiveDocument.C819.Placement=Base.Placement(Base.Vector(-12.307414,-150.928701,545.401289),Base.Rotation(0.093845,0.163852,0.000000,0.982011))
App.ActiveDocument.addObject("Part::Cylinder","C820")
App.ActiveDocument.C820.Radius=0.750000
App.ActiveDocument.C820.Height=15.00
App.ActiveDocument.C820.Angle=360.00 
App.ActiveDocument.C820.Placement=Base.Placement(Base.Vector(-12.159715,-154.056924,544.601443),Base.Rotation(0.131133,0.166774,0.000000,0.977236))
App.ActiveDocument.addObject("Part::Cylinder","C821")
App.ActiveDocument.C821.Radius=0.750000
App.ActiveDocument.C821.Height=15.00
App.ActiveDocument.C821.Angle=360.00 
App.ActiveDocument.C821.Placement=Base.Placement(Base.Vector(-12.335338,-157.107538,543.659538),Base.Rotation(0.175246,0.166247,0.000000,0.970387))
App.ActiveDocument.addObject("Part::Cylinder","C822")
App.ActiveDocument.C822.Radius=0.750000
App.ActiveDocument.C822.Height=15.00
App.ActiveDocument.C822.Angle=360.00 
App.ActiveDocument.C822.Placement=Base.Placement(Base.Vector(-12.315048,-159.962227,542.409811),Base.Rotation(0.220512,0.170738,0.000000,0.960324))
App.ActiveDocument.addObject("Part::Cylinder","C823")
App.ActiveDocument.C823.Radius=0.750000
App.ActiveDocument.C823.Height=15.00
App.ActiveDocument.C823.Angle=360.00 
App.ActiveDocument.C823.Placement=Base.Placement(Base.Vector(-12.223366,-162.628081,540.887024),Base.Rotation(0.264393,0.175541,0.000000,0.948305))
App.ActiveDocument.addObject("Part::Cylinder","C824")
App.ActiveDocument.C824.Radius=0.750000
App.ActiveDocument.C824.Height=15.00
App.ActiveDocument.C824.Angle=360.00 
App.ActiveDocument.C824.Placement=Base.Placement(Base.Vector(-12.369233,-165.120556,539.202825),Base.Rotation(0.309446,0.177572,0.000000,0.934190))
App.ActiveDocument.addObject("Part::Cylinder","C825")
App.ActiveDocument.C825.Radius=0.750000
App.ActiveDocument.C825.Height=15.00
App.ActiveDocument.C825.Angle=360.00 
App.ActiveDocument.C825.Placement=Base.Placement(Base.Vector(-12.334158,-167.294613,537.297128),Base.Rotation(0.357320,0.180762,0.000000,0.916323))
App.ActiveDocument.addObject("Part::Cylinder","C826")
App.ActiveDocument.C826.Radius=0.750000
App.ActiveDocument.C826.Height=15.00
App.ActiveDocument.C826.Angle=360.00 
App.ActiveDocument.C826.Placement=Base.Placement(Base.Vector(-12.467319,-169.326647,535.191282),Base.Rotation(0.403124,0.182169,0.000000,0.896831))
App.ActiveDocument.addObject("Part::Cylinder","C827")
App.ActiveDocument.C827.Radius=0.750000
App.ActiveDocument.C827.Height=15.00
App.ActiveDocument.C827.Angle=360.00 
App.ActiveDocument.C827.Placement=Base.Placement(Base.Vector(-12.300896,-171.090383,532.766300),Base.Rotation(0.447282,0.187891,0.000000,0.874435))
App.ActiveDocument.addObject("Part::Cylinder","C828")
App.ActiveDocument.C828.Radius=0.750000
App.ActiveDocument.C828.Height=15.00
App.ActiveDocument.C828.Angle=360.00 
App.ActiveDocument.C828.Placement=Base.Placement(Base.Vector(-12.427684,-172.660362,530.277227),Base.Rotation(0.486582,0.191460,0.000000,0.852397))
App.ActiveDocument.addObject("Part::Cylinder","C829")
App.ActiveDocument.C829.Radius=0.750000
App.ActiveDocument.C829.Height=15.00
App.ActiveDocument.C829.Angle=360.00 
App.ActiveDocument.C829.Placement=Base.Placement(Base.Vector(-12.332212,-173.930433,527.602565),Base.Rotation(0.523346,0.196229,0.000000,0.829218))
App.ActiveDocument.addObject("Part::Cylinder","C830")
App.ActiveDocument.C830.Radius=0.750000
App.ActiveDocument.C830.Height=15.00
App.ActiveDocument.C830.Angle=360.00 
App.ActiveDocument.C830.Placement=Base.Placement(Base.Vector(-12.181984,-174.966377,524.746944),Base.Rotation(0.556127,0.203768,0.000000,0.805730))
App.ActiveDocument.addObject("Part::Cylinder","C831")
App.ActiveDocument.C831.Radius=0.750000
App.ActiveDocument.C831.Height=15.00
App.ActiveDocument.C831.Angle=360.00 
App.ActiveDocument.C831.Placement=Base.Placement(Base.Vector(-12.198926,-175.836586,521.748761),Base.Rotation(0.585416,0.209907,0.000000,0.783088))
App.ActiveDocument.addObject("Part::Cylinder","C832")
App.ActiveDocument.C832.Radius=0.750000
App.ActiveDocument.C832.Height=15.00
App.ActiveDocument.C832.Angle=360.00 
App.ActiveDocument.C832.Placement=Base.Placement(Base.Vector(-12.498759,-176.558078,518.738838),Base.Rotation(0.614768,0.214780,0.000000,0.758901))
App.ActiveDocument.addObject("Part::Cylinder","C833")
App.ActiveDocument.C833.Radius=0.750000
App.ActiveDocument.C833.Height=15.00
App.ActiveDocument.C833.Angle=360.00 
App.ActiveDocument.C833.Placement=Base.Placement(Base.Vector(-12.452998,-176.947006,515.560759),Base.Rotation(0.636839,0.224961,0.000000,0.737448))
App.ActiveDocument.addObject("Part::Cylinder","C834")
App.ActiveDocument.C834.Radius=0.750000
App.ActiveDocument.C834.Height=15.00
App.ActiveDocument.C834.Angle=360.00 
App.ActiveDocument.C834.Placement=Base.Placement(Base.Vector(-12.530062,-177.155474,512.317895),Base.Rotation(0.660359,0.231811,0.000000,0.714275))
App.ActiveDocument.addObject("Part::Cylinder","C835")
App.ActiveDocument.C835.Radius=0.750000
App.ActiveDocument.C835.Height=15.00
App.ActiveDocument.C835.Angle=360.00 
App.ActiveDocument.C835.Placement=Base.Placement(Base.Vector(-12.674448,-177.174159,509.182589),Base.Rotation(0.679214,0.241541,0.000000,0.693056))
App.ActiveDocument.addObject("Part::Cylinder","C836")
App.ActiveDocument.C836.Radius=0.750000
App.ActiveDocument.C836.Height=15.00
App.ActiveDocument.C836.Angle=360.00 
App.ActiveDocument.C836.Placement=Base.Placement(Base.Vector(-12.575464,-176.908714,506.038055),Base.Rotation(0.695190,0.253791,0.000000,0.672534))
App.ActiveDocument.addObject("Part::Cylinder","C837")
App.ActiveDocument.C837.Radius=0.750000
App.ActiveDocument.C837.Height=15.00
App.ActiveDocument.C837.Angle=360.00 
App.ActiveDocument.C837.Placement=Base.Placement(Base.Vector(-12.711798,-176.525241,502.823523),Base.Rotation(0.710023,0.269625,0.000000,0.650515))
App.ActiveDocument.addObject("Part::Cylinder","C838")
App.ActiveDocument.C838.Radius=0.750000
App.ActiveDocument.C838.Height=15.00
App.ActiveDocument.C838.Angle=360.00 
App.ActiveDocument.C838.Placement=Base.Placement(Base.Vector(-12.824153,-175.934675,499.615084),Base.Rotation(0.723177,0.284952,0.000000,0.629140))
App.ActiveDocument.addObject("Part::Cylinder","C839")
App.ActiveDocument.C839.Radius=0.750000
App.ActiveDocument.C839.Height=15.00
App.ActiveDocument.C839.Angle=360.00 
App.ActiveDocument.C839.Placement=Base.Placement(Base.Vector(-12.979272,-175.164849,496.428635),Base.Rotation(0.733638,0.304507,0.000000,0.607495))
App.ActiveDocument.addObject("Part::Cylinder","C840")
App.ActiveDocument.C840.Radius=0.750000
App.ActiveDocument.C840.Height=15.00
App.ActiveDocument.C840.Angle=360.00 
App.ActiveDocument.C840.Placement=Base.Placement(Base.Vector(-13.134830,-174.196275,493.286916),Base.Rotation(0.742745,0.326228,0.000000,0.584727))
App.ActiveDocument.addObject("Part::Cylinder","C841")
App.ActiveDocument.C841.Radius=0.750000
App.ActiveDocument.C841.Height=15.00
App.ActiveDocument.C841.Angle=360.00 
App.ActiveDocument.C841.Placement=Base.Placement(Base.Vector(-13.427251,-173.118265,490.253774),Base.Rotation(0.746873,0.354614,0.000000,0.562521))
App.ActiveDocument.addObject("Part::Cylinder","C842")
App.ActiveDocument.C842.Radius=0.750000
App.ActiveDocument.C842.Height=15.00
App.ActiveDocument.C842.Angle=360.00 
App.ActiveDocument.C842.Placement=Base.Placement(Base.Vector(-13.673020,-171.882159,487.384338),Base.Rotation(0.748366,0.384021,0.000000,0.540811))
App.ActiveDocument.addObject("Part::Cylinder","C843")
App.ActiveDocument.C843.Radius=0.750000
App.ActiveDocument.C843.Height=15.00
App.ActiveDocument.C843.Angle=360.00 
App.ActiveDocument.C843.Placement=Base.Placement(Base.Vector(-13.828432,-170.404075,484.576507),Base.Rotation(0.746834,0.416657,0.000000,0.518301))
App.ActiveDocument.addObject("Part::Cylinder","C844")
App.ActiveDocument.C844.Radius=0.750000
App.ActiveDocument.C844.Height=15.00
App.ActiveDocument.C844.Angle=360.00 
App.ActiveDocument.C844.Placement=Base.Placement(Base.Vector(-14.160564,-168.840878,481.860243),Base.Rotation(0.741122,0.454305,0.000000,0.494313))
App.ActiveDocument.addObject("Part::Cylinder","C845")
App.ActiveDocument.C845.Radius=0.750000
App.ActiveDocument.C845.Height=15.00
App.ActiveDocument.C845.Angle=360.00 
App.ActiveDocument.C845.Placement=Base.Placement(Base.Vector(-14.355233,-167.022776,479.286680),Base.Rotation(0.725913,0.502160,0.000000,0.469984))
App.ActiveDocument.addObject("Part::Cylinder","C846")
App.ActiveDocument.C846.Radius=0.750000
App.ActiveDocument.C846.Height=15.00
App.ActiveDocument.C846.Angle=360.00 
App.ActiveDocument.C846.Placement=Base.Placement(Base.Vector(-14.815442,-165.194309,476.837127),Base.Rotation(0.711851,0.542793,0.000000,0.445696))
App.ActiveDocument.addObject("Part::Cylinder","C847")
App.ActiveDocument.C847.Radius=0.750000
App.ActiveDocument.C847.Height=15.00
App.ActiveDocument.C847.Angle=360.00 
App.ActiveDocument.C847.Placement=Base.Placement(Base.Vector(-15.040793,-163.123587,474.667211),Base.Rotation(0.678666,0.602646,0.000000,0.419799))
App.ActiveDocument.addObject("Part::Cylinder","C848")
App.ActiveDocument.C848.Radius=0.750000
App.ActiveDocument.C848.Height=15.00
App.ActiveDocument.C848.Angle=360.00 
App.ActiveDocument.C848.Placement=Base.Placement(Base.Vector(-15.828809,-161.046706,472.391361),Base.Rotation(0.648521,0.652791,0.000000,0.391516))
App.ActiveDocument.addObject("Part::Cylinder","C849")
App.ActiveDocument.C849.Radius=0.750000
App.ActiveDocument.C849.Height=15.00
App.ActiveDocument.C849.Angle=360.00 
App.ActiveDocument.C849.Placement=Base.Placement(Base.Vector(-16.775881,-158.802075,470.224830),Base.Rotation(0.606813,0.708370,0.000000,0.360541))
App.ActiveDocument.addObject("Part::Cylinder","C850")
App.ActiveDocument.C850.Radius=0.750000
App.ActiveDocument.C850.Height=15.00
App.ActiveDocument.C850.Angle=360.00 
App.ActiveDocument.C850.Placement=Base.Placement(Base.Vector(-9.003466,-144.268969,544.976797),Base.Rotation(0.026794,0.197304,0.000000,0.979976))
App.ActiveDocument.addObject("Part::Cylinder","C851")
App.ActiveDocument.C851.Radius=0.750000
App.ActiveDocument.C851.Height=15.00
App.ActiveDocument.C851.Angle=360.00 
App.ActiveDocument.C851.Placement=Base.Placement(Base.Vector(-9.375069,-147.558259,544.829062),Base.Rotation(0.058461,0.194015,0.000000,0.979255))
App.ActiveDocument.addObject("Part::Cylinder","C852")
App.ActiveDocument.C852.Radius=0.750000
App.ActiveDocument.C852.Height=15.00
App.ActiveDocument.C852.Angle=360.00 
App.ActiveDocument.C852.Placement=Base.Placement(Base.Vector(-9.129649,-150.750723,544.208819),Base.Rotation(0.093741,0.198828,0.000000,0.975541))
App.ActiveDocument.addObject("Part::Cylinder","C853")
App.ActiveDocument.C853.Radius=0.750000
App.ActiveDocument.C853.Height=15.00
App.ActiveDocument.C853.Angle=360.00 
App.ActiveDocument.C853.Placement=Base.Placement(Base.Vector(-9.035572,-153.868653,543.404380),Base.Rotation(0.132702,0.202348,0.000000,0.970281))
App.ActiveDocument.addObject("Part::Cylinder","C854")
App.ActiveDocument.C854.Radius=0.750000
App.ActiveDocument.C854.Height=15.00
App.ActiveDocument.C854.Angle=360.00 
App.ActiveDocument.C854.Placement=Base.Placement(Base.Vector(-9.327903,-156.841169,542.526335),Base.Rotation(0.174280,0.202072,0.000000,0.963739))
App.ActiveDocument.addObject("Part::Cylinder","C855")
App.ActiveDocument.C855.Radius=0.750000
App.ActiveDocument.C855.Height=15.00
App.ActiveDocument.C855.Angle=360.00 
App.ActiveDocument.C855.Placement=Base.Placement(Base.Vector(-9.219119,-159.625194,541.239711),Base.Rotation(0.217905,0.205323,0.000000,0.954128))
App.ActiveDocument.addObject("Part::Cylinder","C856")
App.ActiveDocument.C856.Radius=0.750000
App.ActiveDocument.C856.Height=15.00
App.ActiveDocument.C856.Angle=360.00 
App.ActiveDocument.C856.Placement=Base.Placement(Base.Vector(-9.092313,-162.280485,539.656344),Base.Rotation(0.264898,0.211036,0.000000,0.940900))
App.ActiveDocument.addObject("Part::Cylinder","C857")
App.ActiveDocument.C857.Radius=0.750000
App.ActiveDocument.C857.Height=15.00
App.ActiveDocument.C857.Angle=360.00 
App.ActiveDocument.C857.Placement=Base.Placement(Base.Vector(-9.195834,-164.687533,537.971088),Base.Rotation(0.312360,0.212864,0.000000,0.925808))
App.ActiveDocument.addObject("Part::Cylinder","C858")
App.ActiveDocument.C858.Radius=0.750000
App.ActiveDocument.C858.Height=15.00
App.ActiveDocument.C858.Angle=360.00 
App.ActiveDocument.C858.Placement=Base.Placement(Base.Vector(-9.194728,-166.913786,535.957276),Base.Rotation(0.360346,0.217808,0.000000,0.907034))
App.ActiveDocument.addObject("Part::Cylinder","C859")
App.ActiveDocument.C859.Radius=0.750000
App.ActiveDocument.C859.Height=15.00
App.ActiveDocument.C859.Angle=360.00 
App.ActiveDocument.C859.Placement=Base.Placement(Base.Vector(-9.300787,-168.878935,533.818464),Base.Rotation(0.406883,0.221297,0.000000,0.886269))
App.ActiveDocument.addObject("Part::Cylinder","C860")
App.ActiveDocument.C860.Radius=0.750000
App.ActiveDocument.C860.Height=15.00
App.ActiveDocument.C860.Angle=360.00 
App.ActiveDocument.C860.Placement=Base.Placement(Base.Vector(-9.111629,-170.552971,531.339576),Base.Rotation(0.446806,0.227777,0.000000,0.865149))
App.ActiveDocument.addObject("Part::Cylinder","C861")
App.ActiveDocument.C861.Radius=0.750000
App.ActiveDocument.C861.Height=15.00
App.ActiveDocument.C861.Angle=360.00 
App.ActiveDocument.C861.Placement=Base.Placement(Base.Vector(-9.285348,-172.015552,528.938516),Base.Rotation(0.486262,0.228163,0.000000,0.843499))
App.ActiveDocument.addObject("Part::Cylinder","C862")
App.ActiveDocument.C862.Radius=0.750000
App.ActiveDocument.C862.Height=15.00
App.ActiveDocument.C862.Angle=360.00 
App.ActiveDocument.C862.Placement=Base.Placement(Base.Vector(-9.094112,-173.146627,526.266718),Base.Rotation(0.521809,0.236344,0.000000,0.819669))
App.ActiveDocument.addObject("Part::Cylinder","C863")
App.ActiveDocument.C863.Radius=0.750000
App.ActiveDocument.C863.Height=15.00
App.ActiveDocument.C863.Angle=360.00 
App.ActiveDocument.C863.Placement=Base.Placement(Base.Vector(-9.058421,-174.120962,523.458849),Base.Rotation(0.552489,0.244191,0.000000,0.796949))
App.ActiveDocument.addObject("Part::Cylinder","C864")
App.ActiveDocument.C864.Radius=0.750000
App.ActiveDocument.C864.Height=15.00
App.ActiveDocument.C864.Angle=360.00 
App.ActiveDocument.C864.Placement=Base.Placement(Base.Vector(-9.041660,-174.886437,520.471181),Base.Rotation(0.583562,0.252144,0.000000,0.771932))
App.ActiveDocument.addObject("Part::Cylinder","C865")
App.ActiveDocument.C865.Radius=0.750000
App.ActiveDocument.C865.Height=15.00
App.ActiveDocument.C865.Angle=360.00 
App.ActiveDocument.C865.Placement=Base.Placement(Base.Vector(-9.291076,-175.520349,517.459202),Base.Rotation(0.610634,0.255770,0.000000,0.749472))
App.ActiveDocument.addObject("Part::Cylinder","C866")
App.ActiveDocument.C866.Radius=0.750000
App.ActiveDocument.C866.Height=15.00
App.ActiveDocument.C866.Angle=360.00 
App.ActiveDocument.C866.Placement=Base.Placement(Base.Vector(-9.289058,-175.825213,514.335956),Base.Rotation(0.632015,0.266585,0.000000,0.727660))
App.ActiveDocument.addObject("Part::Cylinder","C867")
App.ActiveDocument.C867.Radius=0.750000
App.ActiveDocument.C867.Height=15.00
App.ActiveDocument.C867.Angle=360.00 
App.ActiveDocument.C867.Placement=Base.Placement(Base.Vector(-9.412477,-175.958499,511.169090),Base.Rotation(0.653474,0.278149,0.000000,0.703992))
App.ActiveDocument.addObject("Part::Cylinder","C868")
App.ActiveDocument.C868.Radius=0.750000
App.ActiveDocument.C868.Height=15.00
App.ActiveDocument.C868.Angle=360.00 
App.ActiveDocument.C868.Placement=Base.Placement(Base.Vector(-9.468957,-175.855415,508.106291),Base.Rotation(0.670798,0.289191,0.000000,0.682934))
App.ActiveDocument.addObject("Part::Cylinder","C869")
App.ActiveDocument.C869.Radius=0.750000
App.ActiveDocument.C869.Height=15.00
App.ActiveDocument.C869.Angle=360.00 
App.ActiveDocument.C869.Placement=Base.Placement(Base.Vector(-9.520870,-175.541867,504.971506),Base.Rotation(0.685460,0.306334,0.000000,0.660533))
App.ActiveDocument.addObject("Part::Cylinder","C870")
App.ActiveDocument.C870.Radius=0.750000
App.ActiveDocument.C870.Height=15.00
App.ActiveDocument.C870.Angle=360.00 
App.ActiveDocument.C870.Placement=Base.Placement(Base.Vector(-9.633653,-175.039377,501.783842),Base.Rotation(0.697368,0.326549,0.000000,0.638000))
App.ActiveDocument.addObject("Part::Cylinder","C871")
App.ActiveDocument.C871.Radius=0.750000
App.ActiveDocument.C871.Height=15.00
App.ActiveDocument.C871.Angle=360.00 
App.ActiveDocument.C871.Placement=Base.Placement(Base.Vector(-9.827297,-174.390058,498.710794),Base.Rotation(0.706864,0.346972,0.000000,0.616404))
App.ActiveDocument.addObject("Part::Cylinder","C872")
App.ActiveDocument.C872.Radius=0.750000
App.ActiveDocument.C872.Height=15.00
App.ActiveDocument.C872.Angle=360.00 
App.ActiveDocument.C872.Placement=Base.Placement(Base.Vector(-9.994831,-173.532530,495.675623),Base.Rotation(0.713940,0.369434,0.000000,0.594818))
App.ActiveDocument.addObject("Part::Cylinder","C873")
App.ActiveDocument.C873.Radius=0.750000
App.ActiveDocument.C873.Height=15.00
App.ActiveDocument.C873.Angle=360.00 
App.ActiveDocument.C873.Placement=Base.Placement(Base.Vector(-10.263359,-172.525641,492.664748),Base.Rotation(0.716036,0.400193,0.000000,0.571960))
App.ActiveDocument.addObject("Part::Cylinder","C874")
App.ActiveDocument.C874.Radius=0.750000
App.ActiveDocument.C874.Height=15.00
App.ActiveDocument.C874.Angle=360.00 
App.ActiveDocument.C874.Placement=Base.Placement(Base.Vector(-10.499993,-171.334658,489.771723),Base.Rotation(0.716532,0.429190,0.000000,0.549889))
App.ActiveDocument.addObject("Part::Cylinder","C875")
App.ActiveDocument.C875.Radius=0.750000
App.ActiveDocument.C875.Height=15.00
App.ActiveDocument.C875.Angle=360.00 
App.ActiveDocument.C875.Placement=Base.Placement(Base.Vector(-10.785150,-169.984650,486.956080),Base.Rotation(0.712611,0.461659,0.000000,0.528259))
App.ActiveDocument.addObject("Part::Cylinder","C876")
App.ActiveDocument.C876.Radius=0.750000
App.ActiveDocument.C876.Height=15.00
App.ActiveDocument.C876.Angle=360.00 
App.ActiveDocument.C876.Placement=Base.Placement(Base.Vector(-11.027116,-168.460772,484.298858),Base.Rotation(0.704986,0.497147,0.000000,0.505805))
App.ActiveDocument.addObject("Part::Cylinder","C877")
App.ActiveDocument.C877.Radius=0.750000
App.ActiveDocument.C877.Height=15.00
App.ActiveDocument.C877.Angle=360.00 
App.ActiveDocument.C877.Placement=Base.Placement(Base.Vector(-11.302979,-166.762325,481.732873),Base.Rotation(0.691222,0.538384,0.000000,0.482032))
App.ActiveDocument.addObject("Part::Cylinder","C878")
App.ActiveDocument.C878.Radius=0.750000
App.ActiveDocument.C878.Height=15.00
App.ActiveDocument.C878.Angle=360.00 
App.ActiveDocument.C878.Placement=Base.Placement(Base.Vector(-11.612393,-164.898163,479.295341),Base.Rotation(0.668556,0.585214,0.000000,0.458866))
App.ActiveDocument.addObject("Part::Cylinder","C879")
App.ActiveDocument.C879.Radius=0.750000
App.ActiveDocument.C879.Height=15.00
App.ActiveDocument.C879.Angle=360.00 
App.ActiveDocument.C879.Placement=Base.Placement(Base.Vector(-12.040714,-163.039413,477.077940),Base.Rotation(0.646505,0.625292,0.000000,0.437083))
App.ActiveDocument.addObject("Part::Cylinder","C880")
App.ActiveDocument.C880.Radius=0.750000
App.ActiveDocument.C880.Height=15.00
App.ActiveDocument.C880.Angle=360.00 
App.ActiveDocument.C880.Placement=Base.Placement(Base.Vector(-12.482388,-160.860926,474.896863),Base.Rotation(0.601833,0.685878,0.000000,0.409107))
App.ActiveDocument.addObject("Part::Cylinder","C881")
App.ActiveDocument.C881.Radius=0.750000
App.ActiveDocument.C881.Height=15.00
App.ActiveDocument.C881.Angle=360.00 
App.ActiveDocument.C881.Placement=Base.Placement(Base.Vector(-13.360875,-158.758093,472.737684),Base.Rotation(0.565620,0.729160,0.000000,0.385226))
App.ActiveDocument.addObject("Part::Cylinder","C882")
App.ActiveDocument.C882.Radius=0.750000
App.ActiveDocument.C882.Height=15.00
App.ActiveDocument.C882.Angle=360.00 
App.ActiveDocument.C882.Placement=Base.Placement(Base.Vector(-14.433926,-156.547067,470.691333),Base.Rotation(0.514147,0.780507,0.000000,0.355614))
App.ActiveDocument.addObject("Part::Cylinder","C883")
App.ActiveDocument.C883.Radius=0.750000
App.ActiveDocument.C883.Height=15.00
App.ActiveDocument.C883.Angle=360.00 
App.ActiveDocument.C883.Placement=Base.Placement(Base.Vector(-6.030893,-144.245860,543.604575),Base.Rotation(0.028161,0.231560,0.000000,0.972413))
App.ActiveDocument.addObject("Part::Cylinder","C884")
App.ActiveDocument.C884.Radius=0.750000
App.ActiveDocument.C884.Height=15.00
App.ActiveDocument.C884.Angle=360.00 
App.ActiveDocument.C884.Placement=Base.Placement(Base.Vector(-6.419548,-147.546792,543.484563),Base.Rotation(0.059949,0.228360,0.000000,0.971729))
App.ActiveDocument.addObject("Part::Cylinder","C885")
App.ActiveDocument.C885.Radius=0.750000
App.ActiveDocument.C885.Height=15.00
App.ActiveDocument.C885.Angle=360.00 
App.ActiveDocument.C885.Placement=Base.Placement(Base.Vector(-6.123135,-150.703466,542.797593),Base.Rotation(0.095657,0.234629,0.000000,0.967367))
App.ActiveDocument.addObject("Part::Cylinder","C886")
App.ActiveDocument.C886.Radius=0.750000
App.ActiveDocument.C886.Height=15.00
App.ActiveDocument.C886.Angle=360.00 
App.ActiveDocument.C886.Placement=Base.Placement(Base.Vector(-6.076769,-153.862746,541.959645),Base.Rotation(0.134872,0.236505,0.000000,0.962224))
App.ActiveDocument.addObject("Part::Cylinder","C887")
App.ActiveDocument.C887.Radius=0.750000
App.ActiveDocument.C887.Height=15.00
App.ActiveDocument.C887.Angle=360.00 
App.ActiveDocument.C887.Placement=Base.Placement(Base.Vector(-6.324389,-156.793144,541.049571),Base.Rotation(0.176021,0.235995,0.000000,0.955679))
App.ActiveDocument.addObject("Part::Cylinder","C888")
App.ActiveDocument.C888.Radius=0.750000
App.ActiveDocument.C888.Height=15.00
App.ActiveDocument.C888.Angle=360.00 
App.ActiveDocument.C888.Placement=Base.Placement(Base.Vector(-6.213188,-159.487119,539.721981),Base.Rotation(0.221583,0.241134,0.000000,0.944857))
App.ActiveDocument.addObject("Part::Cylinder","C889")
App.ActiveDocument.C889.Radius=0.750000
App.ActiveDocument.C889.Height=15.00
App.ActiveDocument.C889.Angle=360.00 
App.ActiveDocument.C889.Placement=Base.Placement(Base.Vector(-6.119462,-162.035160,538.125885),Base.Rotation(0.270729,0.246897,0.000000,0.930456))
App.ActiveDocument.addObject("Part::Cylinder","C890")
App.ActiveDocument.C890.Radius=0.750000
App.ActiveDocument.C890.Height=15.00
App.ActiveDocument.C890.Angle=360.00 
App.ActiveDocument.C890.Placement=Base.Placement(Base.Vector(-6.286830,-164.422769,536.409940),Base.Rotation(0.316744,0.248050,0.000000,0.915503))
App.ActiveDocument.addObject("Part::Cylinder","C891")
App.ActiveDocument.C891.Radius=0.750000
App.ActiveDocument.C891.Height=15.00
App.ActiveDocument.C891.Angle=360.00 
App.ActiveDocument.C891.Placement=Base.Placement(Base.Vector(-6.183636,-166.473750,534.370477),Base.Rotation(0.363079,0.255174,0.000000,0.896136))
App.ActiveDocument.addObject("Part::Cylinder","C892")
App.ActiveDocument.C892.Radius=0.750000
App.ActiveDocument.C892.Height=15.00
App.ActiveDocument.C892.Angle=360.00 
App.ActiveDocument.C892.Placement=Base.Placement(Base.Vector(-6.222614,-168.314169,532.205107),Base.Rotation(0.405921,0.258098,0.000000,0.876706))
App.ActiveDocument.addObject("Part::Cylinder","C893")
App.ActiveDocument.C893.Radius=0.750000
App.ActiveDocument.C893.Height=15.00
App.ActiveDocument.C893.Angle=360.00 
App.ActiveDocument.C893.Placement=Base.Placement(Base.Vector(-6.018555,-169.834613,529.748022),Base.Rotation(0.447879,0.267573,0.000000,0.853117))
App.ActiveDocument.addObject("Part::Cylinder","C894")
App.ActiveDocument.C894.Radius=0.750000
App.ActiveDocument.C894.Height=15.00
App.ActiveDocument.C894.Angle=360.00 
App.ActiveDocument.C894.Placement=Base.Placement(Base.Vector(-6.159461,-171.248834,527.237579),Base.Rotation(0.487088,0.270931,0.000000,0.830266))
App.ActiveDocument.addObject("Part::Cylinder","C895")
App.ActiveDocument.C895.Radius=0.750000
App.ActiveDocument.C895.Height=15.00
App.ActiveDocument.C895.Angle=360.00 
App.ActiveDocument.C895.Placement=Base.Placement(Base.Vector(-5.971119,-172.256747,524.549520),Base.Rotation(0.520858,0.280843,0.000000,0.806123))
App.ActiveDocument.addObject("Part::Cylinder","C896")
App.ActiveDocument.C896.Radius=0.750000
App.ActiveDocument.C896.Height=15.00
App.ActiveDocument.C896.Angle=360.00 
App.ActiveDocument.C896.Placement=Base.Placement(Base.Vector(-6.050000,-173.149824,521.809590),Base.Rotation(0.551377,0.288937,0.000000,0.782623))
App.ActiveDocument.addObject("Part::Cylinder","C897")
App.ActiveDocument.C897.Radius=0.750000
App.ActiveDocument.C897.Height=15.00
App.ActiveDocument.C897.Angle=360.00 
App.ActiveDocument.C897.Placement=Base.Placement(Base.Vector(-6.120683,-173.842213,518.812294),Base.Rotation(0.580376,0.294188,0.000000,0.759353))
App.ActiveDocument.addObject("Part::Cylinder","C898")
App.ActiveDocument.C898.Radius=0.750000
App.ActiveDocument.C898.Height=15.00
App.ActiveDocument.C898.Angle=360.00 
App.ActiveDocument.C898.Placement=Base.Placement(Base.Vector(-6.308375,-174.327072,515.954128),Base.Rotation(0.603144,0.302810,0.000000,0.737918))
App.ActiveDocument.addObject("Part::Cylinder","C899")
App.ActiveDocument.C899.Radius=0.750000
App.ActiveDocument.C899.Height=15.00
App.ActiveDocument.C899.Angle=360.00 
App.ActiveDocument.C899.Placement=Base.Placement(Base.Vector(-6.314163,-174.511770,512.946194),Base.Rotation(0.625160,0.314897,0.000000,0.714153))
App.ActiveDocument.addObject("Part::Cylinder","C900")
App.ActiveDocument.C900.Radius=0.750000
App.ActiveDocument.C900.Height=15.00
App.ActiveDocument.C900.Angle=360.00 
App.ActiveDocument.C900.Placement=Base.Placement(Base.Vector(-6.368507,-174.501012,509.896866),Base.Rotation(0.641532,0.331866,0.000000,0.691594))
App.ActiveDocument.addObject("Part::Cylinder","C901")
App.ActiveDocument.C901.Radius=0.750000
App.ActiveDocument.C901.Height=15.00
App.ActiveDocument.C901.Angle=360.00 
App.ActiveDocument.C901.Placement=Base.Placement(Base.Vector(-6.521547,-174.324902,506.849491),Base.Rotation(0.655867,0.350164,0.000000,0.668748))
App.ActiveDocument.addObject("Part::Cylinder","C902")
App.ActiveDocument.C902.Radius=0.750000
App.ActiveDocument.C902.Height=15.00
App.ActiveDocument.C902.Angle=360.00 
App.ActiveDocument.C902.Placement=Base.Placement(Base.Vector(-6.590476,-173.900101,503.840727),Base.Rotation(0.665708,0.370529,0.000000,0.647720))
App.ActiveDocument.addObject("Part::Cylinder","C903")
App.ActiveDocument.C903.Radius=0.750000
App.ActiveDocument.C903.Height=15.00
App.ActiveDocument.C903.Angle=360.00 
App.ActiveDocument.C903.Placement=Base.Placement(Base.Vector(-6.775553,-173.309688,500.749713),Base.Rotation(0.675739,0.392895,0.000000,0.623707))
App.ActiveDocument.addObject("Part::Cylinder","C904")
App.ActiveDocument.C904.Radius=0.750000
App.ActiveDocument.C904.Height=15.00
App.ActiveDocument.C904.Angle=360.00 
App.ActiveDocument.C904.Placement=Base.Placement(Base.Vector(-7.014163,-172.547373,497.718329),Base.Rotation(0.680908,0.417981,0.000000,0.601379))
App.ActiveDocument.addObject("Part::Cylinder","C905")
App.ActiveDocument.C905.Radius=0.750000
App.ActiveDocument.C905.Height=15.00
App.ActiveDocument.C905.Angle=360.00 
App.ActiveDocument.C905.Placement=Base.Placement(Base.Vector(-7.194637,-171.575806,494.802539),Base.Rotation(0.681769,0.446077,0.000000,0.579833))
App.ActiveDocument.addObject("Part::Cylinder","C906")
App.ActiveDocument.C906.Radius=0.750000
App.ActiveDocument.C906.Height=15.00
App.ActiveDocument.C906.Angle=360.00 
App.ActiveDocument.C906.Placement=Base.Placement(Base.Vector(-7.555335,-170.476697,491.846816),Base.Rotation(0.681991,0.473451,0.000000,0.557434))
App.ActiveDocument.addObject("Part::Cylinder","C907")
App.ActiveDocument.C907.Radius=0.750000
App.ActiveDocument.C907.Height=15.00
App.ActiveDocument.C907.Angle=360.00 
App.ActiveDocument.C907.Placement=Base.Placement(Base.Vector(-7.694634,-169.133491,489.168691),Base.Rotation(0.674313,0.507112,0.000000,0.536786))
App.ActiveDocument.addObject("Part::Cylinder","C908")
App.ActiveDocument.C908.Radius=0.750000
App.ActiveDocument.C908.Height=15.00
App.ActiveDocument.C908.Angle=360.00 
App.ActiveDocument.C908.Placement=Base.Placement(Base.Vector(-8.093172,-167.773653,486.532386),Base.Rotation(0.669880,0.534036,0.000000,0.515816))
App.ActiveDocument.addObject("Part::Cylinder","C909")
App.ActiveDocument.C909.Radius=0.750000
App.ActiveDocument.C909.Height=15.00
App.ActiveDocument.C909.Angle=360.00 
App.ActiveDocument.C909.Placement=Base.Placement(Base.Vector(-8.278256,-166.120892,484.083118),Base.Rotation(0.650258,0.578220,0.000000,0.492774))
App.ActiveDocument.addObject("Part::Cylinder","C910")
App.ActiveDocument.C910.Radius=0.750000
App.ActiveDocument.C910.Height=15.00
App.ActiveDocument.C910.Angle=360.00 
App.ActiveDocument.C910.Placement=Base.Placement(Base.Vector(-8.663378,-164.438940,481.714893),Base.Rotation(0.630222,0.616275,0.000000,0.472256))
App.ActiveDocument.addObject("Part::Cylinder","C911")
App.ActiveDocument.C911.Radius=0.750000
App.ActiveDocument.C911.Height=15.00
App.ActiveDocument.C911.Angle=360.00 
App.ActiveDocument.C911.Placement=Base.Placement(Base.Vector(-8.964611,-162.430612,479.419775),Base.Rotation(0.600030,0.661728,0.000000,0.449534))
App.ActiveDocument.addObject("Part::Cylinder","C912")
App.ActiveDocument.C912.Radius=0.750000
App.ActiveDocument.C912.Height=15.00
App.ActiveDocument.C912.Angle=360.00 
App.ActiveDocument.C912.Placement=Base.Placement(Base.Vector(-9.476329,-160.510923,477.314796),Base.Rotation(0.572159,0.699946,0.000000,0.427445))
App.ActiveDocument.addObject("Part::Cylinder","C913")
App.ActiveDocument.C913.Radius=0.750000
App.ActiveDocument.C913.Height=15.00
App.ActiveDocument.C913.Angle=360.00 
App.ActiveDocument.C913.Placement=Base.Placement(Base.Vector(-10.020335,-158.295450,475.267685),Base.Rotation(0.529213,0.745814,0.000000,0.404593))
App.ActiveDocument.addObject("Part::Cylinder","C914")
App.ActiveDocument.C914.Radius=0.750000
App.ActiveDocument.C914.Height=15.00
App.ActiveDocument.C914.Angle=360.00 
App.ActiveDocument.C914.Placement=Base.Placement(Base.Vector(-10.977578,-156.185388,473.235118),Base.Rotation(0.479693,0.791472,0.000000,0.378770))
App.ActiveDocument.addObject("Part::Cylinder","C915")
App.ActiveDocument.C915.Radius=0.750000
App.ActiveDocument.C915.Height=15.00
App.ActiveDocument.C915.Angle=360.00 
App.ActiveDocument.C915.Placement=Base.Placement(Base.Vector(-12.198230,-154.016627,471.270642),Base.Rotation(0.422717,0.835360,0.000000,0.351402))
App.ActiveDocument.addObject("Part::Cylinder","C916")
App.ActiveDocument.C916.Radius=0.750000
App.ActiveDocument.C916.Height=15.00
App.ActiveDocument.C916.Angle=360.00 
App.ActiveDocument.C916.Placement=Base.Placement(Base.Vector(-3.162123,-144.250892,542.013346),Base.Rotation(0.028771,0.269099,0.000000,0.962683))
App.ActiveDocument.addObject("Part::Cylinder","C917")
App.ActiveDocument.C917.Radius=0.750000
App.ActiveDocument.C917.Height=15.00
App.ActiveDocument.C917.Angle=360.00 
App.ActiveDocument.C917.Placement=Base.Placement(Base.Vector(-3.542800,-147.559370,541.907592),Base.Rotation(0.061686,0.265262,0.000000,0.962201))
App.ActiveDocument.addObject("Part::Cylinder","C918")
App.ActiveDocument.C918.Radius=0.750000
App.ActiveDocument.C918.Height=15.00
App.ActiveDocument.C918.Angle=360.00 
App.ActiveDocument.C918.Placement=Base.Placement(Base.Vector(-3.245416,-150.728088,541.154719),Base.Rotation(0.098193,0.271955,0.000000,0.957287))
App.ActiveDocument.addObject("Part::Cylinder","C919")
App.ActiveDocument.C919.Radius=0.750000
App.ActiveDocument.C919.Height=15.00
App.ActiveDocument.C919.Angle=360.00 
App.ActiveDocument.C919.Placement=Base.Placement(Base.Vector(-3.213550,-153.806583,540.291674),Base.Rotation(0.138704,0.275383,0.000000,0.951276))
App.ActiveDocument.addObject("Part::Cylinder","C920")
App.ActiveDocument.C920.Radius=0.750000
App.ActiveDocument.C920.Height=15.00
App.ActiveDocument.C920.Angle=360.00 
App.ActiveDocument.C920.Placement=Base.Placement(Base.Vector(-3.494461,-156.679236,539.389912),Base.Rotation(0.180980,0.276876,0.000000,0.943709))
App.ActiveDocument.addObject("Part::Cylinder","C921")
App.ActiveDocument.C921.Radius=0.750000
App.ActiveDocument.C921.Height=15.00
App.ActiveDocument.C921.Angle=360.00 
App.ActiveDocument.C921.Placement=Base.Placement(Base.Vector(-3.403681,-159.339431,537.999457),Base.Rotation(0.226597,0.281929,0.000000,0.932293))
App.ActiveDocument.addObject("Part::Cylinder","C922")
App.ActiveDocument.C922.Radius=0.750000
App.ActiveDocument.C922.Height=15.00
App.ActiveDocument.C922.Angle=360.00 
App.ActiveDocument.C922.Placement=Base.Placement(Base.Vector(-3.261710,-161.754834,536.337598),Base.Rotation(0.270958,0.289294,0.000000,0.918091))
App.ActiveDocument.addObject("Part::Cylinder","C923")
App.ActiveDocument.C923.Radius=0.750000
App.ActiveDocument.C923.Height=15.00
App.ActiveDocument.C923.Angle=360.00 
App.ActiveDocument.C923.Placement=Base.Placement(Base.Vector(-3.496568,-164.013449,534.682527),Base.Rotation(0.318141,0.286977,0.000000,0.903565))
App.ActiveDocument.addObject("Part::Cylinder","C924")
App.ActiveDocument.C924.Radius=0.750000
App.ActiveDocument.C924.Height=15.00
App.ActiveDocument.C924.Angle=360.00 
App.ActiveDocument.C924.Placement=Base.Placement(Base.Vector(-3.327384,-165.904036,532.599888),Base.Rotation(0.361449,0.297385,0.000000,0.883695))
App.ActiveDocument.addObject("Part::Cylinder","C925")
App.ActiveDocument.C925.Radius=0.750000
App.ActiveDocument.C925.Height=15.00
App.ActiveDocument.C925.Angle=360.00 
App.ActiveDocument.C925.Placement=Base.Placement(Base.Vector(-3.350529,-167.635462,530.407175),Base.Rotation(0.405133,0.303496,0.000000,0.862414))
App.ActiveDocument.addObject("Part::Cylinder","C926")
App.ActiveDocument.C926.Radius=0.750000
App.ActiveDocument.C926.Height=15.00
App.ActiveDocument.C926.Angle=360.00 
App.ActiveDocument.C926.Placement=Base.Placement(Base.Vector(-3.187786,-169.026500,527.962792),Base.Rotation(0.446579,0.310868,0.000000,0.839004))
App.ActiveDocument.addObject("Part::Cylinder","C927")
App.ActiveDocument.C927.Radius=0.750000
App.ActiveDocument.C927.Height=15.00
App.ActiveDocument.C927.Angle=360.00 
App.ActiveDocument.C927.Placement=Base.Placement(Base.Vector(-3.231463,-170.287998,525.414991),Base.Rotation(0.482264,0.319990,0.000000,0.815493))
App.ActiveDocument.addObject("Part::Cylinder","C928")
App.ActiveDocument.C928.Radius=0.750000
App.ActiveDocument.C928.Height=15.00
App.ActiveDocument.C928.Angle=360.00 
App.ActiveDocument.C928.Placement=Base.Placement(Base.Vector(-3.125235,-171.206604,522.711124),Base.Rotation(0.513778,0.327233,0.000000,0.793064))
App.ActiveDocument.addObject("Part::Cylinder","C929")
App.ActiveDocument.C929.Radius=0.750000
App.ActiveDocument.C929.Height=15.00
App.ActiveDocument.C929.Angle=360.00 
App.ActiveDocument.C929.Placement=Base.Placement(Base.Vector(-3.162956,-171.958571,519.950480),Base.Rotation(0.543281,0.337465,0.000000,0.768741))
App.ActiveDocument.addObject("Part::Cylinder","C930")
App.ActiveDocument.C930.Radius=0.750000
App.ActiveDocument.C930.Height=15.00
App.ActiveDocument.C930.Angle=360.00 
App.ActiveDocument.C930.Placement=Base.Placement(Base.Vector(-3.326849,-172.552156,517.060572),Base.Rotation(0.570419,0.346930,0.000000,0.744488))
App.ActiveDocument.addObject("Part::Cylinder","C931")
App.ActiveDocument.C931.Radius=0.750000
App.ActiveDocument.C931.Height=15.00
App.ActiveDocument.C931.Angle=360.00 
App.ActiveDocument.C931.Placement=Base.Placement(Base.Vector(-3.449518,-172.877343,514.223228),Base.Rotation(0.590711,0.360644,0.000000,0.721801))
App.ActiveDocument.addObject("Part::Cylinder","C932")
App.ActiveDocument.C932.Radius=0.750000
App.ActiveDocument.C932.Height=15.00
App.ActiveDocument.C932.Angle=360.00 
App.ActiveDocument.C932.Placement=Base.Placement(Base.Vector(-3.512749,-172.943095,511.297949),Base.Rotation(0.607921,0.379400,0.000000,0.697487))
App.ActiveDocument.addObject("Part::Cylinder","C933")
App.ActiveDocument.C933.Radius=0.750000
App.ActiveDocument.C933.Height=15.00
App.ActiveDocument.C933.Angle=360.00 
App.ActiveDocument.C933.Placement=Base.Placement(Base.Vector(-3.682226,-172.843810,508.306387),Base.Rotation(0.622894,0.396766,0.000000,0.674225))
App.ActiveDocument.addObject("Part::Cylinder","C934")
App.ActiveDocument.C934.Radius=0.750000
App.ActiveDocument.C934.Height=15.00
App.ActiveDocument.C934.Angle=360.00 
App.ActiveDocument.C934.Placement=Base.Placement(Base.Vector(-3.612337,-172.388784,505.426064),Base.Rotation(0.630780,0.418901,0.000000,0.653176))
App.ActiveDocument.addObject("Part::Cylinder","C935")
App.ActiveDocument.C935.Radius=0.750000
App.ActiveDocument.C935.Height=15.00
App.ActiveDocument.C935.Angle=360.00 
App.ActiveDocument.C935.Placement=Base.Placement(Base.Vector(-3.981089,-171.983007,502.420790),Base.Rotation(0.641571,0.439563,0.000000,0.628626))
App.ActiveDocument.addObject("Part::Cylinder","C936")
App.ActiveDocument.C936.Radius=0.750000
App.ActiveDocument.C936.Height=15.00
App.ActiveDocument.C936.Angle=360.00 
App.ActiveDocument.C936.Placement=Base.Placement(Base.Vector(-4.085617,-171.204636,499.512524),Base.Rotation(0.646411,0.458407,0.000000,0.609931))
App.ActiveDocument.addObject("Part::Cylinder","C937")
App.ActiveDocument.C937.Radius=0.750000
App.ActiveDocument.C937.Height=15.00
App.ActiveDocument.C937.Angle=360.00 
App.ActiveDocument.C937.Placement=Base.Placement(Base.Vector(-4.314100,-170.376350,496.817140),Base.Rotation(0.645051,0.487811,0.000000,0.588175))
App.ActiveDocument.addObject("Part::Cylinder","C938")
App.ActiveDocument.C938.Radius=0.750000
App.ActiveDocument.C938.Height=15.00
App.ActiveDocument.C938.Angle=360.00 
App.ActiveDocument.C938.Placement=Base.Placement(Base.Vector(-4.666053,-169.353263,493.934097),Base.Rotation(0.642497,0.516354,0.000000,0.566195))
App.ActiveDocument.addObject("Part::Cylinder","C939")
App.ActiveDocument.C939.Radius=0.750000
App.ActiveDocument.C939.Height=15.00
App.ActiveDocument.C939.Angle=360.00 
App.ActiveDocument.C939.Placement=Base.Placement(Base.Vector(-4.869828,-168.116068,491.313152),Base.Rotation(0.634348,0.547542,0.000000,0.545711))
App.ActiveDocument.addObject("Part::Cylinder","C940")
App.ActiveDocument.C940.Radius=0.750000
App.ActiveDocument.C940.Height=15.00
App.ActiveDocument.C940.Angle=360.00 
App.ActiveDocument.C940.Placement=Base.Placement(Base.Vector(-5.199152,-166.634884,488.531947),Base.Rotation(0.621924,0.583022,0.000000,0.522777))
App.ActiveDocument.addObject("Part::Cylinder","C941")
App.ActiveDocument.C941.Radius=0.750000
App.ActiveDocument.C941.Height=15.00
App.ActiveDocument.C941.Angle=360.00 
App.ActiveDocument.C941.Placement=Base.Placement(Base.Vector(-5.520070,-165.198201,486.186176),Base.Rotation(0.606699,0.615278,0.000000,0.503338))
App.ActiveDocument.addObject("Part::Cylinder","C942")
App.ActiveDocument.C942.Radius=0.750000
App.ActiveDocument.C942.Height=15.00
App.ActiveDocument.C942.Angle=360.00 
App.ActiveDocument.C942.Placement=Base.Placement(Base.Vector(-5.765634,-163.466558,483.899699),Base.Rotation(0.585633,0.650601,0.000000,0.483480))
App.ActiveDocument.addObject("Part::Cylinder","C943")
App.ActiveDocument.C943.Radius=0.750000
App.ActiveDocument.C943.Height=15.00
App.ActiveDocument.C943.Angle=360.00 
App.ActiveDocument.C943.Placement=Base.Placement(Base.Vector(-6.174991,-161.732034,481.716748),Base.Rotation(0.561240,0.686162,0.000000,0.462808))
App.ActiveDocument.addObject("Part::Cylinder","C944")
App.ActiveDocument.C944.Radius=0.750000
App.ActiveDocument.C944.Height=15.00
App.ActiveDocument.C944.Angle=360.00 
App.ActiveDocument.C944.Placement=Base.Placement(Base.Vector(-6.543913,-159.625063,479.561473),Base.Rotation(0.526905,0.726654,0.000000,0.440846))
App.ActiveDocument.addObject("Part::Cylinder","C945")
App.ActiveDocument.C945.Radius=0.750000
App.ActiveDocument.C945.Height=15.00
App.ActiveDocument.C945.Angle=360.00 
App.ActiveDocument.C945.Placement=Base.Placement(Base.Vector(-7.123563,-157.610814,477.555938),Base.Rotation(0.497951,0.758243,0.000000,0.420848))
App.ActiveDocument.addObject("Part::Cylinder","C946")
App.ActiveDocument.C946.Radius=0.750000
App.ActiveDocument.C946.Height=15.00
App.ActiveDocument.C946.Angle=360.00 
App.ActiveDocument.C946.Placement=Base.Placement(Base.Vector(-7.781632,-155.335807,475.612029),Base.Rotation(0.449454,0.800278,0.000000,0.396921))
App.ActiveDocument.addObject("Part::Cylinder","C947")
App.ActiveDocument.C947.Radius=0.750000
App.ActiveDocument.C947.Height=15.00
App.ActiveDocument.C947.Angle=360.00 
App.ActiveDocument.C947.Placement=Base.Placement(Base.Vector(-8.826879,-153.237660,473.700390),Base.Rotation(0.401823,0.837272,0.000000,0.370829))
App.ActiveDocument.addObject("Part::Cylinder","C948")
App.ActiveDocument.C948.Radius=0.750000
App.ActiveDocument.C948.Height=15.00
App.ActiveDocument.C948.Angle=360.00 
App.ActiveDocument.C948.Placement=Base.Placement(Base.Vector(-10.336810,-151.143667,471.705952),Base.Rotation(0.352923,0.870378,0.000000,0.343348))
App.ActiveDocument.addObject("Part::Cylinder","C949")
App.ActiveDocument.C949.Radius=0.750000
App.ActiveDocument.C949.Height=15.00
App.ActiveDocument.C949.Angle=360.00 
App.ActiveDocument.C949.Placement=Base.Placement(Base.Vector(-0.515376,-144.220003,540.266895),Base.Rotation(0.028380,0.306830,0.000000,0.951341))
App.ActiveDocument.addObject("Part::Cylinder","C950")
App.ActiveDocument.C950.Radius=0.750000
App.ActiveDocument.C950.Height=15.00
App.ActiveDocument.C950.Angle=360.00 
App.ActiveDocument.C950.Placement=Base.Placement(Base.Vector(-0.887063,-147.405124,540.194637),Base.Rotation(0.061605,0.302862,0.000000,0.951041))
App.ActiveDocument.addObject("Part::Cylinder","C951")
App.ActiveDocument.C951.Radius=0.750000
App.ActiveDocument.C951.Height=15.00
App.ActiveDocument.C951.Angle=360.00 
App.ActiveDocument.C951.Placement=Base.Placement(Base.Vector(-0.548488,-150.560917,539.352722),Base.Rotation(0.098672,0.310214,0.000000,0.945532))
App.ActiveDocument.addObject("Part::Cylinder","C952")
App.ActiveDocument.C952.Radius=0.750000
App.ActiveDocument.C952.Height=15.00
App.ActiveDocument.C952.Angle=360.00 
App.ActiveDocument.C952.Placement=Base.Placement(Base.Vector(-0.595166,-153.650027,538.494161),Base.Rotation(0.140909,0.313231,0.000000,0.939165))
App.ActiveDocument.addObject("Part::Cylinder","C953")
App.ActiveDocument.C953.Radius=0.750000
App.ActiveDocument.C953.Height=15.00
App.ActiveDocument.C953.Angle=360.00 
App.ActiveDocument.C953.Placement=Base.Placement(Base.Vector(-0.768317,-156.511688,537.476202),Base.Rotation(0.183616,0.315819,0.000000,0.930883))
App.ActiveDocument.addObject("Part::Cylinder","C954")
App.ActiveDocument.C954.Radius=0.750000
App.ActiveDocument.C954.Height=15.00
App.ActiveDocument.C954.Angle=360.00 
App.ActiveDocument.C954.Placement=Base.Placement(Base.Vector(-0.677729,-159.000642,536.072019),Base.Rotation(0.226843,0.321901,0.000000,0.919196))
App.ActiveDocument.addObject("Part::Cylinder","C955")
App.ActiveDocument.C955.Radius=0.750000
App.ActiveDocument.C955.Height=15.00
App.ActiveDocument.C955.Angle=360.00 
App.ActiveDocument.C955.Placement=Base.Placement(Base.Vector(-0.607370,-161.426564,534.323931),Base.Rotation(0.275264,0.328547,0.000000,0.903486))
App.ActiveDocument.addObject("Part::Cylinder","C956")
App.ActiveDocument.C956.Radius=0.750000
App.ActiveDocument.C956.Height=15.00
App.ActiveDocument.C956.Angle=360.00 
App.ActiveDocument.C956.Placement=Base.Placement(Base.Vector(-0.756918,-163.534411,532.606814),Base.Rotation(0.321652,0.333394,0.000000,0.886221))
App.ActiveDocument.addObject("Part::Cylinder","C957")
App.ActiveDocument.C957.Radius=0.750000
App.ActiveDocument.C957.Height=15.00
App.ActiveDocument.C957.Angle=360.00 
App.ActiveDocument.C957.Placement=Base.Placement(Base.Vector(-0.621399,-165.331624,530.439711),Base.Rotation(0.364786,0.343286,0.000000,0.865498))
App.ActiveDocument.addObject("Part::Cylinder","C958")
App.ActiveDocument.C958.Radius=0.750000
App.ActiveDocument.C958.Height=15.00
App.ActiveDocument.C958.Angle=360.00 
App.ActiveDocument.C958.Placement=Base.Placement(Base.Vector(-0.539357,-166.833037,528.201830),Base.Rotation(0.403064,0.350104,0.000000,0.845557))
App.ActiveDocument.addObject("Part::Cylinder","C959")
App.ActiveDocument.C959.Radius=0.750000
App.ActiveDocument.C959.Height=15.00
App.ActiveDocument.C959.Angle=360.00 
App.ActiveDocument.C959.Placement=Base.Placement(Base.Vector(-0.572269,-168.121411,525.906198),Base.Rotation(0.444206,0.359056,0.000000,0.820829))
App.ActiveDocument.addObject("Part::Cylinder","C960")
App.ActiveDocument.C960.Radius=0.750000
App.ActiveDocument.C960.Height=15.00
App.ActiveDocument.C960.Angle=360.00 
App.ActiveDocument.C960.Placement=Base.Placement(Base.Vector(-0.451579,-169.127946,523.289524),Base.Rotation(0.475579,0.371094,0.000000,0.797568))
App.ActiveDocument.addObject("Part::Cylinder","C961")
App.ActiveDocument.C961.Radius=0.750000
App.ActiveDocument.C961.Height=15.00
App.ActiveDocument.C961.Angle=360.00 
App.ActiveDocument.C961.Placement=Base.Placement(Base.Vector(-0.469252,-169.960313,520.592256),Base.Rotation(0.504441,0.385750,0.000000,0.772487))
App.ActiveDocument.addObject("Part::Cylinder","C962")
App.ActiveDocument.C962.Radius=0.750000
App.ActiveDocument.C962.Height=15.00
App.ActiveDocument.C962.Angle=360.00 
App.ActiveDocument.C962.Placement=Base.Placement(Base.Vector(-0.672580,-170.674508,517.758708),Base.Rotation(0.528603,0.396653,0.000000,0.750497))
App.ActiveDocument.addObject("Part::Cylinder","C963")
App.ActiveDocument.C963.Radius=0.750000
App.ActiveDocument.C963.Height=15.00
App.ActiveDocument.C963.Angle=360.00 
App.ActiveDocument.C963.Placement=Base.Placement(Base.Vector(-0.684901,-170.974356,515.000442),Base.Rotation(0.554693,0.410973,0.000000,0.723475))
App.ActiveDocument.addObject("Part::Cylinder","C964")
App.ActiveDocument.C964.Radius=0.750000
App.ActiveDocument.C964.Height=15.00
App.ActiveDocument.C964.Angle=360.00 
App.ActiveDocument.C964.Placement=Base.Placement(Base.Vector(-0.783334,-171.103039,512.217347),Base.Rotation(0.569643,0.428562,0.000000,0.701315))
App.ActiveDocument.addObject("Part::Cylinder","C965")
App.ActiveDocument.C965.Radius=0.750000
App.ActiveDocument.C965.Height=15.00
App.ActiveDocument.C965.Angle=360.00 
App.ActiveDocument.C965.Placement=Base.Placement(Base.Vector(-0.956297,-171.052319,509.328427),Base.Rotation(0.582770,0.447070,0.000000,0.678607))
App.ActiveDocument.addObject("Part::Cylinder","C966")
App.ActiveDocument.C966.Radius=0.750000
App.ActiveDocument.C966.Height=15.00
App.ActiveDocument.C966.Angle=360.00 
App.ActiveDocument.C966.Placement=Base.Placement(Base.Vector(-1.043456,-170.731464,506.560974),Base.Rotation(0.591323,0.468881,0.000000,0.656115))
App.ActiveDocument.addObject("Part::Cylinder","C967")
App.ActiveDocument.C967.Radius=0.750000
App.ActiveDocument.C967.Height=15.00
App.ActiveDocument.C967.Angle=360.00 
App.ActiveDocument.C967.Placement=Base.Placement(Base.Vector(-1.243777,-170.245241,503.630680),Base.Rotation(0.598967,0.490423,0.000000,0.633028))
App.ActiveDocument.addObject("Part::Cylinder","C968")
App.ActiveDocument.C968.Radius=0.750000
App.ActiveDocument.C968.Height=15.00
App.ActiveDocument.C968.Angle=360.00 
App.ActiveDocument.C968.Placement=Base.Placement(Base.Vector(-1.455640,-169.566367,500.782568),Base.Rotation(0.601384,0.514022,0.000000,0.611652))
App.ActiveDocument.addObject("Part::Cylinder","C969")
App.ActiveDocument.C969.Radius=0.750000
App.ActiveDocument.C969.Height=15.00
App.ActiveDocument.C969.Angle=360.00 
App.ActiveDocument.C969.Placement=Base.Placement(Base.Vector(-1.717718,-168.741906,498.030209),Base.Rotation(0.600008,0.540383,0.000000,0.589896))
App.ActiveDocument.addObject("Part::Cylinder","C970")
App.ActiveDocument.C970.Radius=0.750000
App.ActiveDocument.C970.Height=15.00
App.ActiveDocument.C970.Angle=360.00 
App.ActiveDocument.C970.Placement=Base.Placement(Base.Vector(-1.877727,-167.691778,495.472655),Base.Rotation(0.593927,0.566114,0.000000,0.571634))
App.ActiveDocument.addObject("Part::Cylinder","C971")
App.ActiveDocument.C971.Radius=0.750000
App.ActiveDocument.C971.Height=15.00
App.ActiveDocument.C971.Angle=360.00 
App.ActiveDocument.C971.Placement=Base.Placement(Base.Vector(-2.205664,-166.639805,493.001334),Base.Rotation(0.584667,0.594684,0.000000,0.551829))
App.ActiveDocument.addObject("Part::Cylinder","C972")
App.ActiveDocument.C972.Radius=0.750000
App.ActiveDocument.C972.Height=15.00
App.ActiveDocument.C972.Angle=360.00 
App.ActiveDocument.C972.Placement=Base.Placement(Base.Vector(-2.540231,-165.301758,490.425747),Base.Rotation(0.576757,0.619459,0.000000,0.532562))
App.ActiveDocument.addObject("Part::Cylinder","C973")
App.ActiveDocument.C973.Radius=0.750000
App.ActiveDocument.C973.Height=15.00
App.ActiveDocument.C973.Angle=360.00 
App.ActiveDocument.C973.Placement=Base.Placement(Base.Vector(-2.766836,-163.638748,487.938666),Base.Rotation(0.558909,0.652547,0.000000,0.511667))
App.ActiveDocument.addObject("Part::Cylinder","C974")
App.ActiveDocument.C974.Radius=0.750000
App.ActiveDocument.C974.Height=15.00
App.ActiveDocument.C974.Angle=360.00 
App.ActiveDocument.C974.Placement=Base.Placement(Base.Vector(-3.147816,-162.016058,485.629583),Base.Rotation(0.536688,0.685766,0.000000,0.491620))
App.ActiveDocument.addObject("Part::Cylinder","C975")
App.ActiveDocument.C975.Radius=0.750000
App.ActiveDocument.C975.Height=15.00
App.ActiveDocument.C975.Angle=360.00 
App.ActiveDocument.C975.Placement=Base.Placement(Base.Vector(-3.382085,-160.182940,483.600313),Base.Rotation(0.508549,0.719087,0.000000,0.473595))
App.ActiveDocument.addObject("Part::Cylinder","C976")
App.ActiveDocument.C976.Radius=0.750000
App.ActiveDocument.C976.Height=15.00
App.ActiveDocument.C976.Angle=360.00 
App.ActiveDocument.C976.Placement=Base.Placement(Base.Vector(-3.906272,-158.531894,481.630256),Base.Rotation(0.482577,0.748918,0.000000,0.454137))
App.ActiveDocument.addObject("Part::Cylinder","C977")
App.ActiveDocument.C977.Radius=0.750000
App.ActiveDocument.C977.Height=15.00
App.ActiveDocument.C977.Angle=360.00 
App.ActiveDocument.C977.Placement=Base.Placement(Base.Vector(-4.216709,-156.373321,479.791449),Base.Rotation(0.449835,0.778785,0.000000,0.437198))
App.ActiveDocument.addObject("Part::Cylinder","C978")
App.ActiveDocument.C978.Radius=0.750000
App.ActiveDocument.C978.Height=15.00
App.ActiveDocument.C978.Angle=360.00 
App.ActiveDocument.C978.Placement=Base.Placement(Base.Vector(-4.913292,-154.434985,477.928965),Base.Rotation(0.418209,0.806939,0.000000,0.417075))
App.ActiveDocument.addObject("Part::Cylinder","C979")
App.ActiveDocument.C979.Radius=0.750000
App.ActiveDocument.C979.Height=15.00
App.ActiveDocument.C979.Angle=360.00 
App.ActiveDocument.C979.Placement=Base.Placement(Base.Vector(-5.699876,-152.180922,476.080211),Base.Rotation(0.380556,0.837465,0.000000,0.392211))
App.ActiveDocument.addObject("Part::Cylinder","C980")
App.ActiveDocument.C980.Radius=0.750000
App.ActiveDocument.C980.Height=15.00
App.ActiveDocument.C980.Angle=360.00 
App.ActiveDocument.C980.Placement=Base.Placement(Base.Vector(-6.932743,-150.020971,474.139032),Base.Rotation(0.336188,0.867965,0.000000,0.365532))
App.ActiveDocument.addObject("Part::Cylinder","C981")
App.ActiveDocument.C981.Radius=0.750000
App.ActiveDocument.C981.Height=15.00
App.ActiveDocument.C981.Angle=360.00 
App.ActiveDocument.C981.Placement=Base.Placement(Base.Vector(-8.638622,-148.074724,472.175630),Base.Rotation(0.290141,0.896110,0.000000,0.335864))
App.ActiveDocument.addObject("Part::Cylinder","C982")
App.ActiveDocument.C982.Radius=0.750000
App.ActiveDocument.C982.Height=15.00
App.ActiveDocument.C982.Angle=360.00 
App.ActiveDocument.C982.Placement=Base.Placement(Base.Vector(1.928482,-144.193412,538.342557),Base.Rotation(0.029227,0.348017,0.000000,0.937032))
App.ActiveDocument.addObject("Part::Cylinder","C983")
App.ActiveDocument.C983.Radius=0.750000
App.ActiveDocument.C983.Height=15.00
App.ActiveDocument.C983.Angle=360.00 
App.ActiveDocument.C983.Placement=Base.Placement(Base.Vector(1.596560,-147.338640,538.271921),Base.Rotation(0.062601,0.343996,0.000000,0.936882))
App.ActiveDocument.addObject("Part::Cylinder","C984")
App.ActiveDocument.C984.Radius=0.750000
App.ActiveDocument.C984.Height=15.00
App.ActiveDocument.C984.Angle=360.00 
App.ActiveDocument.C984.Placement=Base.Placement(Base.Vector(1.912436,-150.411974,537.374785),Base.Rotation(0.099765,0.352832,0.000000,0.930353))
App.ActiveDocument.addObject("Part::Cylinder","C985")
App.ActiveDocument.C985.Radius=0.750000
App.ActiveDocument.C985.Height=15.00
App.ActiveDocument.C985.Angle=360.00 
App.ActiveDocument.C985.Placement=Base.Placement(Base.Vector(1.820873,-153.465081,536.511634),Base.Rotation(0.142557,0.356436,0.000000,0.923380))
App.ActiveDocument.addObject("Part::Cylinder","C986")
App.ActiveDocument.C986.Radius=0.750000
App.ActiveDocument.C986.Height=15.00
App.ActiveDocument.C986.Angle=360.00 
App.ActiveDocument.C986.Placement=Base.Placement(Base.Vector(1.725904,-156.187888,535.422200),Base.Rotation(0.186791,0.358596,0.000000,0.914613))
App.ActiveDocument.addObject("Part::Cylinder","C987")
App.ActiveDocument.C987.Radius=0.750000
App.ActiveDocument.C987.Height=15.00
App.ActiveDocument.C987.Angle=360.00 
App.ActiveDocument.C987.Placement=Base.Placement(Base.Vector(1.761251,-158.739628,533.905477),Base.Rotation(0.227638,0.368335,0.000000,0.901394))
App.ActiveDocument.addObject("Part::Cylinder","C988")
App.ActiveDocument.C988.Radius=0.750000
App.ActiveDocument.C988.Height=15.00
App.ActiveDocument.C988.Angle=360.00 
App.ActiveDocument.C988.Placement=Base.Placement(Base.Vector(1.778321,-161.013067,532.150792),Base.Rotation(0.278103,0.376296,0.000000,0.883776))
App.ActiveDocument.addObject("Part::Cylinder","C989")
App.ActiveDocument.C989.Radius=0.750000
App.ActiveDocument.C989.Height=15.00
App.ActiveDocument.C989.Angle=360.00 
App.ActiveDocument.C989.Placement=Base.Placement(Base.Vector(1.724809,-163.026693,530.234934),Base.Rotation(0.321747,0.383189,0.000000,0.865820))
App.ActiveDocument.addObject("Part::Cylinder","C990")
App.ActiveDocument.C990.Radius=0.750000
App.ActiveDocument.C990.Height=15.00
App.ActiveDocument.C990.Angle=360.00 
App.ActiveDocument.C990.Placement=Base.Placement(Base.Vector(1.807441,-164.619157,528.103098),Base.Rotation(0.362155,0.394618,0.000000,0.844465))
App.ActiveDocument.addObject("Part::Cylinder","C991")
App.ActiveDocument.C991.Radius=0.750000
App.ActiveDocument.C991.Height=15.00
App.ActiveDocument.C991.Angle=360.00 
App.ActiveDocument.C991.Placement=Base.Placement(Base.Vector(1.870027,-165.958688,525.803666),Base.Rotation(0.400697,0.407182,0.000000,0.820759))
App.ActiveDocument.addObject("Part::Cylinder","C992")
App.ActiveDocument.C992.Radius=0.750000
App.ActiveDocument.C992.Height=15.00
App.ActiveDocument.C992.Angle=360.00 
App.ActiveDocument.C992.Placement=Base.Placement(Base.Vector(1.905933,-167.041206,523.393263),Base.Rotation(0.433207,0.420903,0.000000,0.796977))
App.ActiveDocument.addObject("Part::Cylinder","C993")
App.ActiveDocument.C993.Radius=0.750000
App.ActiveDocument.C993.Height=15.00
App.ActiveDocument.C993.Angle=360.00 
App.ActiveDocument.C993.Placement=Base.Placement(Base.Vector(1.956124,-167.855585,520.803102),Base.Rotation(0.464337,0.434744,0.000000,0.771615))
App.ActiveDocument.addObject("Part::Cylinder","C994")
App.ActiveDocument.C994.Radius=0.750000
App.ActiveDocument.C994.Height=15.00
App.ActiveDocument.C994.Angle=360.00 
App.ActiveDocument.C994.Placement=Base.Placement(Base.Vector(1.827294,-168.557067,518.114801),Base.Rotation(0.487747,0.450289,0.000000,0.747892))
App.ActiveDocument.addObject("Part::Cylinder","C995")
App.ActiveDocument.C995.Radius=0.750000
App.ActiveDocument.C995.Height=15.00
App.ActiveDocument.C995.Angle=360.00 
App.ActiveDocument.C995.Placement=Base.Placement(Base.Vector(1.704716,-168.978834,515.438165),Base.Rotation(0.511936,0.462287,0.000000,0.724025))
App.ActiveDocument.addObject("Part::Cylinder","C996")
App.ActiveDocument.C996.Radius=0.750000
App.ActiveDocument.C996.Height=15.00
App.ActiveDocument.C996.Angle=360.00 
App.ActiveDocument.C996.Placement=Base.Placement(Base.Vector(1.628908,-169.104727,512.596576),Base.Rotation(0.525853,0.483152,0.000000,0.700031))
App.ActiveDocument.addObject("Part::Cylinder","C997")
App.ActiveDocument.C997.Radius=0.750000
App.ActiveDocument.C997.Height=15.00
App.ActiveDocument.C997.Angle=360.00 
App.ActiveDocument.C997.Placement=Base.Placement(Base.Vector(1.505216,-169.041930,509.964658),Base.Rotation(0.538675,0.499341,0.000000,0.678593))
App.ActiveDocument.addObject("Part::Cylinder","C998")
App.ActiveDocument.C998.Radius=0.750000
App.ActiveDocument.C998.Height=15.00
App.ActiveDocument.C998.Angle=360.00 
App.ActiveDocument.C998.Placement=Base.Placement(Base.Vector(1.348519,-168.781389,507.243857),Base.Rotation(0.545769,0.520055,0.000000,0.657023))
App.ActiveDocument.addObject("Part::Cylinder","C999")
App.ActiveDocument.C999.Radius=0.750000
App.ActiveDocument.C999.Height=15.00
App.ActiveDocument.C999.Angle=360.00 
App.ActiveDocument.C999.Placement=Base.Placement(Base.Vector(1.177427,-168.345355,504.636644),Base.Rotation(0.549752,0.542449,0.000000,0.635234))
App.ActiveDocument.addObject("Part::Cylinder","C1000")
App.ActiveDocument.C1000.Radius=0.750000
App.ActiveDocument.C1000.Height=15.00
App.ActiveDocument.C1000.Angle=360.00 
App.ActiveDocument.C1000.Placement=Base.Placement(Base.Vector(0.985282,-167.683993,501.917236),Base.Rotation(0.550363,0.563982,0.000000,0.615650))
App.ActiveDocument.addObject("Part::Cylinder","C1001")
App.ActiveDocument.C1001.Radius=0.750000
App.ActiveDocument.C1001.Height=15.00
App.ActiveDocument.C1001.Angle=360.00 
App.ActiveDocument.C1001.Placement=Base.Placement(Base.Vector(0.793636,-166.833235,499.294696),Base.Rotation(0.548964,0.584806,0.000000,0.597194))
App.ActiveDocument.addObject("Part::Cylinder","C1002")
App.ActiveDocument.C1002.Radius=0.750000
App.ActiveDocument.C1002.Height=15.00
App.ActiveDocument.C1002.Angle=360.00 
App.ActiveDocument.C1002.Placement=Base.Placement(Base.Vector(0.545637,-165.826209,496.695153),Base.Rotation(0.541446,0.613527,0.000000,0.574823))
App.ActiveDocument.addObject("Part::Cylinder","C1003")
App.ActiveDocument.C1003.Radius=0.750000
App.ActiveDocument.C1003.Height=15.00
App.ActiveDocument.C1003.Angle=360.00 
App.ActiveDocument.C1003.Placement=Base.Placement(Base.Vector(0.334923,-164.656959,494.295378),Base.Rotation(0.533513,0.636230,0.000000,0.557292))
App.ActiveDocument.addObject("Part::Cylinder","C1004")
App.ActiveDocument.C1004.Radius=0.750000
App.ActiveDocument.C1004.Height=15.00
App.ActiveDocument.C1004.Angle=360.00 
App.ActiveDocument.C1004.Placement=Base.Placement(Base.Vector(-0.067570,-163.448384,491.839699),Base.Rotation(0.520059,0.663540,0.000000,0.537822))
App.ActiveDocument.addObject("Part::Cylinder","C1005")
App.ActiveDocument.C1005.Radius=0.750000
App.ActiveDocument.C1005.Height=15.00
App.ActiveDocument.C1005.Angle=360.00 
App.ActiveDocument.C1005.Placement=Base.Placement(Base.Vector(-0.441610,-162.053449,489.509996),Base.Rotation(0.507798,0.686987,0.000000,0.519798))
App.ActiveDocument.addObject("Part::Cylinder","C1006")
App.ActiveDocument.C1006.Radius=0.750000
App.ActiveDocument.C1006.Height=15.00
App.ActiveDocument.C1006.Angle=360.00 
App.ActiveDocument.C1006.Placement=Base.Placement(Base.Vector(-0.711711,-160.327115,487.284243),Base.Rotation(0.487626,0.714451,0.000000,0.501778))
App.ActiveDocument.addObject("Part::Cylinder","C1007")
App.ActiveDocument.C1007.Radius=0.750000
App.ActiveDocument.C1007.Height=15.00
App.ActiveDocument.C1007.Angle=360.00 
App.ActiveDocument.C1007.Placement=Base.Placement(Base.Vector(-0.890397,-158.459653,485.351353),Base.Rotation(0.457265,0.746358,0.000000,0.483589))
App.ActiveDocument.addObject("Part::Cylinder","C1008")
App.ActiveDocument.C1008.Radius=0.750000
App.ActiveDocument.C1008.Height=15.00
App.ActiveDocument.C1008.Angle=360.00 
App.ActiveDocument.C1008.Placement=Base.Placement(Base.Vector(-1.433785,-156.612795,483.222701),Base.Rotation(0.430857,0.773935,0.000000,0.464097))
App.ActiveDocument.addObject("Part::Cylinder","C1009")
App.ActiveDocument.C1009.Radius=0.750000
App.ActiveDocument.C1009.Height=15.00
App.ActiveDocument.C1009.Angle=360.00 
App.ActiveDocument.C1009.Placement=Base.Placement(Base.Vector(-1.667835,-154.624309,481.633888),Base.Rotation(0.402168,0.797426,0.000000,0.449859))
App.ActiveDocument.addObject("Part::Cylinder","C1010")
App.ActiveDocument.C1010.Radius=0.750000
App.ActiveDocument.C1010.Height=15.00
App.ActiveDocument.C1010.Angle=360.00 
App.ActiveDocument.C1010.Placement=Base.Placement(Base.Vector(-2.306517,-152.698265,479.828867),Base.Rotation(0.364407,0.825182,0.000000,0.431604))
App.ActiveDocument.addObject("Part::Cylinder","C1011")
App.ActiveDocument.C1011.Radius=0.750000
App.ActiveDocument.C1011.Height=15.00
App.ActiveDocument.C1011.Angle=360.00 
App.ActiveDocument.C1011.Placement=Base.Placement(Base.Vector(-3.125539,-150.606764,477.978291),Base.Rotation(0.335468,0.848403,0.000000,0.409479))
App.ActiveDocument.addObject("Part::Cylinder","C1012")
App.ActiveDocument.C1012.Radius=0.750000
App.ActiveDocument.C1012.Height=15.00
App.ActiveDocument.C1012.Angle=360.00 
App.ActiveDocument.C1012.Placement=Base.Placement(Base.Vector(-4.144080,-148.489267,476.171052),Base.Rotation(0.295673,0.874108,0.000000,0.385373))
App.ActiveDocument.addObject("Part::Cylinder","C1013")
App.ActiveDocument.C1013.Radius=0.750000
App.ActiveDocument.C1013.Height=15.00
App.ActiveDocument.C1013.Angle=360.00 
App.ActiveDocument.C1013.Placement=Base.Placement(Base.Vector(-5.531283,-146.499581,474.323049),Base.Rotation(0.255085,0.897577,0.000000,0.359564))
App.ActiveDocument.addObject("Part::Cylinder","C1014")
App.ActiveDocument.C1014.Radius=0.750000
App.ActiveDocument.C1014.Height=15.00
App.ActiveDocument.C1014.Angle=360.00 
App.ActiveDocument.C1014.Placement=Base.Placement(Base.Vector(-7.472333,-144.754400,472.365541),Base.Rotation(0.217283,0.919820,0.000000,0.326679))
App.ActiveDocument.addObject("Part::Cylinder","C1015")
App.ActiveDocument.C1015.Radius=0.750000
App.ActiveDocument.C1015.Height=15.00
App.ActiveDocument.C1015.Angle=360.00 
App.ActiveDocument.C1015.Placement=Base.Placement(Base.Vector(4.165613,-144.183391,536.223200),Base.Rotation(0.030073,0.391848,0.000000,0.919538))
App.ActiveDocument.addObject("Part::Cylinder","C1016")
App.ActiveDocument.C1016.Radius=0.750000
App.ActiveDocument.C1016.Height=15.00
App.ActiveDocument.C1016.Angle=360.00 
App.ActiveDocument.C1016.Placement=Base.Placement(Base.Vector(3.895283,-147.359885,536.111578),Base.Rotation(0.064426,0.388664,0.000000,0.919124))
App.ActiveDocument.addObject("Part::Cylinder","C1017")
App.ActiveDocument.C1017.Radius=0.750000
App.ActiveDocument.C1017.Height=15.00
App.ActiveDocument.C1017.Angle=360.00 
App.ActiveDocument.C1017.Placement=Base.Placement(Base.Vector(4.132963,-150.388083,535.178195),Base.Rotation(0.102162,0.398855,0.000000,0.911305))
App.ActiveDocument.addObject("Part::Cylinder","C1018")
App.ActiveDocument.C1018.Radius=0.750000
App.ActiveDocument.C1018.Height=15.00
App.ActiveDocument.C1018.Angle=360.00 
App.ActiveDocument.C1018.Placement=Base.Placement(Base.Vector(4.019411,-153.387333,534.273038),Base.Rotation(0.144868,0.401314,0.000000,0.904411))
App.ActiveDocument.addObject("Part::Cylinder","C1019")
App.ActiveDocument.C1019.Radius=0.750000
App.ActiveDocument.C1019.Height=15.00
App.ActiveDocument.C1019.Angle=360.00 
App.ActiveDocument.C1019.Placement=Base.Placement(Base.Vector(3.889205,-156.126887,533.097526),Base.Rotation(0.189937,0.406842,0.000000,0.893534))
App.ActiveDocument.addObject("Part::Cylinder","C1020")
App.ActiveDocument.C1020.Radius=0.750000
App.ActiveDocument.C1020.Height=15.00
App.ActiveDocument.C1020.Angle=360.00 
App.ActiveDocument.C1020.Placement=Base.Placement(Base.Vector(3.923392,-158.457713,531.522395),Base.Rotation(0.234356,0.417637,0.000000,0.877871))
App.ActiveDocument.addObject("Part::Cylinder","C1021")
App.ActiveDocument.C1021.Radius=0.750000
App.ActiveDocument.C1021.Height=15.00
App.ActiveDocument.C1021.Angle=360.00 
App.ActiveDocument.C1021.Placement=Base.Placement(Base.Vector(3.972753,-160.466749,529.720911),Base.Rotation(0.276629,0.426971,0.000000,0.860914))
App.ActiveDocument.addObject("Part::Cylinder","C1022")
App.ActiveDocument.C1022.Radius=0.750000
App.ActiveDocument.C1022.Height=15.00
App.ActiveDocument.C1022.Angle=360.00 
App.ActiveDocument.C1022.Placement=Base.Placement(Base.Vector(4.007688,-162.261079,527.641623),Base.Rotation(0.318070,0.443398,0.000000,0.837991))
App.ActiveDocument.addObject("Part::Cylinder","C1023")
App.ActiveDocument.C1023.Radius=0.750000
App.ActiveDocument.C1023.Height=15.00
App.ActiveDocument.C1023.Angle=360.00 
App.ActiveDocument.C1023.Placement=Base.Placement(Base.Vector(3.989192,-163.770301,525.418186),Base.Rotation(0.357364,0.452193,0.000000,0.817198))
App.ActiveDocument.addObject("Part::Cylinder","C1024")
App.ActiveDocument.C1024.Radius=0.750000
App.ActiveDocument.C1024.Height=15.00
App.ActiveDocument.C1024.Angle=360.00 
App.ActiveDocument.C1024.Placement=Base.Placement(Base.Vector(4.071107,-164.810639,523.108798),Base.Rotation(0.386585,0.469203,0.000000,0.793977))
App.ActiveDocument.addObject("Part::Cylinder","C1025")
App.ActiveDocument.C1025.Radius=0.750000
App.ActiveDocument.C1025.Height=15.00
App.ActiveDocument.C1025.Angle=360.00 
App.ActiveDocument.C1025.Placement=Base.Placement(Base.Vector(4.074717,-165.691963,520.589657),Base.Rotation(0.415459,0.486112,0.000000,0.768823))
App.ActiveDocument.addObject("Part::Cylinder","C1026")
App.ActiveDocument.C1026.Radius=0.750000
App.ActiveDocument.C1026.Height=15.00
App.ActiveDocument.C1026.Angle=360.00 
App.ActiveDocument.C1026.Placement=Base.Placement(Base.Vector(3.974833,-166.373426,518.065220),Base.Rotation(0.440761,0.500546,0.000000,0.745106))
App.ActiveDocument.addObject("Part::Cylinder","C1027")
App.ActiveDocument.C1027.Radius=0.750000
App.ActiveDocument.C1027.Height=15.00
App.ActiveDocument.C1027.Angle=360.00 
App.ActiveDocument.C1027.Placement=Base.Placement(Base.Vector(3.829682,-166.836624,515.460684),Base.Rotation(0.460239,0.515731,0.000000,0.722635))
App.ActiveDocument.addObject("Part::Cylinder","C1028")
App.ActiveDocument.C1028.Radius=0.750000
App.ActiveDocument.C1028.Height=15.00
App.ActiveDocument.C1028.Angle=360.00 
App.ActiveDocument.C1028.Placement=Base.Placement(Base.Vector(3.800438,-166.911408,512.928783),Base.Rotation(0.474296,0.534516,0.000000,0.699526))
App.ActiveDocument.addObject("Part::Cylinder","C1029")
App.ActiveDocument.C1029.Radius=0.750000
App.ActiveDocument.C1029.Height=15.00
App.ActiveDocument.C1029.Angle=360.00 
App.ActiveDocument.C1029.Placement=Base.Placement(Base.Vector(3.638888,-166.878837,510.188709),Base.Rotation(0.487830,0.549443,0.000000,0.678333))
App.ActiveDocument.addObject("Part::Cylinder","C1030")
App.ActiveDocument.C1030.Radius=0.750000
App.ActiveDocument.C1030.Height=15.00
App.ActiveDocument.C1030.Angle=360.00 
App.ActiveDocument.C1030.Placement=Base.Placement(Base.Vector(3.568236,-166.523737,507.604202),Base.Rotation(0.493963,0.569099,0.000000,0.657363))
App.ActiveDocument.addObject("Part::Cylinder","C1031")
App.ActiveDocument.C1031.Radius=0.750000
App.ActiveDocument.C1031.Height=15.00
App.ActiveDocument.C1031.Angle=360.00 
App.ActiveDocument.C1031.Placement=Base.Placement(Base.Vector(3.341648,-166.102914,504.953056),Base.Rotation(0.498148,0.590103,0.000000,0.635317))
App.ActiveDocument.addObject("Part::Cylinder","C1032")
App.ActiveDocument.C1032.Radius=0.750000
App.ActiveDocument.C1032.Height=15.00
App.ActiveDocument.C1032.Angle=360.00 
App.ActiveDocument.C1032.Placement=Base.Placement(Base.Vector(3.133740,-165.501895,502.494533),Base.Rotation(0.495511,0.612457,0.000000,0.615926))
App.ActiveDocument.addObject("Part::Cylinder","C1033")
App.ActiveDocument.C1033.Radius=0.750000
App.ActiveDocument.C1033.Height=15.00
App.ActiveDocument.C1033.Angle=360.00 
App.ActiveDocument.C1033.Placement=Base.Placement(Base.Vector(2.976643,-164.629694,500.048415),Base.Rotation(0.490582,0.632738,0.000000,0.599143))
App.ActiveDocument.addObject("Part::Cylinder","C1034")
App.ActiveDocument.C1034.Radius=0.750000
App.ActiveDocument.C1034.Height=15.00
App.ActiveDocument.C1034.Angle=360.00 
App.ActiveDocument.C1034.Placement=Base.Placement(Base.Vector(2.760864,-163.652682,497.681858),Base.Rotation(0.485743,0.653996,0.000000,0.579951))
App.ActiveDocument.addObject("Part::Cylinder","C1035")
App.ActiveDocument.C1035.Radius=0.750000
App.ActiveDocument.C1035.Height=15.00
App.ActiveDocument.C1035.Angle=360.00 
App.ActiveDocument.C1035.Placement=Base.Placement(Base.Vector(2.499856,-162.474668,495.265729),Base.Rotation(0.475463,0.677362,0.000000,0.561351))
App.ActiveDocument.addObject("Part::Cylinder","C1036")
App.ActiveDocument.C1036.Radius=0.750000
App.ActiveDocument.C1036.Height=15.00
App.ActiveDocument.C1036.Angle=360.00 
App.ActiveDocument.C1036.Placement=Base.Placement(Base.Vector(2.076797,-161.254677,492.821398),Base.Rotation(0.462376,0.700973,0.000000,0.542996))
App.ActiveDocument.addObject("Part::Cylinder","C1037")
App.ActiveDocument.C1037.Radius=0.750000
App.ActiveDocument.C1037.Height=15.00
App.ActiveDocument.C1037.Angle=360.00 
App.ActiveDocument.C1037.Placement=Base.Placement(Base.Vector(1.716247,-159.828687,490.567290),Base.Rotation(0.446902,0.724261,0.000000,0.525095))
App.ActiveDocument.addObject("Part::Cylinder","C1038")
App.ActiveDocument.C1038.Radius=0.750000
App.ActiveDocument.C1038.Height=15.00
App.ActiveDocument.C1038.Angle=360.00 
App.ActiveDocument.C1038.Placement=Base.Placement(Base.Vector(1.514863,-157.705249,488.232554),Base.Rotation(0.412746,0.756532,0.000000,0.507247))
App.ActiveDocument.addObject("Part::Cylinder","C1039")
App.ActiveDocument.C1039.Radius=0.750000
App.ActiveDocument.C1039.Height=15.00
App.ActiveDocument.C1039.Angle=360.00 
App.ActiveDocument.C1039.Placement=Base.Placement(Base.Vector(1.077273,-155.552742,485.882242),Base.Rotation(0.385342,0.783775,0.000000,0.487041))
App.ActiveDocument.addObject("Part::Cylinder","C1040")
App.ActiveDocument.C1040.Radius=0.750000
App.ActiveDocument.C1040.Height=15.00
App.ActiveDocument.C1040.Angle=360.00 
App.ActiveDocument.C1040.Placement=Base.Placement(Base.Vector(0.649773,-153.300990,483.821090),Base.Rotation(0.347365,0.812101,0.000000,0.468859))
App.ActiveDocument.addObject("Part::Cylinder","C1041")
App.ActiveDocument.C1041.Radius=0.750000
App.ActiveDocument.C1041.Height=15.00
App.ActiveDocument.C1041.Angle=360.00 
App.ActiveDocument.C1041.Placement=Base.Placement(Base.Vector(0.113582,-151.063737,481.936424),Base.Rotation(0.307796,0.836419,0.000000,0.453502))
App.ActiveDocument.addObject("Part::Cylinder","C1042")
App.ActiveDocument.C1042.Radius=0.750000
App.ActiveDocument.C1042.Height=15.00
App.ActiveDocument.C1042.Angle=360.00 
App.ActiveDocument.C1042.Placement=Base.Placement(Base.Vector(-0.816548,-149.072486,479.944341),Base.Rotation(0.268273,0.859961,0.000000,0.434163))
App.ActiveDocument.addObject("Part::Cylinder","C1043")
App.ActiveDocument.C1043.Radius=0.750000
App.ActiveDocument.C1043.Height=15.00
App.ActiveDocument.C1043.Angle=360.00 
App.ActiveDocument.C1043.Placement=Base.Placement(Base.Vector(-1.772870,-147.056758,478.171915),Base.Rotation(0.233100,0.879805,0.000000,0.414255))
App.ActiveDocument.addObject("Part::Cylinder","C1044")
App.ActiveDocument.C1044.Radius=0.750000
App.ActiveDocument.C1044.Height=15.00
App.ActiveDocument.C1044.Angle=360.00 
App.ActiveDocument.C1044.Placement=Base.Placement(Base.Vector(-3.039532,-145.104965,476.345500),Base.Rotation(0.172266,0.904202,0.000000,0.390824))
App.ActiveDocument.addObject("Part::Cylinder","C1045")
App.ActiveDocument.C1045.Radius=0.750000
App.ActiveDocument.C1045.Height=15.00
App.ActiveDocument.C1045.Angle=360.00 
App.ActiveDocument.C1045.Placement=Base.Placement(Base.Vector(-4.704738,-143.505806,474.470517),Base.Rotation(0.126067,0.922218,0.000000,0.365543))
App.ActiveDocument.addObject("Part::Cylinder","C1046")
App.ActiveDocument.C1046.Radius=0.750000
App.ActiveDocument.C1046.Height=15.00
App.ActiveDocument.C1046.Angle=360.00 
App.ActiveDocument.C1046.Placement=Base.Placement(Base.Vector(-6.720405,-142.786655,472.659876),Base.Rotation(0.115341,0.936024,0.000000,0.332500))
App.ActiveDocument.addObject("Part::Cylinder","C1047")
App.ActiveDocument.C1047.Radius=0.750000
App.ActiveDocument.C1047.Height=15.00
App.ActiveDocument.C1047.Angle=360.00 
App.ActiveDocument.C1047.Placement=Base.Placement(Base.Vector(6.086367,-144.172968,534.002828),Base.Rotation(0.030050,0.438934,0.000000,0.898017))
App.ActiveDocument.addObject("Part::Cylinder","C1048")
App.ActiveDocument.C1048.Radius=0.750000
App.ActiveDocument.C1048.Height=15.00
App.ActiveDocument.C1048.Angle=360.00 
App.ActiveDocument.C1048.Placement=Base.Placement(Base.Vector(5.911272,-147.387033,533.778079),Base.Rotation(0.066515,0.437999,0.000000,0.896512))
App.ActiveDocument.addObject("Part::Cylinder","C1049")
App.ActiveDocument.C1049.Radius=0.750000
App.ActiveDocument.C1049.Height=15.00
App.ActiveDocument.C1049.Angle=360.00 
App.ActiveDocument.C1049.Placement=Base.Placement(Base.Vector(6.050506,-150.415022,532.815614),Base.Rotation(0.103996,0.448924,0.000000,0.887498))
App.ActiveDocument.addObject("Part::Cylinder","C1050")
App.ActiveDocument.C1050.Radius=0.750000
App.ActiveDocument.C1050.Height=15.00
App.ActiveDocument.C1050.Angle=360.00 
App.ActiveDocument.C1050.Placement=Base.Placement(Base.Vector(5.892723,-153.318222,531.892709),Base.Rotation(0.149518,0.451891,0.000000,0.879454))
App.ActiveDocument.addObject("Part::Cylinder","C1051")
App.ActiveDocument.C1051.Radius=0.750000
App.ActiveDocument.C1051.Height=15.00
App.ActiveDocument.C1051.Angle=360.00 
App.ActiveDocument.C1051.Placement=Base.Placement(Base.Vector(5.843388,-155.825561,530.571924),Base.Rotation(0.189739,0.460939,0.000000,0.866911))
App.ActiveDocument.addObject("Part::Cylinder","C1052")
App.ActiveDocument.C1052.Radius=0.750000
App.ActiveDocument.C1052.Height=15.00
App.ActiveDocument.C1052.Angle=360.00 
App.ActiveDocument.C1052.Placement=Base.Placement(Base.Vector(5.847663,-157.989208,528.922300),Base.Rotation(0.232436,0.472520,0.000000,0.850117))
App.ActiveDocument.addObject("Part::Cylinder","C1053")
App.ActiveDocument.C1053.Radius=0.750000
App.ActiveDocument.C1053.Height=15.00
App.ActiveDocument.C1053.Angle=360.00 
App.ActiveDocument.C1053.Placement=Base.Placement(Base.Vector(5.910150,-159.719366,527.050774),Base.Rotation(0.267508,0.486971,0.000000,0.831444))
App.ActiveDocument.addObject("Part::Cylinder","C1054")
App.ActiveDocument.C1054.Radius=0.750000
App.ActiveDocument.C1054.Height=15.00
App.ActiveDocument.C1054.Angle=360.00 
App.ActiveDocument.C1054.Placement=Base.Placement(Base.Vector(5.878160,-161.331059,524.936639),Base.Rotation(0.305425,0.502703,0.000000,0.808706))
App.ActiveDocument.addObject("Part::Cylinder","C1055")
App.ActiveDocument.C1055.Radius=0.750000
App.ActiveDocument.C1055.Height=15.00
App.ActiveDocument.C1055.Angle=360.00 
App.ActiveDocument.C1055.Placement=Base.Placement(Base.Vector(5.982358,-162.392454,522.652513),Base.Rotation(0.336227,0.516851,0.000000,0.787284))
App.ActiveDocument.addObject("Part::Cylinder","C1056")
App.ActiveDocument.C1056.Radius=0.750000
App.ActiveDocument.C1056.Height=15.00
App.ActiveDocument.C1056.Angle=360.00 
App.ActiveDocument.C1056.Placement=Base.Placement(Base.Vector(5.937593,-163.346571,520.261623),Base.Rotation(0.363794,0.533968,0.000000,0.763238))
App.ActiveDocument.addObject("Part::Cylinder","C1057")
App.ActiveDocument.C1057.Radius=0.750000
App.ActiveDocument.C1057.Height=15.00
App.ActiveDocument.C1057.Angle=360.00 
App.ActiveDocument.C1057.Placement=Base.Placement(Base.Vector(5.866194,-164.044722,517.669767),Base.Rotation(0.391604,0.546071,0.000000,0.740576))
App.ActiveDocument.addObject("Part::Cylinder","C1058")
App.ActiveDocument.C1058.Radius=0.750000
App.ActiveDocument.C1058.Height=15.00
App.ActiveDocument.C1058.Angle=360.00 
App.ActiveDocument.C1058.Placement=Base.Placement(Base.Vector(5.742340,-164.484449,515.137098),Base.Rotation(0.408148,0.565833,0.000000,0.716414))
App.ActiveDocument.addObject("Part::Cylinder","C1059")
App.ActiveDocument.C1059.Radius=0.750000
App.ActiveDocument.C1059.Height=15.00
App.ActiveDocument.C1059.Angle=360.00 
App.ActiveDocument.C1059.Placement=Base.Placement(Base.Vector(5.604294,-164.671226,512.700883),Base.Rotation(0.421073,0.580693,0.000000,0.696774))
App.ActiveDocument.addObject("Part::Cylinder","C1060")
App.ActiveDocument.C1060.Radius=0.750000
App.ActiveDocument.C1060.Height=15.00
App.ActiveDocument.C1060.Angle=360.00 
App.ActiveDocument.C1060.Placement=Base.Placement(Base.Vector(5.551607,-164.500000,510.273215),Base.Rotation(0.433108,0.595730,0.000000,0.676404))
App.ActiveDocument.addObject("Part::Cylinder","C1061")
App.ActiveDocument.C1061.Radius=0.750000
App.ActiveDocument.C1061.Height=15.00
App.ActiveDocument.C1061.Angle=360.00 
App.ActiveDocument.C1061.Placement=Base.Placement(Base.Vector(5.381683,-164.218190,507.649346),Base.Rotation(0.438592,0.613781,0.000000,0.656438))
App.ActiveDocument.addObject("Part::Cylinder","C1062")
App.ActiveDocument.C1062.Radius=0.750000
App.ActiveDocument.C1062.Height=15.00
App.ActiveDocument.C1062.Angle=360.00 
App.ActiveDocument.C1062.Placement=Base.Placement(Base.Vector(5.222270,-163.735161,505.240702),Base.Rotation(0.440050,0.634111,0.000000,0.635813))
App.ActiveDocument.addObject("Part::Cylinder","C1063")
App.ActiveDocument.C1063.Radius=0.750000
App.ActiveDocument.C1063.Height=15.00
App.ActiveDocument.C1063.Angle=360.00 
App.ActiveDocument.C1063.Placement=Base.Placement(Base.Vector(5.025277,-163.134562,502.941934),Base.Rotation(0.439156,0.652074,0.000000,0.618014))
App.ActiveDocument.addObject("Part::Cylinder","C1064")
App.ActiveDocument.C1064.Radius=0.750000
App.ActiveDocument.C1064.Height=15.00
App.ActiveDocument.C1064.Angle=360.00 
App.ActiveDocument.C1064.Placement=Base.Placement(Base.Vector(4.830456,-162.236856,500.488465),Base.Rotation(0.428830,0.675634,0.000000,0.599687))
App.ActiveDocument.addObject("Part::Cylinder","C1065")
App.ActiveDocument.C1065.Radius=0.750000
App.ActiveDocument.C1065.Height=15.00
App.ActiveDocument.C1065.Angle=360.00 
App.ActiveDocument.C1065.Placement=Base.Placement(Base.Vector(4.582190,-161.282429,498.214140),Base.Rotation(0.425055,0.692317,0.000000,0.583117))
App.ActiveDocument.addObject("Part::Cylinder","C1066")
App.ActiveDocument.C1066.Radius=0.750000
App.ActiveDocument.C1066.Height=15.00
App.ActiveDocument.C1066.Angle=360.00 
App.ActiveDocument.C1066.Placement=Base.Placement(Base.Vector(4.315544,-160.232232,496.087258),Base.Rotation(0.415076,0.712450,0.000000,0.565797))
App.ActiveDocument.addObject("Part::Cylinder","C1067")
App.ActiveDocument.C1067.Radius=0.750000
App.ActiveDocument.C1067.Height=15.00
App.ActiveDocument.C1067.Angle=360.00 
App.ActiveDocument.C1067.Placement=Base.Placement(Base.Vector(4.023840,-158.926516,493.883233),Base.Rotation(0.397399,0.733063,0.000000,0.551989))
App.ActiveDocument.addObject("Part::Cylinder","C1068")
App.ActiveDocument.C1068.Radius=0.750000
App.ActiveDocument.C1068.Height=15.00
App.ActiveDocument.C1068.Angle=360.00 
App.ActiveDocument.C1068.Placement=Base.Placement(Base.Vector(3.614039,-157.676199,491.787655),Base.Rotation(0.386249,0.752180,0.000000,0.533888))
App.ActiveDocument.addObject("Part::Cylinder","C1069")
App.ActiveDocument.C1069.Radius=0.750000
App.ActiveDocument.C1069.Height=15.00
App.ActiveDocument.C1069.Angle=360.00 
App.ActiveDocument.C1069.Placement=Base.Placement(Base.Vector(3.456300,-155.272359,489.459079),Base.Rotation(0.342377,0.785100,0.000000,0.516135))
App.ActiveDocument.addObject("Part::Cylinder","C1070")
App.ActiveDocument.C1070.Radius=0.750000
App.ActiveDocument.C1070.Height=15.00
App.ActiveDocument.C1070.Angle=360.00 
App.ActiveDocument.C1070.Placement=Base.Placement(Base.Vector(3.004708,-153.038777,487.164901),Base.Rotation(0.305515,0.809521,0.000000,0.501335))
App.ActiveDocument.addObject("Part::Cylinder","C1071")
App.ActiveDocument.C1071.Radius=0.750000
App.ActiveDocument.C1071.Height=15.00
App.ActiveDocument.C1071.Angle=360.00 
App.ActiveDocument.C1071.Placement=Base.Placement(Base.Vector(2.479421,-150.670014,485.057599),Base.Rotation(0.264702,0.833628,0.000000,0.484766))
App.ActiveDocument.addObject("Part::Cylinder","C1072")
App.ActiveDocument.C1072.Radius=0.750000
App.ActiveDocument.C1072.Height=15.00
App.ActiveDocument.C1072.Angle=360.00 
App.ActiveDocument.C1072.Placement=Base.Placement(Base.Vector(1.688760,-148.352366,482.945211),Base.Rotation(0.206737,0.860466,0.000000,0.465680))
App.ActiveDocument.addObject("Part::Cylinder","C1073")
App.ActiveDocument.C1073.Radius=0.750000
App.ActiveDocument.C1073.Height=15.00
App.ActiveDocument.C1073.Angle=360.00 
App.ActiveDocument.C1073.Placement=Base.Placement(Base.Vector(0.588122,-146.226914,480.816857),Base.Rotation(0.161421,0.879649,0.000000,0.447394))
App.ActiveDocument.addObject("Part::Cylinder","C1074")
App.ActiveDocument.C1074.Radius=0.750000
App.ActiveDocument.C1074.Height=15.00
App.ActiveDocument.C1074.Angle=360.00 
App.ActiveDocument.C1074.Placement=Base.Placement(Base.Vector(-0.649528,-144.137406,478.862579),Base.Rotation(0.095749,0.898009,0.000000,0.429432))
App.ActiveDocument.addObject("Part::Cylinder","C1075")
App.ActiveDocument.C1075.Radius=0.750000
App.ActiveDocument.C1075.Height=15.00
App.ActiveDocument.C1075.Angle=360.00 
App.ActiveDocument.C1075.Placement=Base.Placement(Base.Vector(-2.127534,-143.239593,477.034939),Base.Rotation(0.081349,0.911235,0.000000,0.403773))
App.ActiveDocument.addObject("Part::Cylinder","C1076")
App.ActiveDocument.C1076.Radius=0.750000
App.ActiveDocument.C1076.Height=15.00
App.ActiveDocument.C1076.Angle=360.00 
App.ActiveDocument.C1076.Placement=Base.Placement(Base.Vector(7.709452,-144.149779,531.655688),Base.Rotation(0.030552,0.488705,0.000000,0.871914))
App.ActiveDocument.addObject("Part::Cylinder","C1077")
App.ActiveDocument.C1077.Radius=0.750000
App.ActiveDocument.C1077.Height=15.00
App.ActiveDocument.C1077.Angle=360.00 
App.ActiveDocument.C1077.Placement=Base.Placement(Base.Vector(7.610767,-147.316592,531.309311),Base.Rotation(0.065311,0.488199,0.000000,0.870285))
App.ActiveDocument.addObject("Part::Cylinder","C1078")
App.ActiveDocument.C1078.Radius=0.750000
App.ActiveDocument.C1078.Height=15.00
App.ActiveDocument.C1078.Angle=360.00 
App.ActiveDocument.C1078.Placement=Base.Placement(Base.Vector(7.704766,-150.236130,530.280288),Base.Rotation(0.104254,0.504804,0.000000,0.856916))
App.ActiveDocument.addObject("Part::Cylinder","C1079")
App.ActiveDocument.C1079.Radius=0.750000
App.ActiveDocument.C1079.Height=15.00
App.ActiveDocument.C1079.Angle=360.00 
App.ActiveDocument.C1079.Placement=Base.Placement(Base.Vector(7.527537,-153.072396,529.301585),Base.Rotation(0.145189,0.505084,0.000000,0.850770))
App.ActiveDocument.addObject("Part::Cylinder","C1080")
App.ActiveDocument.C1080.Radius=0.750000
App.ActiveDocument.C1080.Height=15.00
App.ActiveDocument.C1080.Angle=360.00 
App.ActiveDocument.C1080.Placement=Base.Placement(Base.Vector(7.500558,-155.428604,527.789277),Base.Rotation(0.187377,0.513996,0.000000,0.837077))
App.ActiveDocument.addObject("Part::Cylinder","C1081")
App.ActiveDocument.C1081.Radius=0.750000
App.ActiveDocument.C1081.Height=15.00
App.ActiveDocument.C1081.Angle=360.00 
App.ActiveDocument.C1081.Placement=Base.Placement(Base.Vector(7.571332,-157.292529,525.900803),Base.Rotation(0.224656,0.533245,0.000000,0.815585))
App.ActiveDocument.addObject("Part::Cylinder","C1082")
App.ActiveDocument.C1082.Radius=0.750000
App.ActiveDocument.C1082.Height=15.00
App.ActiveDocument.C1082.Angle=360.00 
App.ActiveDocument.C1082.Placement=Base.Placement(Base.Vector(7.522988,-159.002870,523.829048),Base.Rotation(0.259265,0.547845,0.000000,0.795391))
App.ActiveDocument.addObject("Part::Cylinder","C1083")
App.ActiveDocument.C1083.Radius=0.750000
App.ActiveDocument.C1083.Height=15.00
App.ActiveDocument.C1083.Angle=360.00 
App.ActiveDocument.C1083.Placement=Base.Placement(Base.Vector(7.553536,-160.139613,521.629012),Base.Rotation(0.289010,0.561872,0.000000,0.775095))
App.ActiveDocument.addObject("Part::Cylinder","C1084")
App.ActiveDocument.C1084.Radius=0.750000
App.ActiveDocument.C1084.Height=15.00
App.ActiveDocument.C1084.Angle=360.00 
App.ActiveDocument.C1084.Placement=Base.Placement(Base.Vector(7.519048,-161.055625,519.271869),Base.Rotation(0.313923,0.577354,0.000000,0.753734))
App.ActiveDocument.addObject("Part::Cylinder","C1085")
App.ActiveDocument.C1085.Radius=0.750000
App.ActiveDocument.C1085.Height=15.00
App.ActiveDocument.C1085.Angle=360.00 
App.ActiveDocument.C1085.Placement=Base.Placement(Base.Vector(7.411231,-161.727233,517.004721),Base.Rotation(0.337964,0.591080,0.000000,0.732397))
App.ActiveDocument.addObject("Part::Cylinder","C1086")
App.ActiveDocument.C1086.Radius=0.750000
App.ActiveDocument.C1086.Height=15.00
App.ActiveDocument.C1086.Angle=360.00 
App.ActiveDocument.C1086.Placement=Base.Placement(Base.Vector(7.389154,-161.953131,513.982310),Base.Rotation(0.360711,0.610422,0.000000,0.705176))
App.ActiveDocument.addObject("Part::Cylinder","C1087")
App.ActiveDocument.C1087.Radius=0.750000
App.ActiveDocument.C1087.Height=15.00
App.ActiveDocument.C1087.Angle=360.00 
App.ActiveDocument.C1087.Placement=Base.Placement(Base.Vector(7.325282,-161.855820,511.064108),Base.Rotation(0.364514,0.632798,0.000000,0.683152))
App.ActiveDocument.addObject("Part::Cylinder","C1088")
App.ActiveDocument.C1088.Radius=0.750000
App.ActiveDocument.C1088.Height=15.00
App.ActiveDocument.C1088.Angle=360.00 
App.ActiveDocument.C1088.Placement=Base.Placement(Base.Vector(7.086898,-161.705845,508.273965),Base.Rotation(0.372521,0.652527,0.000000,0.659876))
App.ActiveDocument.addObject("Part::Cylinder","C1089")
App.ActiveDocument.C1089.Radius=0.750000
App.ActiveDocument.C1089.Height=15.00
App.ActiveDocument.C1089.Angle=360.00 
App.ActiveDocument.C1089.Placement=Base.Placement(Base.Vector(6.821905,-161.258162,505.464960),Base.Rotation(0.376232,0.673021,0.000000,0.636782))
App.ActiveDocument.addObject("Part::Cylinder","C1090")
App.ActiveDocument.C1090.Radius=0.750000
App.ActiveDocument.C1090.Height=15.00
App.ActiveDocument.C1090.Angle=360.00 
App.ActiveDocument.C1090.Placement=Base.Placement(Base.Vector(6.559581,-160.622886,502.974869),Base.Rotation(0.375378,0.689383,0.000000,0.619551))
App.ActiveDocument.addObject("Part::Cylinder","C1091")
App.ActiveDocument.C1091.Radius=0.750000
App.ActiveDocument.C1091.Height=15.00
App.ActiveDocument.C1091.Angle=360.00 
App.ActiveDocument.C1091.Placement=Base.Placement(Base.Vector(6.503184,-159.103929,500.203238),Base.Rotation(0.357415,0.717251,0.000000,0.598168))
App.ActiveDocument.addObject("Part::Cylinder","C1092")
App.ActiveDocument.C1092.Radius=0.750000
App.ActiveDocument.C1092.Height=15.00
App.ActiveDocument.C1092.Angle=360.00 
App.ActiveDocument.C1092.Placement=Base.Placement(Base.Vector(6.087865,-157.898028,497.423233),Base.Rotation(0.344991,0.740057,0.000000,0.577318))
App.ActiveDocument.addObject("Part::Cylinder","C1093")
App.ActiveDocument.C1093.Radius=0.750000
App.ActiveDocument.C1093.Height=15.00
App.ActiveDocument.C1093.Angle=360.00 
App.ActiveDocument.C1093.Placement=Base.Placement(Base.Vector(5.729883,-156.577359,495.097478),Base.Rotation(0.329714,0.758291,0.000000,0.562391))
App.ActiveDocument.addObject("Part::Cylinder","C1094")
App.ActiveDocument.C1094.Radius=0.750000
App.ActiveDocument.C1094.Height=15.00
App.ActiveDocument.C1094.Angle=360.00 
App.ActiveDocument.C1094.Placement=Base.Placement(Base.Vector(5.324787,-155.208946,492.952346),Base.Rotation(0.312376,0.777773,0.000000,0.545426))
App.ActiveDocument.addObject("Part::Cylinder","C1095")
App.ActiveDocument.C1095.Radius=0.750000
App.ActiveDocument.C1095.Height=15.00
App.ActiveDocument.C1095.Angle=360.00 
App.ActiveDocument.C1095.Placement=Base.Placement(Base.Vector(5.112678,-152.756210,490.729349),Base.Rotation(0.262327,0.806939,0.000000,0.529182))
App.ActiveDocument.addObject("Part::Cylinder","C1096")
App.ActiveDocument.C1096.Radius=0.750000
App.ActiveDocument.C1096.Height=15.00
App.ActiveDocument.C1096.Angle=360.00 
App.ActiveDocument.C1096.Placement=Base.Placement(Base.Vector(4.617376,-150.452701,488.504367),Base.Rotation(0.220643,0.828483,0.000000,0.514716))
App.ActiveDocument.addObject("Part::Cylinder","C1097")
App.ActiveDocument.C1097.Radius=0.750000
App.ActiveDocument.C1097.Height=15.00
App.ActiveDocument.C1097.Angle=360.00 
App.ActiveDocument.C1097.Placement=Base.Placement(Base.Vector(3.912034,-148.185032,486.335523),Base.Rotation(0.171925,0.849069,0.000000,0.499524))
App.ActiveDocument.addObject("Part::Cylinder","C1098")
App.ActiveDocument.C1098.Radius=0.750000
App.ActiveDocument.C1098.Height=15.00
App.ActiveDocument.C1098.Angle=360.00 
App.ActiveDocument.C1098.Placement=Base.Placement(Base.Vector(3.061398,-145.836056,484.301616),Base.Rotation(0.114417,0.867592,0.000000,0.483934))
App.ActiveDocument.addObject("Part::Cylinder","C1099")
App.ActiveDocument.C1099.Radius=0.750000
App.ActiveDocument.C1099.Height=15.00
App.ActiveDocument.C1099.Angle=360.00 
App.ActiveDocument.C1099.Placement=Base.Placement(Base.Vector(1.885961,-143.825773,482.200515),Base.Rotation(0.066341,0.882423,0.000000,0.465756))
App.ActiveDocument.addObject("Part::Cylinder","C1100")
App.ActiveDocument.C1100.Radius=0.750000
App.ActiveDocument.C1100.Height=15.00
App.ActiveDocument.C1100.Angle=360.00 
App.ActiveDocument.C1100.Placement=Base.Placement(Base.Vector(0.540066,-142.847329,480.234269),Base.Rotation(0.045730,0.893922,0.000000,0.445883))
App.ActiveDocument.addObject("Part::Cylinder","C1101")
App.ActiveDocument.C1101.Radius=0.750000
App.ActiveDocument.C1101.Height=15.00
App.ActiveDocument.C1101.Angle=360.00 
App.ActiveDocument.C1101.Placement=Base.Placement(Base.Vector(9.075199,-144.103902,529.116649),Base.Rotation(0.030424,0.535979,0.000000,0.843683))
App.ActiveDocument.addObject("Part::Cylinder","C1102")
App.ActiveDocument.C1102.Radius=0.750000
App.ActiveDocument.C1102.Height=15.00
App.ActiveDocument.C1102.Angle=360.00 
App.ActiveDocument.C1102.Placement=Base.Placement(Base.Vector(9.000425,-147.243702,528.673454),Base.Rotation(0.065994,0.539415,0.000000,0.839450))
App.ActiveDocument.addObject("Part::Cylinder","C1103")
App.ActiveDocument.C1103.Radius=0.750000
App.ActiveDocument.C1103.Height=15.00
App.ActiveDocument.C1103.Angle=360.00 
App.ActiveDocument.C1103.Placement=Base.Placement(Base.Vector(9.054305,-150.164025,527.486901),Base.Rotation(0.105656,0.549327,0.000000,0.828901))
App.ActiveDocument.addObject("Part::Cylinder","C1104")
App.ActiveDocument.C1104.Radius=0.750000
App.ActiveDocument.C1104.Height=15.00
App.ActiveDocument.C1104.Angle=360.00 
App.ActiveDocument.C1104.Placement=Base.Placement(Base.Vector(8.918257,-152.779658,526.336523),Base.Rotation(0.146264,0.556031,0.000000,0.818191))
App.ActiveDocument.addObject("Part::Cylinder","C1105")
App.ActiveDocument.C1105.Radius=0.750000
App.ActiveDocument.C1105.Height=15.00
App.ActiveDocument.C1105.Angle=360.00 
App.ActiveDocument.C1105.Placement=Base.Placement(Base.Vector(8.942360,-154.846998,524.528725),Base.Rotation(0.179388,0.571484,0.000000,0.800766))
App.ActiveDocument.addObject("Part::Cylinder","C1106")
App.ActiveDocument.C1106.Radius=0.750000
App.ActiveDocument.C1106.Height=15.00
App.ActiveDocument.C1106.Angle=360.00 
App.ActiveDocument.C1106.Placement=Base.Placement(Base.Vector(8.928395,-156.541996,522.466495),Base.Rotation(0.214532,0.585244,0.000000,0.781963))
App.ActiveDocument.addObject("Part::Cylinder","C1107")
App.ActiveDocument.C1107.Radius=0.750000
App.ActiveDocument.C1107.Height=15.00
App.ActiveDocument.C1107.Angle=360.00 
App.ActiveDocument.C1107.Placement=Base.Placement(Base.Vector(8.931967,-157.643035,520.433033),Base.Rotation(0.241600,0.601050,0.000000,0.761819))
App.ActiveDocument.addObject("Part::Cylinder","C1108")
App.ActiveDocument.C1108.Radius=0.750000
App.ActiveDocument.C1108.Height=15.00
App.ActiveDocument.C1108.Angle=360.00 
App.ActiveDocument.C1108.Placement=Base.Placement(Base.Vector(8.869773,-158.544916,518.278438),Base.Rotation(0.262606,0.615317,0.000000,0.743252))
App.ActiveDocument.addObject("Part::Cylinder","C1109")
App.ActiveDocument.C1109.Radius=0.750000
App.ActiveDocument.C1109.Height=15.00
App.ActiveDocument.C1109.Angle=360.00 
App.ActiveDocument.C1109.Placement=Base.Placement(Base.Vector(8.661571,-159.450507,515.764757),Base.Rotation(0.290581,0.630086,0.000000,0.720108))
App.ActiveDocument.addObject("Part::Cylinder","C1110")
App.ActiveDocument.C1110.Radius=0.750000
App.ActiveDocument.C1110.Height=15.00
App.ActiveDocument.C1110.Angle=360.00 
App.ActiveDocument.C1110.Placement=Base.Placement(Base.Vector(8.794465,-159.158539,512.750862),Base.Rotation(0.294469,0.654302,0.000000,0.696547))
App.ActiveDocument.addObject("Part::Cylinder","C1111")
App.ActiveDocument.C1111.Radius=0.750000
App.ActiveDocument.C1111.Height=15.00
App.ActiveDocument.C1111.Angle=360.00 
App.ActiveDocument.C1111.Placement=Base.Placement(Base.Vector(8.636947,-159.029561,509.769086),Base.Rotation(0.301422,0.676807,0.000000,0.671623))
App.ActiveDocument.addObject("Part::Cylinder","C1112")
App.ActiveDocument.C1112.Radius=0.750000
App.ActiveDocument.C1112.Height=15.00
App.ActiveDocument.C1112.Angle=360.00 
App.ActiveDocument.C1112.Placement=Base.Placement(Base.Vector(8.353440,-158.723957,506.801733),Base.Rotation(0.304922,0.696884,0.000000,0.649134))
App.ActiveDocument.addObject("Part::Cylinder","C1113")
App.ActiveDocument.C1113.Radius=0.750000
App.ActiveDocument.C1113.Height=15.00
App.ActiveDocument.C1113.Angle=360.00 
App.ActiveDocument.C1113.Placement=Base.Placement(Base.Vector(8.085749,-157.986039,503.944185),Base.Rotation(0.306451,0.716795,0.000000,0.626333))
App.ActiveDocument.addObject("Part::Cylinder","C1114")
App.ActiveDocument.C1114.Radius=0.750000
App.ActiveDocument.C1114.Height=15.00
App.ActiveDocument.C1114.Angle=360.00 
App.ActiveDocument.C1114.Placement=Base.Placement(Base.Vector(7.928419,-156.385473,500.952162),Base.Rotation(0.282523,0.743614,0.000000,0.605986))
App.ActiveDocument.addObject("Part::Cylinder","C1115")
App.ActiveDocument.C1115.Radius=0.750000
App.ActiveDocument.C1115.Height=15.00
App.ActiveDocument.C1115.Angle=360.00 
App.ActiveDocument.C1115.Placement=Base.Placement(Base.Vector(7.495235,-155.022648,498.064831),Base.Rotation(0.269849,0.764595,0.000000,0.585300))
App.ActiveDocument.addObject("Part::Cylinder","C1116")
App.ActiveDocument.C1116.Radius=0.750000
App.ActiveDocument.C1116.Height=15.00
App.ActiveDocument.C1116.Angle=360.00 
App.ActiveDocument.C1116.Placement=Base.Placement(Base.Vector(7.022892,-153.362789,495.343988),Base.Rotation(0.245370,0.786523,0.000000,0.566724))
App.ActiveDocument.addObject("Part::Cylinder","C1117")
App.ActiveDocument.C1117.Radius=0.750000
App.ActiveDocument.C1117.Height=15.00
App.ActiveDocument.C1117.Angle=360.00 
App.ActiveDocument.C1117.Placement=Base.Placement(Base.Vector(6.709340,-151.605823,493.367134),Base.Rotation(0.214944,0.805283,0.000000,0.552557))
App.ActiveDocument.addObject("Part::Cylinder","C1118")
App.ActiveDocument.C1118.Radius=0.750000
App.ActiveDocument.C1118.Height=15.00
App.ActiveDocument.C1118.Angle=360.00 
App.ActiveDocument.C1118.Placement=Base.Placement(Base.Vector(6.392533,-149.404360,491.519537),Base.Rotation(0.167152,0.823938,0.000000,0.541466))
App.ActiveDocument.addObject("Part::Cylinder","C1119")
App.ActiveDocument.C1119.Radius=0.750000
App.ActiveDocument.C1119.Height=15.00
App.ActiveDocument.C1119.Angle=360.00 
App.ActiveDocument.C1119.Placement=Base.Placement(Base.Vector(5.699454,-147.305679,489.327375),Base.Rotation(0.124164,0.840123,0.000000,0.527992))
App.ActiveDocument.addObject("Part::Cylinder","C1120")
App.ActiveDocument.C1120.Radius=0.750000
App.ActiveDocument.C1120.Height=15.00
App.ActiveDocument.C1120.Angle=360.00 
App.ActiveDocument.C1120.Placement=Base.Placement(Base.Vector(4.942441,-145.026879,487.357403),Base.Rotation(0.076935,0.855213,0.000000,0.512534))
App.ActiveDocument.addObject("Part::Cylinder","C1121")
App.ActiveDocument.C1121.Radius=0.750000
App.ActiveDocument.C1121.Height=15.00
App.ActiveDocument.C1121.Angle=360.00 
App.ActiveDocument.C1121.Placement=Base.Placement(Base.Vector(3.969856,-143.386011,485.422961),Base.Rotation(0.045023,0.866739,0.000000,0.496725))
App.ActiveDocument.addObject("Part::Cylinder","C1122")
App.ActiveDocument.C1122.Radius=0.750000
App.ActiveDocument.C1122.Height=15.00
App.ActiveDocument.C1122.Angle=360.00 
App.ActiveDocument.C1122.Placement=Base.Placement(Base.Vector(10.192996,-144.075732,526.354646),Base.Rotation(0.030844,0.579107,0.000000,0.814668))
App.ActiveDocument.addObject("Part::Cylinder","C1123")
App.ActiveDocument.C1123.Radius=0.750000
App.ActiveDocument.C1123.Height=15.00
App.ActiveDocument.C1123.Angle=360.00 
App.ActiveDocument.C1123.Placement=Base.Placement(Base.Vector(10.126062,-147.138286,525.809056),Base.Rotation(0.065844,0.584130,0.000000,0.808985))
App.ActiveDocument.addObject("Part::Cylinder","C1124")
App.ActiveDocument.C1124.Radius=0.750000
App.ActiveDocument.C1124.Height=15.00
App.ActiveDocument.C1124.Angle=360.00 
App.ActiveDocument.C1124.Placement=Base.Placement(Base.Vector(10.148057,-149.965851,524.419982),Base.Rotation(0.104039,0.594369,0.000000,0.797434))
App.ActiveDocument.addObject("Part::Cylinder","C1125")
App.ActiveDocument.C1125.Radius=0.750000
App.ActiveDocument.C1125.Height=15.00
App.ActiveDocument.C1125.Angle=360.00 
App.ActiveDocument.C1125.Placement=Base.Placement(Base.Vector(10.044910,-152.353360,522.996088),Base.Rotation(0.137651,0.607049,0.000000,0.782652))
App.ActiveDocument.addObject("Part::Cylinder","C1126")
App.ActiveDocument.C1126.Radius=0.750000
App.ActiveDocument.C1126.Height=15.00
App.ActiveDocument.C1126.Angle=360.00 
App.ActiveDocument.C1126.Placement=Base.Placement(Base.Vector(10.043092,-154.011836,521.019889),Base.Rotation(0.170279,0.620256,0.000000,0.765694))
App.ActiveDocument.addObject("Part::Cylinder","C1127")
App.ActiveDocument.C1127.Radius=0.750000
App.ActiveDocument.C1127.Height=15.00
App.ActiveDocument.C1127.Angle=360.00 
App.ActiveDocument.C1127.Placement=Base.Placement(Base.Vector(10.041362,-155.179991,518.796003),Base.Rotation(0.198745,0.635913,0.000000,0.745731))
App.ActiveDocument.addObject("Part::Cylinder","C1128")
App.ActiveDocument.C1128.Radius=0.750000
App.ActiveDocument.C1128.Height=15.00
App.ActiveDocument.C1128.Angle=360.00 
App.ActiveDocument.C1128.Placement=Base.Placement(Base.Vector(9.902439,-156.223231,516.634699),Base.Rotation(0.224431,0.648410,0.000000,0.727458))
App.ActiveDocument.addObject("Part::Cylinder","C1129")
App.ActiveDocument.C1129.Radius=0.750000
App.ActiveDocument.C1129.Height=15.00
App.ActiveDocument.C1129.Angle=360.00 
App.ActiveDocument.C1129.Placement=Base.Placement(Base.Vector(9.910193,-156.414454,514.009576),Base.Rotation(0.232492,0.669492,0.000000,0.705498))
App.ActiveDocument.addObject("Part::Cylinder","C1130")
App.ActiveDocument.C1130.Radius=0.750000
App.ActiveDocument.C1130.Height=15.00
App.ActiveDocument.C1130.Angle=360.00 
App.ActiveDocument.C1130.Placement=Base.Placement(Base.Vector(9.891389,-156.129299,511.076423),Base.Rotation(0.233597,0.691815,0.000000,0.683245))
App.ActiveDocument.addObject("Part::Cylinder","C1131")
App.ActiveDocument.C1131.Radius=0.750000
App.ActiveDocument.C1131.Height=15.00
App.ActiveDocument.C1131.Angle=360.00 
App.ActiveDocument.C1131.Placement=Base.Placement(Base.Vector(9.674155,-155.846076,508.106103),Base.Rotation(0.240717,0.712423,0.000000,0.659173))
App.ActiveDocument.addObject("Part::Cylinder","C1132")
App.ActiveDocument.C1132.Radius=0.750000
App.ActiveDocument.C1132.Height=15.00
App.ActiveDocument.C1132.Angle=360.00 
App.ActiveDocument.C1132.Placement=Base.Placement(Base.Vector(9.378932,-155.362728,505.362652),Base.Rotation(0.239380,0.731157,0.000000,0.638832))
App.ActiveDocument.addObject("Part::Cylinder","C1133")
App.ActiveDocument.C1133.Radius=0.750000
App.ActiveDocument.C1133.Height=15.00
App.ActiveDocument.C1133.Angle=360.00 
App.ActiveDocument.C1133.Placement=Base.Placement(Base.Vector(9.206376,-154.276211,503.005792),Base.Rotation(0.224247,0.749483,0.000000,0.622887))
App.ActiveDocument.addObject("Part::Cylinder","C1134")
App.ActiveDocument.C1134.Radius=0.750000
App.ActiveDocument.C1134.Height=15.00
App.ActiveDocument.C1134.Angle=360.00 
App.ActiveDocument.C1134.Placement=Base.Placement(Base.Vector(8.880322,-152.894149,500.326660),Base.Rotation(0.205958,0.769895,0.000000,0.604022))
App.ActiveDocument.addObject("Part::Cylinder","C1135")
App.ActiveDocument.C1135.Radius=0.750000
App.ActiveDocument.C1135.Height=15.00
App.ActiveDocument.C1135.Angle=360.00 
App.ActiveDocument.C1135.Placement=Base.Placement(Base.Vector(8.495343,-151.414998,497.906822),Base.Rotation(0.188829,0.786657,0.000000,0.587805))
App.ActiveDocument.addObject("Part::Cylinder","C1136")
App.ActiveDocument.C1136.Radius=0.750000
App.ActiveDocument.C1136.Height=15.00
App.ActiveDocument.C1136.Angle=360.00 
App.ActiveDocument.C1136.Placement=Base.Placement(Base.Vector(8.106364,-149.614351,495.732903),Base.Rotation(0.153678,0.804657,0.000000,0.573507))
App.ActiveDocument.addObject("Part::Cylinder","C1137")
App.ActiveDocument.C1137.Radius=0.750000
App.ActiveDocument.C1137.Height=15.00
App.ActiveDocument.C1137.Angle=360.00 
App.ActiveDocument.C1137.Placement=Base.Placement(Base.Vector(7.725941,-147.709922,493.935232),Base.Rotation(0.116135,0.819512,0.000000,0.561171))
App.ActiveDocument.addObject("Part::Cylinder","C1138")
App.ActiveDocument.C1138.Radius=0.750000
App.ActiveDocument.C1138.Height=15.00
App.ActiveDocument.C1138.Angle=360.00 
App.ActiveDocument.C1138.Placement=Base.Placement(Base.Vector(7.177127,-145.555363,492.032927),Base.Rotation(0.074929,0.832669,0.000000,0.548678))
App.ActiveDocument.addObject("Part::Cylinder","C1139")
App.ActiveDocument.C1139.Radius=0.750000
App.ActiveDocument.C1139.Height=15.00
App.ActiveDocument.C1139.Angle=360.00 
App.ActiveDocument.C1139.Placement=Base.Placement(Base.Vector(6.529555,-143.595692,490.299381),Base.Rotation(0.041459,0.843120,0.000000,0.536125))
App.ActiveDocument.addObject("Part::Cylinder","C1140")
App.ActiveDocument.C1140.Radius=0.750000
App.ActiveDocument.C1140.Height=15.00
App.ActiveDocument.C1140.Angle=360.00 
App.ActiveDocument.C1140.Placement=Base.Placement(Base.Vector(11.056592,-144.002159,523.402735),Base.Rotation(0.030135,0.618347,0.000000,0.785327))
App.ActiveDocument.addObject("Part::Cylinder","C1141")
App.ActiveDocument.C1141.Radius=0.750000
App.ActiveDocument.C1141.Height=15.00
App.ActiveDocument.C1141.Angle=360.00 
App.ActiveDocument.C1141.Placement=Base.Placement(Base.Vector(11.001881,-147.012129,522.645424),Base.Rotation(0.065725,0.623626,0.000000,0.778955))
App.ActiveDocument.addObject("Part::Cylinder","C1142")
App.ActiveDocument.C1142.Radius=0.750000
App.ActiveDocument.C1142.Height=15.00
App.ActiveDocument.C1142.Angle=360.00 
App.ActiveDocument.C1142.Placement=Base.Placement(Base.Vector(10.995708,-149.496678,521.047805),Base.Rotation(0.099447,0.636847,0.000000,0.764550))
App.ActiveDocument.addObject("Part::Cylinder","C1143")
App.ActiveDocument.C1143.Radius=0.750000
App.ActiveDocument.C1143.Height=15.00
App.ActiveDocument.C1143.Angle=360.00 
App.ActiveDocument.C1143.Placement=Base.Placement(Base.Vector(10.937209,-151.394508,519.239092),Base.Rotation(0.130789,0.647953,0.000000,0.750367))
App.ActiveDocument.addObject("Part::Cylinder","C1144")
App.ActiveDocument.C1144.Radius=0.750000
App.ActiveDocument.C1144.Height=15.00
App.ActiveDocument.C1144.Angle=360.00 
App.ActiveDocument.C1144.Placement=Base.Placement(Base.Vector(10.833038,-152.808461,517.250694),Base.Rotation(0.158368,0.662341,0.000000,0.732273))
App.ActiveDocument.addObject("Part::Cylinder","C1145")
App.ActiveDocument.C1145.Radius=0.750000
App.ActiveDocument.C1145.Height=15.00
App.ActiveDocument.C1145.Angle=360.00 
App.ActiveDocument.C1145.Placement=Base.Placement(Base.Vector(10.725471,-153.676667,515.012114),Base.Rotation(0.173122,0.679628,0.000000,0.712835))
App.ActiveDocument.addObject("Part::Cylinder","C1146")
App.ActiveDocument.C1146.Radius=0.750000
App.ActiveDocument.C1146.Height=15.00
App.ActiveDocument.C1146.Angle=360.00 
App.ActiveDocument.C1146.Placement=Base.Placement(Base.Vector(10.837784,-153.081209,512.218359),Base.Rotation(0.167949,0.701113,0.000000,0.692989))
App.ActiveDocument.addObject("Part::Cylinder","C1147")
App.ActiveDocument.C1147.Radius=0.750000
App.ActiveDocument.C1147.Height=15.00
App.ActiveDocument.C1147.Angle=360.00 
App.ActiveDocument.C1147.Placement=Base.Placement(Base.Vector(10.656150,-152.906468,509.283521),Base.Rotation(0.173317,0.722202,0.000000,0.669616))
App.ActiveDocument.addObject("Part::Cylinder","C1148")
App.ActiveDocument.C1148.Radius=0.750000
App.ActiveDocument.C1148.Height=15.00
App.ActiveDocument.C1148.Angle=360.00 
App.ActiveDocument.C1148.Placement=Base.Placement(Base.Vector(10.396484,-152.369367,506.427298),Base.Rotation(0.174611,0.739779,0.000000,0.649798))
App.ActiveDocument.addObject("Part::Cylinder","C1149")
App.ActiveDocument.C1149.Radius=0.750000
App.ActiveDocument.C1149.Height=15.00
App.ActiveDocument.C1149.Angle=360.00 
App.ActiveDocument.C1149.Placement=Base.Placement(Base.Vector(10.091010,-151.621555,503.909379),Base.Rotation(0.163319,0.758548,0.000000,0.630818))
App.ActiveDocument.addObject("Part::Cylinder","C1150")
App.ActiveDocument.C1150.Radius=0.750000
App.ActiveDocument.C1150.Height=15.00
App.ActiveDocument.C1150.Angle=360.00 
App.ActiveDocument.C1150.Placement=Base.Placement(Base.Vector(9.885312,-150.292638,501.876182),Base.Rotation(0.145787,0.774299,0.000000,0.615798))
App.ActiveDocument.addObject("Part::Cylinder","C1151")
App.ActiveDocument.C1151.Radius=0.750000
App.ActiveDocument.C1151.Height=15.00
App.ActiveDocument.C1151.Angle=360.00 
App.ActiveDocument.C1151.Placement=Base.Placement(Base.Vector(9.478837,-148.939425,499.529201),Base.Rotation(0.122267,0.789709,0.000000,0.601174))
App.ActiveDocument.addObject("Part::Cylinder","C1152")
App.ActiveDocument.C1152.Radius=0.750000
App.ActiveDocument.C1152.Height=15.00
App.ActiveDocument.C1152.Angle=360.00 
App.ActiveDocument.C1152.Placement=Base.Placement(Base.Vector(9.051337,-147.326398,497.433364),Base.Rotation(0.096267,0.803659,0.000000,0.587252))
App.ActiveDocument.addObject("Part::Cylinder","C1153")
App.ActiveDocument.C1153.Radius=0.750000
App.ActiveDocument.C1153.Height=15.00
App.ActiveDocument.C1153.Angle=360.00 
App.ActiveDocument.C1153.Placement=Base.Placement(Base.Vector(8.651115,-144.661280,495.586419),Base.Rotation(0.052794,0.816393,0.000000,0.575079))
App.ActiveDocument.addObject("Part::Cylinder","C1154")
App.ActiveDocument.C1154.Radius=0.750000
App.ActiveDocument.C1154.Height=15.00
App.ActiveDocument.C1154.Angle=360.00 
App.ActiveDocument.C1154.Placement=Base.Placement(Base.Vector(7.864910,-143.415288,493.337679),Base.Rotation(0.034336,0.828240,0.000000,0.559321))
App.ActiveDocument.addObject("Part::Cylinder","C1155")
App.ActiveDocument.C1155.Radius=0.750000
App.ActiveDocument.C1155.Height=15.00
App.ActiveDocument.C1155.Angle=360.00 
App.ActiveDocument.C1155.Placement=Base.Placement(Base.Vector(11.657272,-143.981424,520.296591),Base.Rotation(0.030425,0.651832,0.000000,0.757753))
App.ActiveDocument.addObject("Part::Cylinder","C1156")
App.ActiveDocument.C1156.Radius=0.750000
App.ActiveDocument.C1156.Height=15.00
App.ActiveDocument.C1156.Angle=360.00 
App.ActiveDocument.C1156.Placement=Base.Placement(Base.Vector(11.628961,-146.729634,519.079535),Base.Rotation(0.063068,0.661209,0.000000,0.747546))
App.ActiveDocument.addObject("Part::Cylinder","C1157")
App.ActiveDocument.C1157.Radius=0.750000
App.ActiveDocument.C1157.Height=15.00
App.ActiveDocument.C1157.Angle=360.00 
App.ActiveDocument.C1157.Placement=Base.Placement(Base.Vector(11.565398,-148.839177,517.179941),Base.Rotation(0.092346,0.675433,0.000000,0.731617))
App.ActiveDocument.addObject("Part::Cylinder","C1158")
App.ActiveDocument.C1158.Radius=0.750000
App.ActiveDocument.C1158.Height=15.00
App.ActiveDocument.C1158.Angle=360.00 
App.ActiveDocument.C1158.Placement=Base.Placement(Base.Vector(11.434862,-150.307666,515.274352),Base.Rotation(0.116202,0.687904,0.000000,0.716440))
App.ActiveDocument.addObject("Part::Cylinder","C1159")
App.ActiveDocument.C1159.Radius=0.750000
App.ActiveDocument.C1159.Height=15.00
App.ActiveDocument.C1159.Angle=360.00 
App.ActiveDocument.C1159.Placement=Base.Placement(Base.Vector(11.470925,-150.049729,512.754965),Base.Rotation(0.114625,0.707692,0.000000,0.697161))
App.ActiveDocument.addObject("Part::Cylinder","C1160")
App.ActiveDocument.C1160.Radius=0.750000
App.ActiveDocument.C1160.Height=15.00
App.ActiveDocument.C1160.Angle=360.00 
App.ActiveDocument.C1160.Placement=Base.Placement(Base.Vector(11.369212,-149.680407,510.069938),Base.Rotation(0.114823,0.727134,0.000000,0.676825))
App.ActiveDocument.addObject("Part::Cylinder","C1161")
App.ActiveDocument.C1161.Radius=0.750000
App.ActiveDocument.C1161.Height=15.00
App.ActiveDocument.C1161.Angle=360.00 
App.ActiveDocument.C1161.Placement=Base.Placement(Base.Vector(11.105981,-149.332291,507.312791),Base.Rotation(0.112260,0.745792,0.000000,0.656652))
App.ActiveDocument.addObject("Part::Cylinder","C1162")
App.ActiveDocument.C1162.Radius=0.750000
App.ActiveDocument.C1162.Height=15.00
App.ActiveDocument.C1162.Angle=360.00 
App.ActiveDocument.C1162.Placement=Base.Placement(Base.Vector(10.803436,-148.488356,504.758360),Base.Rotation(0.102779,0.763070,0.000000,0.638091))
App.ActiveDocument.addObject("Part::Cylinder","C1163")
App.ActiveDocument.C1163.Radius=0.750000
App.ActiveDocument.C1163.Height=15.00
App.ActiveDocument.C1163.Angle=360.00 
App.ActiveDocument.C1163.Placement=Base.Placement(Base.Vector(10.459214,-146.558328,502.148759),Base.Rotation(0.074727,0.780811,0.000000,0.620283))
App.ActiveDocument.addObject("Part::Cylinder","C1164")
App.ActiveDocument.C1164.Radius=0.750000
App.ActiveDocument.C1164.Height=15.00
App.ActiveDocument.C1164.Angle=360.00 
App.ActiveDocument.C1164.Placement=Base.Placement(Base.Vector(9.985040,-144.962399,499.805481),Base.Rotation(0.052082,0.794743,0.000000,0.604707))
App.ActiveDocument.addObject("Part::Cylinder","C1165")
App.ActiveDocument.C1165.Radius=0.750000
App.ActiveDocument.C1165.Height=15.00
App.ActiveDocument.C1165.Angle=360.00 
App.ActiveDocument.C1165.Placement=Base.Placement(Base.Vector(9.638231,-143.064404,498.301567),Base.Rotation(0.026133,0.803697,0.000000,0.594465))
App.ActiveDocument.addObject("Part::Cylinder","C1166")
App.ActiveDocument.C1166.Radius=0.750000
App.ActiveDocument.C1166.Height=15.00
App.ActiveDocument.C1166.Angle=360.00 
App.ActiveDocument.C1166.Placement=Base.Placement(Base.Vector(12.014375,-143.769672,516.983984),Base.Rotation(0.028333,0.683219,0.000000,0.729664))
App.ActiveDocument.addObject("Part::Cylinder","C1167")
App.ActiveDocument.C1167.Radius=0.750000
App.ActiveDocument.C1167.Height=15.00
App.ActiveDocument.C1167.Angle=360.00 
App.ActiveDocument.C1167.Placement=Base.Placement(Base.Vector(11.962902,-145.998392,515.161935),Base.Rotation(0.057112,0.698349,0.000000,0.713475))
App.ActiveDocument.addObject("Part::Cylinder","C1168")
App.ActiveDocument.C1168.Radius=0.750000
App.ActiveDocument.C1168.Height=15.00
App.ActiveDocument.C1168.Angle=360.00 
App.ActiveDocument.C1168.Placement=Base.Placement(Base.Vector(11.811965,-147.625761,513.209050),Base.Rotation(0.079599,0.708314,0.000000,0.701395))
App.ActiveDocument.addObject("Part::Cylinder","C1169")
App.ActiveDocument.C1169.Radius=0.750000
App.ActiveDocument.C1169.Height=15.00
App.ActiveDocument.C1169.Angle=360.00 
App.ActiveDocument.C1169.Placement=Base.Placement(Base.Vector(11.843705,-146.259234,510.982669),Base.Rotation(0.061917,0.727748,0.000000,0.683045))
App.ActiveDocument.addObject("Part::Cylinder","C1170")
App.ActiveDocument.C1170.Radius=0.750000
App.ActiveDocument.C1170.Height=15.00
App.ActiveDocument.C1170.Angle=360.00 
App.ActiveDocument.C1170.Placement=Base.Placement(Base.Vector(11.600942,-145.969582,508.175834),Base.Rotation(0.059946,0.746153,0.000000,0.663070))
App.ActiveDocument.addObject("Part::Cylinder","C1171")
App.ActiveDocument.C1171.Radius=0.750000
App.ActiveDocument.C1171.Height=15.00
App.ActiveDocument.C1171.Angle=360.00 
App.ActiveDocument.C1171.Placement=Base.Placement(Base.Vector(11.291461,-145.244625,505.688083),Base.Rotation(0.051382,0.762153,0.000000,0.645355))
App.ActiveDocument.addObject("Part::Cylinder","C1172")
App.ActiveDocument.C1172.Radius=0.750000
App.ActiveDocument.C1172.Height=15.00
App.ActiveDocument.C1172.Angle=360.00 
App.ActiveDocument.C1172.Placement=Base.Placement(Base.Vector(10.966089,-143.633634,503.549498),Base.Rotation(0.031128,0.775312,0.000000,0.630811))
App.ActiveDocument.addObject("Part::Cylinder","C1173")
App.ActiveDocument.C1173.Radius=0.750000
App.ActiveDocument.C1173.Height=15.00
App.ActiveDocument.C1173.Angle=360.00 
App.ActiveDocument.C1173.Placement=Base.Placement(Base.Vector(12.102768,-143.503691,513.087547),Base.Rotation(0.025929,0.714662,0.000000,0.698990))
App.ActiveDocument.addObject("Part::Cylinder","C1174")
App.ActiveDocument.C1174.Radius=0.750000
App.ActiveDocument.C1174.Height=15.00
App.ActiveDocument.C1174.Angle=360.00 
App.ActiveDocument.C1174.Placement=Base.Placement(Base.Vector(11.975380,-143.408604,510.460177),Base.Rotation(0.025325,0.733555,0.000000,0.679158))
App.ActiveDocument.addObject("Part::Cylinder","C1175")
App.ActiveDocument.C1175.Radius=0.750000
App.ActiveDocument.C1175.Height=15.00
App.ActiveDocument.C1175.Angle=360.00 
App.ActiveDocument.C1175.Placement=Base.Placement(Base.Vector(11.738336,-143.073243,508.014789),Base.Rotation(0.022699,0.749295,0.000000,0.661847))
App.ActiveDocument.addObject("Part::Cylinder","C1176")
App.ActiveDocument.C1176.Radius=0.750000
App.ActiveDocument.C1176.Height=15.00
App.ActiveDocument.C1176.Angle=360.00 
App.ActiveDocument.C1176.Placement=Base.Placement(Base.Vector(-35.064827,-137.434977,548.179005),Base.Rotation(-0.028936,-0.079513,0.000000,0.996414))
App.ActiveDocument.addObject("Part::Cylinder","C1177")
App.ActiveDocument.C1177.Radius=0.750000
App.ActiveDocument.C1177.Height=15.00
App.ActiveDocument.C1177.Angle=360.00 
App.ActiveDocument.C1177.Placement=Base.Placement(Base.Vector(-35.106922,-134.046667,547.872829),Base.Rotation(-0.058832,-0.078118,0.000000,0.995207))
App.ActiveDocument.addObject("Part::Cylinder","C1178")
App.ActiveDocument.C1178.Radius=0.750000
App.ActiveDocument.C1178.Height=15.00
App.ActiveDocument.C1178.Angle=360.00 
App.ActiveDocument.C1178.Placement=Base.Placement(Base.Vector(-35.090645,-130.764052,547.375441),Base.Rotation(-0.091115,-0.076266,0.000000,0.992916))
App.ActiveDocument.addObject("Part::Cylinder","C1179")
App.ActiveDocument.C1179.Radius=0.750000
App.ActiveDocument.C1179.Height=15.00
App.ActiveDocument.C1179.Angle=360.00 
App.ActiveDocument.C1179.Placement=Base.Placement(Base.Vector(-35.116511,-127.606889,546.664237),Base.Rotation(-0.127927,-0.073895,0.000000,0.989027))
App.ActiveDocument.addObject("Part::Cylinder","C1180")
App.ActiveDocument.C1180.Radius=0.750000
App.ActiveDocument.C1180.Height=15.00
App.ActiveDocument.C1180.Angle=360.00 
App.ActiveDocument.C1180.Placement=Base.Placement(Base.Vector(-35.179438,-124.477875,545.700127),Base.Rotation(-0.168401,-0.070141,0.000000,0.983220))
App.ActiveDocument.addObject("Part::Cylinder","C1181")
App.ActiveDocument.C1181.Radius=0.750000
App.ActiveDocument.C1181.Height=15.00
App.ActiveDocument.C1181.Angle=360.00 
App.ActiveDocument.C1181.Placement=Base.Placement(Base.Vector(-35.267547,-121.507841,544.496551),Base.Rotation(-0.208149,-0.071082,0.000000,0.975511))
App.ActiveDocument.addObject("Part::Cylinder","C1182")
App.ActiveDocument.C1182.Radius=0.750000
App.ActiveDocument.C1182.Height=15.00
App.ActiveDocument.C1182.Angle=360.00 
App.ActiveDocument.C1182.Placement=Base.Placement(Base.Vector(-35.345871,-118.790953,543.105583),Base.Rotation(-0.253893,-0.065759,0.000000,0.964994))
App.ActiveDocument.addObject("Part::Cylinder","C1183")
App.ActiveDocument.C1183.Radius=0.750000
App.ActiveDocument.C1183.Height=15.00
App.ActiveDocument.C1183.Angle=360.00 
App.ActiveDocument.C1183.Placement=Base.Placement(Base.Vector(-35.420922,-116.243086,541.489246),Base.Rotation(-0.298801,-0.063260,0.000000,0.952217))
App.ActiveDocument.addObject("Part::Cylinder","C1184")
App.ActiveDocument.C1184.Radius=0.750000
App.ActiveDocument.C1184.Height=15.00
App.ActiveDocument.C1184.Angle=360.00 
App.ActiveDocument.C1184.Placement=Base.Placement(Base.Vector(-35.526995,-113.874017,539.639981),Base.Rotation(-0.343577,-0.059443,0.000000,0.937241))
App.ActiveDocument.addObject("Part::Cylinder","C1185")
App.ActiveDocument.C1185.Radius=0.750000
App.ActiveDocument.C1185.Height=15.00
App.ActiveDocument.C1185.Angle=360.00 
App.ActiveDocument.C1185.Placement=Base.Placement(Base.Vector(-35.626895,-111.646957,537.525672),Base.Rotation(-0.393407,-0.054028,0.000000,0.917776))
App.ActiveDocument.addObject("Part::Cylinder","C1186")
App.ActiveDocument.C1186.Radius=0.750000
App.ActiveDocument.C1186.Height=15.00
App.ActiveDocument.C1186.Angle=360.00 
App.ActiveDocument.C1186.Placement=Base.Placement(Base.Vector(-35.753012,-109.608819,535.163151),Base.Rotation(-0.434857,-0.053582,0.000000,0.898904))
App.ActiveDocument.addObject("Part::Cylinder","C1187")
App.ActiveDocument.C1187.Radius=0.750000
App.ActiveDocument.C1187.Height=15.00
App.ActiveDocument.C1187.Angle=360.00 
App.ActiveDocument.C1187.Placement=Base.Placement(Base.Vector(-35.774785,-107.830414,532.674446),Base.Rotation(-0.477165,-0.045762,0.000000,0.877621))
App.ActiveDocument.addObject("Part::Cylinder","C1188")
App.ActiveDocument.C1188.Radius=0.750000
App.ActiveDocument.C1188.Height=15.00
App.ActiveDocument.C1188.Angle=360.00 
App.ActiveDocument.C1188.Placement=Base.Placement(Base.Vector(-35.857591,-106.200120,529.877752),Base.Rotation(-0.515210,-0.044986,0.000000,0.855882))
App.ActiveDocument.addObject("Part::Cylinder","C1189")
App.ActiveDocument.C1189.Radius=0.750000
App.ActiveDocument.C1189.Height=15.00
App.ActiveDocument.C1189.Angle=360.00 
App.ActiveDocument.C1189.Placement=Base.Placement(Base.Vector(-35.900175,-104.826026,526.974427),Base.Rotation(-0.551063,-0.040889,0.000000,0.833461))
App.ActiveDocument.addObject("Part::Cylinder","C1190")
App.ActiveDocument.C1190.Radius=0.750000
App.ActiveDocument.C1190.Height=15.00
App.ActiveDocument.C1190.Angle=360.00 
App.ActiveDocument.C1190.Placement=Base.Placement(Base.Vector(-36.024236,-103.700556,523.991668),Base.Rotation(-0.582675,-0.040186,0.000000,0.811711))
App.ActiveDocument.addObject("Part::Cylinder","C1191")
App.ActiveDocument.C1191.Radius=0.750000
App.ActiveDocument.C1191.Height=15.00
App.ActiveDocument.C1191.Angle=360.00 
App.ActiveDocument.C1191.Placement=Base.Placement(Base.Vector(-36.020939,-102.762659,520.830205),Base.Rotation(-0.611394,-0.036319,0.000000,0.790492))
App.ActiveDocument.addObject("Part::Cylinder","C1192")
App.ActiveDocument.C1192.Radius=0.750000
App.ActiveDocument.C1192.Height=15.00
App.ActiveDocument.C1192.Angle=360.00 
App.ActiveDocument.C1192.Placement=Base.Placement(Base.Vector(-36.131081,-102.056880,517.616779),Base.Rotation(-0.638787,-0.032731,0.000000,0.768687))
App.ActiveDocument.addObject("Part::Cylinder","C1193")
App.ActiveDocument.C1193.Radius=0.750000
App.ActiveDocument.C1193.Height=15.00
App.ActiveDocument.C1193.Angle=360.00 
App.ActiveDocument.C1193.Placement=Base.Placement(Base.Vector(-36.165797,-101.560531,514.351197),Base.Rotation(-0.662958,-0.029067,0.000000,0.748092))
App.ActiveDocument.addObject("Part::Cylinder","C1194")
App.ActiveDocument.C1194.Radius=0.750000
App.ActiveDocument.C1194.Height=15.00
App.ActiveDocument.C1194.Angle=360.00 
App.ActiveDocument.C1194.Placement=Base.Placement(Base.Vector(-36.240154,-101.269053,511.012084),Base.Rotation(-0.686209,-0.024552,0.000000,0.726990))
App.ActiveDocument.addObject("Part::Cylinder","C1195")
App.ActiveDocument.C1195.Radius=0.750000
App.ActiveDocument.C1195.Height=15.00
App.ActiveDocument.C1195.Angle=360.00 
App.ActiveDocument.C1195.Placement=Base.Placement(Base.Vector(-36.314632,-101.182785,507.657798),Base.Rotation(-0.707426,-0.015771,0.000000,0.706611))
App.ActiveDocument.addObject("Part::Cylinder","C1196")
App.ActiveDocument.C1196.Radius=0.750000
App.ActiveDocument.C1196.Height=15.00
App.ActiveDocument.C1196.Angle=360.00 
App.ActiveDocument.C1196.Placement=Base.Placement(Base.Vector(-36.567433,-101.299795,504.283427),Base.Rotation(-0.728590,-0.008170,0.000000,0.684902))
App.ActiveDocument.addObject("Part::Cylinder","C1197")
App.ActiveDocument.C1197.Radius=0.750000
App.ActiveDocument.C1197.Height=15.00
App.ActiveDocument.C1197.Angle=360.00 
App.ActiveDocument.C1197.Placement=Base.Placement(Base.Vector(-36.603508,-101.603073,500.933243),Base.Rotation(-0.747731,0.000522,0.000000,0.664002))
App.ActiveDocument.addObject("Part::Cylinder","C1198")
App.ActiveDocument.C1198.Radius=0.750000
App.ActiveDocument.C1198.Height=15.00
App.ActiveDocument.C1198.Angle=360.00 
App.ActiveDocument.C1198.Placement=Base.Placement(Base.Vector(-36.760769,-102.106579,497.500118),Base.Rotation(-0.765955,0.009472,0.000000,0.642825))
App.ActiveDocument.addObject("Part::Cylinder","C1199")
App.ActiveDocument.C1199.Radius=0.750000
App.ActiveDocument.C1199.Height=15.00
App.ActiveDocument.C1199.Angle=360.00 
App.ActiveDocument.C1199.Placement=Base.Placement(Base.Vector(-36.813524,-102.785818,494.141493),Base.Rotation(-0.781981,0.017084,0.000000,0.623069))
App.ActiveDocument.addObject("Part::Cylinder","C1200")
App.ActiveDocument.C1200.Radius=0.750000
App.ActiveDocument.C1200.Height=15.00
App.ActiveDocument.C1200.Angle=360.00 
App.ActiveDocument.C1200.Placement=Base.Placement(Base.Vector(-36.844067,-103.654964,490.772031),Base.Rotation(-0.797919,0.024749,0.000000,0.602257))
App.ActiveDocument.addObject("Part::Cylinder","C1201")
App.ActiveDocument.C1201.Radius=0.750000
App.ActiveDocument.C1201.Height=15.00
App.ActiveDocument.C1201.Angle=360.00 
App.ActiveDocument.C1201.Placement=Base.Placement(Base.Vector(-36.999949,-104.696705,487.441548),Base.Rotation(-0.813915,0.031191,0.000000,0.580145))
App.ActiveDocument.addObject("Part::Cylinder","C1202")
App.ActiveDocument.C1202.Radius=0.750000
App.ActiveDocument.C1202.Height=15.00
App.ActiveDocument.C1202.Angle=360.00 
App.ActiveDocument.C1202.Placement=Base.Placement(Base.Vector(-37.055933,-105.902626,484.211547),Base.Rotation(-0.827762,0.039260,0.000000,0.559704))
App.ActiveDocument.addObject("Part::Cylinder","C1203")
App.ActiveDocument.C1203.Radius=0.750000
App.ActiveDocument.C1203.Height=15.00
App.ActiveDocument.C1203.Angle=360.00 
App.ActiveDocument.C1203.Placement=Base.Placement(Base.Vector(-37.070573,-107.266822,481.088653),Base.Rotation(-0.842728,0.050208,0.000000,0.535993))
App.ActiveDocument.addObject("Part::Cylinder","C1204")
App.ActiveDocument.C1204.Radius=0.750000
App.ActiveDocument.C1204.Height=15.00
App.ActiveDocument.C1204.Angle=360.00 
App.ActiveDocument.C1204.Placement=Base.Placement(Base.Vector(-37.190532,-108.805650,478.019334),Base.Rotation(-0.856539,0.061500,0.000000,0.512405))
App.ActiveDocument.addObject("Part::Cylinder","C1205")
App.ActiveDocument.C1205.Radius=0.750000
App.ActiveDocument.C1205.Height=15.00
App.ActiveDocument.C1205.Angle=360.00 
App.ActiveDocument.C1205.Placement=Base.Placement(Base.Vector(-37.293678,-110.502205,475.071966),Base.Rotation(-0.870060,0.072991,0.000000,0.487511))
App.ActiveDocument.addObject("Part::Cylinder","C1206")
App.ActiveDocument.C1206.Radius=0.750000
App.ActiveDocument.C1206.Height=15.00
App.ActiveDocument.C1206.Angle=360.00 
App.ActiveDocument.C1206.Placement=Base.Placement(Base.Vector(-37.313135,-112.352413,472.273223),Base.Rotation(-0.883546,0.087185,0.000000,0.460158))
App.ActiveDocument.addObject("Part::Cylinder","C1207")
App.ActiveDocument.C1207.Radius=0.750000
App.ActiveDocument.C1207.Height=15.00
App.ActiveDocument.C1207.Angle=360.00 
App.ActiveDocument.C1207.Placement=Base.Placement(Base.Vector(-37.412390,-114.371679,469.597599),Base.Rotation(-0.896484,0.102258,0.000000,0.431115))
App.ActiveDocument.addObject("Part::Cylinder","C1208")
App.ActiveDocument.C1208.Radius=0.750000
App.ActiveDocument.C1208.Height=15.00
App.ActiveDocument.C1208.Angle=360.00 
App.ActiveDocument.C1208.Placement=Base.Placement(Base.Vector(-38.227847,-137.436843,547.545914),Base.Rotation(-0.027961,-0.116658,0.000000,0.992778))
App.ActiveDocument.addObject("Part::Cylinder","C1209")
App.ActiveDocument.C1209.Radius=0.750000
App.ActiveDocument.C1209.Height=15.00
App.ActiveDocument.C1209.Angle=360.00 
App.ActiveDocument.C1209.Placement=Base.Placement(Base.Vector(-38.270203,-134.045024,547.240356),Base.Rotation(-0.057885,-0.116373,0.000000,0.991517))
App.ActiveDocument.addObject("Part::Cylinder","C1210")
App.ActiveDocument.C1210.Radius=0.750000
App.ActiveDocument.C1210.Height=15.00
App.ActiveDocument.C1210.Angle=360.00 
App.ActiveDocument.C1210.Placement=Base.Placement(Base.Vector(-38.248804,-130.730152,546.742659),Base.Rotation(-0.090181,-0.116067,0.000000,0.989139))
App.ActiveDocument.addObject("Part::Cylinder","C1211")
App.ActiveDocument.C1211.Radius=0.750000
App.ActiveDocument.C1211.Height=15.00
App.ActiveDocument.C1211.Angle=360.00 
App.ActiveDocument.C1211.Placement=Base.Placement(Base.Vector(-38.223898,-127.594641,546.045910),Base.Rotation(-0.125562,-0.115633,0.000000,0.985324))
App.ActiveDocument.addObject("Part::Cylinder","C1212")
App.ActiveDocument.C1212.Radius=0.750000
App.ActiveDocument.C1212.Height=15.00
App.ActiveDocument.C1212.Angle=360.00 
App.ActiveDocument.C1212.Placement=Base.Placement(Base.Vector(-38.221261,-124.508661,545.105688),Base.Rotation(-0.165113,-0.112849,0.000000,0.979797))
App.ActiveDocument.addObject("Part::Cylinder","C1213")
App.ActiveDocument.C1213.Radius=0.750000
App.ActiveDocument.C1213.Height=15.00
App.ActiveDocument.C1213.Angle=360.00 
App.ActiveDocument.C1213.Placement=Base.Placement(Base.Vector(-38.344337,-121.644238,543.936781),Base.Rotation(-0.204353,-0.114415,0.000000,0.972188))
App.ActiveDocument.addObject("Part::Cylinder","C1214")
App.ActiveDocument.C1214.Radius=0.750000
App.ActiveDocument.C1214.Height=15.00
App.ActiveDocument.C1214.Angle=360.00 
App.ActiveDocument.C1214.Placement=Base.Placement(Base.Vector(-38.279958,-118.899287,542.571070),Base.Rotation(-0.248818,-0.111512,0.000000,0.962109))
App.ActiveDocument.addObject("Part::Cylinder","C1215")
App.ActiveDocument.C1215.Radius=0.750000
App.ActiveDocument.C1215.Height=15.00
App.ActiveDocument.C1215.Angle=360.00 
App.ActiveDocument.C1215.Placement=Base.Placement(Base.Vector(-38.488866,-116.334881,540.911959),Base.Rotation(-0.293355,-0.111745,0.000000,0.949450))
App.ActiveDocument.addObject("Part::Cylinder","C1216")
App.ActiveDocument.C1216.Radius=0.750000
App.ActiveDocument.C1216.Height=15.00
App.ActiveDocument.C1216.Angle=360.00 
App.ActiveDocument.C1216.Placement=Base.Placement(Base.Vector(-38.531268,-113.936649,539.052806),Base.Rotation(-0.340238,-0.111886,0.000000,0.933659))
App.ActiveDocument.addObject("Part::Cylinder","C1217")
App.ActiveDocument.C1217.Radius=0.750000
App.ActiveDocument.C1217.Height=15.00
App.ActiveDocument.C1217.Angle=360.00 
App.ActiveDocument.C1217.Placement=Base.Placement(Base.Vector(-38.604682,-111.724232,536.954421),Base.Rotation(-0.386572,-0.108689,0.000000,0.915833))
App.ActiveDocument.addObject("Part::Cylinder","C1218")
App.ActiveDocument.C1218.Radius=0.750000
App.ActiveDocument.C1218.Height=15.00
App.ActiveDocument.C1218.Angle=360.00 
App.ActiveDocument.C1218.Placement=Base.Placement(Base.Vector(-38.750836,-109.723446,534.620042),Base.Rotation(-0.428629,-0.104298,0.000000,0.897440))
App.ActiveDocument.addObject("Part::Cylinder","C1219")
App.ActiveDocument.C1219.Radius=0.750000
App.ActiveDocument.C1219.Height=15.00
App.ActiveDocument.C1219.Angle=360.00 
App.ActiveDocument.C1219.Placement=Base.Placement(Base.Vector(-38.815513,-107.934516,532.111943),Base.Rotation(-0.469976,-0.100485,0.000000,0.876941))
App.ActiveDocument.addObject("Part::Cylinder","C1220")
App.ActiveDocument.C1220.Radius=0.750000
App.ActiveDocument.C1220.Height=15.00
App.ActiveDocument.C1220.Angle=360.00 
App.ActiveDocument.C1220.Placement=Base.Placement(Base.Vector(-38.895637,-106.365832,529.418857),Base.Rotation(-0.508646,-0.095635,0.000000,0.855648))
App.ActiveDocument.addObject("Part::Cylinder","C1221")
App.ActiveDocument.C1221.Radius=0.750000
App.ActiveDocument.C1221.Height=15.00
App.ActiveDocument.C1221.Angle=360.00 
App.ActiveDocument.C1221.Placement=Base.Placement(Base.Vector(-39.048964,-105.009251,526.529721),Base.Rotation(-0.544347,-0.090855,0.000000,0.833925))
App.ActiveDocument.addObject("Part::Cylinder","C1222")
App.ActiveDocument.C1222.Radius=0.750000
App.ActiveDocument.C1222.Height=15.00
App.ActiveDocument.C1222.Angle=360.00 
App.ActiveDocument.C1222.Placement=Base.Placement(Base.Vector(-39.244648,-103.890223,523.526238),Base.Rotation(-0.577542,-0.088212,0.000000,0.811581))
App.ActiveDocument.addObject("Part::Cylinder","C1223")
App.ActiveDocument.C1223.Radius=0.750000
App.ActiveDocument.C1223.Height=15.00
App.ActiveDocument.C1223.Angle=360.00 
App.ActiveDocument.C1223.Placement=Base.Placement(Base.Vector(-39.268119,-102.940627,520.334368),Base.Rotation(-0.608002,-0.080650,0.000000,0.789828))
App.ActiveDocument.addObject("Part::Cylinder","C1224")
App.ActiveDocument.C1224.Radius=0.750000
App.ActiveDocument.C1224.Height=15.00
App.ActiveDocument.C1224.Angle=360.00 
App.ActiveDocument.C1224.Placement=Base.Placement(Base.Vector(-39.408044,-102.240236,517.104487),Base.Rotation(-0.634155,-0.078877,0.000000,0.769173))
App.ActiveDocument.addObject("Part::Cylinder","C1225")
App.ActiveDocument.C1225.Radius=0.750000
App.ActiveDocument.C1225.Height=15.00
App.ActiveDocument.C1225.Angle=360.00 
App.ActiveDocument.C1225.Placement=Base.Placement(Base.Vector(-39.448191,-101.737504,513.804402),Base.Rotation(-0.659322,-0.072758,0.000000,0.748332))
App.ActiveDocument.addObject("Part::Cylinder","C1226")
App.ActiveDocument.C1226.Radius=0.750000
App.ActiveDocument.C1226.Height=15.00
App.ActiveDocument.C1226.Angle=360.00 
App.ActiveDocument.C1226.Placement=Base.Placement(Base.Vector(-39.635370,-101.453182,510.418762),Base.Rotation(-0.682368,-0.068726,0.000000,0.727771))
App.ActiveDocument.addObject("Part::Cylinder","C1227")
App.ActiveDocument.C1227.Radius=0.750000
App.ActiveDocument.C1227.Height=15.00
App.ActiveDocument.C1227.Angle=360.00 
App.ActiveDocument.C1227.Placement=Base.Placement(Base.Vector(-39.645388,-101.356763,507.077514),Base.Rotation(-0.705114,-0.060749,0.000000,0.706487))
App.ActiveDocument.addObject("Part::Cylinder","C1228")
App.ActiveDocument.C1228.Radius=0.750000
App.ActiveDocument.C1228.Height=15.00
App.ActiveDocument.C1228.Angle=360.00 
App.ActiveDocument.C1228.Placement=Base.Placement(Base.Vector(-39.943370,-101.480248,503.649544),Base.Rotation(-0.724940,-0.055863,0.000000,0.686543))
App.ActiveDocument.addObject("Part::Cylinder","C1229")
App.ActiveDocument.C1229.Radius=0.750000
App.ActiveDocument.C1229.Height=15.00
App.ActiveDocument.C1229.Angle=360.00 
App.ActiveDocument.C1229.Placement=Base.Placement(Base.Vector(-39.997598,-101.771212,500.295048),Base.Rotation(-0.745559,-0.042387,0.000000,0.665090))
App.ActiveDocument.addObject("Part::Cylinder","C1230")
App.ActiveDocument.C1230.Radius=0.750000
App.ActiveDocument.C1230.Height=15.00
App.ActiveDocument.C1230.Angle=360.00 
App.ActiveDocument.C1230.Placement=Base.Placement(Base.Vector(-40.121910,-102.269439,496.849665),Base.Rotation(-0.763219,-0.035165,0.000000,0.645183))
App.ActiveDocument.addObject("Part::Cylinder","C1231")
App.ActiveDocument.C1231.Radius=0.750000
App.ActiveDocument.C1231.Height=15.00
App.ActiveDocument.C1231.Angle=360.00 
App.ActiveDocument.C1231.Placement=Base.Placement(Base.Vector(-40.278638,-102.941720,493.518269),Base.Rotation(-0.781381,-0.025904,0.000000,0.623516))
App.ActiveDocument.addObject("Part::Cylinder","C1232")
App.ActiveDocument.C1232.Radius=0.750000
App.ActiveDocument.C1232.Height=15.00
App.ActiveDocument.C1232.Angle=360.00 
App.ActiveDocument.C1232.Placement=Base.Placement(Base.Vector(-40.381050,-103.795463,490.195525),Base.Rotation(-0.798086,-0.016350,0.000000,0.602322))
App.ActiveDocument.addObject("Part::Cylinder","C1233")
App.ActiveDocument.C1233.Radius=0.750000
App.ActiveDocument.C1233.Height=15.00
App.ActiveDocument.C1233.Angle=360.00 
App.ActiveDocument.C1233.Placement=Base.Placement(Base.Vector(-40.510339,-104.825983,486.922015),Base.Rotation(-0.813581,-0.009705,0.000000,0.581371))
App.ActiveDocument.addObject("Part::Cylinder","C1234")
App.ActiveDocument.C1234.Radius=0.750000
App.ActiveDocument.C1234.Height=15.00
App.ActiveDocument.C1234.Angle=360.00 
App.ActiveDocument.C1234.Placement=Base.Placement(Base.Vector(-40.596074,-106.052134,483.642701),Base.Rotation(-0.829236,-0.002338,0.000000,0.558894))
App.ActiveDocument.addObject("Part::Cylinder","C1235")
App.ActiveDocument.C1235.Radius=0.750000
App.ActiveDocument.C1235.Height=15.00
App.ActiveDocument.C1235.Angle=360.00 
App.ActiveDocument.C1235.Placement=Base.Placement(Base.Vector(-40.583741,-107.379446,480.596038),Base.Rotation(-0.842868,0.002996,0.000000,0.538113))
App.ActiveDocument.addObject("Part::Cylinder","C1236")
App.ActiveDocument.C1236.Radius=0.750000
App.ActiveDocument.C1236.Height=15.00
App.ActiveDocument.C1236.Angle=360.00 
App.ActiveDocument.C1236.Placement=Base.Placement(Base.Vector(-40.673413,-108.879386,477.602906),Base.Rotation(-0.857474,0.011180,0.000000,0.514405))
App.ActiveDocument.addObject("Part::Cylinder","C1237")
App.ActiveDocument.C1237.Radius=0.750000
App.ActiveDocument.C1237.Height=15.00
App.ActiveDocument.C1237.Angle=360.00 
App.ActiveDocument.C1237.Placement=Base.Placement(Base.Vector(-40.827042,-110.550358,474.689186),Base.Rotation(-0.872341,0.018854,0.000000,0.488535))
App.ActiveDocument.addObject("Part::Cylinder","C1238")
App.ActiveDocument.C1238.Radius=0.750000
App.ActiveDocument.C1238.Height=15.00
App.ActiveDocument.C1238.Angle=360.00 
App.ActiveDocument.C1238.Placement=Base.Placement(Base.Vector(-40.762755,-112.391915,471.891062),Base.Rotation(-0.886936,0.030450,0.000000,0.460888))
App.ActiveDocument.addObject("Part::Cylinder","C1239")
App.ActiveDocument.C1239.Radius=0.750000
App.ActiveDocument.C1239.Height=15.00
App.ActiveDocument.C1239.Angle=360.00 
App.ActiveDocument.C1239.Placement=Base.Placement(Base.Vector(-40.865204,-114.423435,469.193947),Base.Rotation(-0.901480,0.041597,0.000000,0.430818))
App.ActiveDocument.addObject("Part::Cylinder","C1240")
App.ActiveDocument.C1240.Radius=0.750000
App.ActiveDocument.C1240.Height=15.00
App.ActiveDocument.C1240.Angle=360.00 
App.ActiveDocument.C1240.Placement=Base.Placement(Base.Vector(-41.377380,-137.425495,546.676163),Base.Rotation(-0.028674,-0.150813,0.000000,0.988146))
App.ActiveDocument.addObject("Part::Cylinder","C1241")
App.ActiveDocument.C1241.Radius=0.750000
App.ActiveDocument.C1241.Height=15.00
App.ActiveDocument.C1241.Angle=360.00 
App.ActiveDocument.C1241.Placement=Base.Placement(Base.Vector(-41.421818,-134.003365,546.359170),Base.Rotation(-0.057898,-0.151810,0.000000,0.986712))
App.ActiveDocument.addObject("Part::Cylinder","C1242")
App.ActiveDocument.C1242.Radius=0.750000
App.ActiveDocument.C1242.Height=15.00
App.ActiveDocument.C1242.Angle=360.00 
App.ActiveDocument.C1242.Placement=Base.Placement(Base.Vector(-41.431618,-130.706691,545.847837),Base.Rotation(-0.090830,-0.151528,0.000000,0.984271))
App.ActiveDocument.addObject("Part::Cylinder","C1243")
App.ActiveDocument.C1243.Radius=0.750000
App.ActiveDocument.C1243.Height=15.00
App.ActiveDocument.C1243.Angle=360.00 
App.ActiveDocument.C1243.Placement=Base.Placement(Base.Vector(-41.355887,-127.519802,545.144499),Base.Rotation(-0.126683,-0.151481,0.000000,0.980309))
App.ActiveDocument.addObject("Part::Cylinder","C1244")
App.ActiveDocument.C1244.Radius=0.750000
App.ActiveDocument.C1244.Height=15.00
App.ActiveDocument.C1244.Angle=360.00 
App.ActiveDocument.C1244.Placement=Base.Placement(Base.Vector(-41.375557,-124.430037,544.174351),Base.Rotation(-0.166233,-0.150740,0.000000,0.974497))
App.ActiveDocument.addObject("Part::Cylinder","C1245")
App.ActiveDocument.C1245.Radius=0.750000
App.ActiveDocument.C1245.Height=15.00
App.ActiveDocument.C1245.Angle=360.00 
App.ActiveDocument.C1245.Placement=Base.Placement(Base.Vector(-41.435015,-121.519534,542.966949),Base.Rotation(-0.207048,-0.152407,0.000000,0.966387))
App.ActiveDocument.addObject("Part::Cylinder","C1246")
App.ActiveDocument.C1246.Radius=0.750000
App.ActiveDocument.C1246.Height=15.00
App.ActiveDocument.C1246.Angle=360.00 
App.ActiveDocument.C1246.Placement=Base.Placement(Base.Vector(-41.421629,-118.805338,541.567572),Base.Rotation(-0.250707,-0.152115,0.000000,0.956037))
App.ActiveDocument.addObject("Part::Cylinder","C1247")
App.ActiveDocument.C1247.Radius=0.750000
App.ActiveDocument.C1247.Height=15.00
App.ActiveDocument.C1247.Angle=360.00 
App.ActiveDocument.C1247.Placement=Base.Placement(Base.Vector(-41.600282,-116.310273,539.899639),Base.Rotation(-0.293395,-0.153403,0.000000,0.943603))
App.ActiveDocument.addObject("Part::Cylinder","C1248")
App.ActiveDocument.C1248.Radius=0.750000
App.ActiveDocument.C1248.Height=15.00
App.ActiveDocument.C1248.Angle=360.00 
App.ActiveDocument.C1248.Placement=Base.Placement(Base.Vector(-41.673579,-113.951406,538.011175),Base.Rotation(-0.337380,-0.152592,0.000000,0.928919))
App.ActiveDocument.addObject("Part::Cylinder","C1249")
App.ActiveDocument.C1249.Radius=0.750000
App.ActiveDocument.C1249.Height=15.00
App.ActiveDocument.C1249.Angle=360.00 
App.ActiveDocument.C1249.Placement=Base.Placement(Base.Vector(-41.766313,-111.869860,535.979326),Base.Rotation(-0.381060,-0.153104,0.000000,0.911785))
App.ActiveDocument.addObject("Part::Cylinder","C1250")
App.ActiveDocument.C1250.Radius=0.750000
App.ActiveDocument.C1250.Height=15.00
App.ActiveDocument.C1250.Angle=360.00 
App.ActiveDocument.C1250.Placement=Base.Placement(Base.Vector(-41.797914,-109.905871,533.690413),Base.Rotation(-0.425002,-0.149085,0.000000,0.892831))
App.ActiveDocument.addObject("Part::Cylinder","C1251")
App.ActiveDocument.C1251.Radius=0.750000
App.ActiveDocument.C1251.Height=15.00
App.ActiveDocument.C1251.Angle=360.00 
App.ActiveDocument.C1251.Placement=Base.Placement(Base.Vector(-41.893344,-108.152278,531.179106),Base.Rotation(-0.464843,-0.148040,0.000000,0.872929))
App.ActiveDocument.addObject("Part::Cylinder","C1252")
App.ActiveDocument.C1252.Radius=0.750000
App.ActiveDocument.C1252.Height=15.00
App.ActiveDocument.C1252.Angle=360.00 
App.ActiveDocument.C1252.Placement=Base.Placement(Base.Vector(-41.962364,-106.618225,528.515541),Base.Rotation(-0.503187,-0.144424,0.000000,0.852024))
App.ActiveDocument.addObject("Part::Cylinder","C1253")
App.ActiveDocument.C1253.Radius=0.750000
App.ActiveDocument.C1253.Height=15.00
App.ActiveDocument.C1253.Angle=360.00 
App.ActiveDocument.C1253.Placement=Base.Placement(Base.Vector(-42.161649,-105.299360,525.623359),Base.Rotation(-0.536503,-0.144654,0.000000,0.831408))
App.ActiveDocument.addObject("Part::Cylinder","C1254")
App.ActiveDocument.C1254.Radius=0.750000
App.ActiveDocument.C1254.Height=15.00
App.ActiveDocument.C1254.Angle=360.00 
App.ActiveDocument.C1254.Placement=Base.Placement(Base.Vector(-42.308484,-104.187268,522.597134),Base.Rotation(-0.569900,-0.138398,0.000000,0.809976))
App.ActiveDocument.addObject("Part::Cylinder","C1255")
App.ActiveDocument.C1255.Radius=0.750000
App.ActiveDocument.C1255.Height=15.00
App.ActiveDocument.C1255.Angle=360.00 
App.ActiveDocument.C1255.Placement=Base.Placement(Base.Vector(-42.418315,-103.294678,519.506410),Base.Rotation(-0.599679,-0.135960,0.000000,0.788607))
App.ActiveDocument.addObject("Part::Cylinder","C1256")
App.ActiveDocument.C1256.Radius=0.750000
App.ActiveDocument.C1256.Height=15.00
App.ActiveDocument.C1256.Angle=360.00 
App.ActiveDocument.C1256.Placement=Base.Placement(Base.Vector(-42.568430,-102.622349,516.345831),Base.Rotation(-0.625212,-0.130848,0.000000,0.769408))
App.ActiveDocument.addObject("Part::Cylinder","C1257")
App.ActiveDocument.C1257.Radius=0.750000
App.ActiveDocument.C1257.Height=15.00
App.ActiveDocument.C1257.Angle=360.00 
App.ActiveDocument.C1257.Placement=Base.Placement(Base.Vector(-42.650719,-102.133855,513.083050),Base.Rotation(-0.651100,-0.127881,0.000000,0.748142))
App.ActiveDocument.addObject("Part::Cylinder","C1258")
App.ActiveDocument.C1258.Radius=0.750000
App.ActiveDocument.C1258.Height=15.00
App.ActiveDocument.C1258.Angle=360.00 
App.ActiveDocument.C1258.Placement=Base.Placement(Base.Vector(-42.853207,-101.865127,509.763964),Base.Rotation(-0.673528,-0.124131,0.000000,0.728664))
App.ActiveDocument.addObject("Part::Cylinder","C1259")
App.ActiveDocument.C1259.Radius=0.750000
App.ActiveDocument.C1259.Height=15.00
App.ActiveDocument.C1259.Angle=360.00 
App.ActiveDocument.C1259.Placement=Base.Placement(Base.Vector(-42.855566,-101.754215,506.487096),Base.Rotation(-0.694359,-0.115511,0.000000,0.710297))
App.ActiveDocument.addObject("Part::Cylinder","C1260")
App.ActiveDocument.C1260.Radius=0.750000
App.ActiveDocument.C1260.Height=15.00
App.ActiveDocument.C1260.Angle=360.00 
App.ActiveDocument.C1260.Placement=Base.Placement(Base.Vector(-43.140190,-101.884483,502.991129),Base.Rotation(-0.716347,-0.114767,0.000000,0.688241))
App.ActiveDocument.addObject("Part::Cylinder","C1261")
App.ActiveDocument.C1261.Radius=0.750000
App.ActiveDocument.C1261.Height=15.00
App.ActiveDocument.C1261.Angle=360.00 
App.ActiveDocument.C1261.Placement=Base.Placement(Base.Vector(-43.163440,-102.170611,499.501318),Base.Rotation(-0.737379,-0.103852,0.000000,0.667448))
App.ActiveDocument.addObject("Part::Cylinder","C1262")
App.ActiveDocument.C1262.Radius=0.750000
App.ActiveDocument.C1262.Height=15.00
App.ActiveDocument.C1262.Angle=360.00 
App.ActiveDocument.C1262.Placement=Base.Placement(Base.Vector(-43.324973,-102.660553,496.112432),Base.Rotation(-0.756805,-0.095668,0.000000,0.646602))
App.ActiveDocument.addObject("Part::Cylinder","C1263")
App.ActiveDocument.C1263.Radius=0.750000
App.ActiveDocument.C1263.Height=15.00
App.ActiveDocument.C1263.Angle=360.00 
App.ActiveDocument.C1263.Placement=Base.Placement(Base.Vector(-43.528516,-103.348746,492.701417),Base.Rotation(-0.776625,-0.081967,0.000000,0.624607))
App.ActiveDocument.addObject("Part::Cylinder","C1264")
App.ActiveDocument.C1264.Radius=0.750000
App.ActiveDocument.C1264.Height=15.00
App.ActiveDocument.C1264.Angle=360.00 
App.ActiveDocument.C1264.Placement=Base.Placement(Base.Vector(-43.688716,-104.195019,489.418538),Base.Rotation(-0.793085,-0.072855,0.000000,0.604738))
App.ActiveDocument.addObject("Part::Cylinder","C1265")
App.ActiveDocument.C1265.Radius=0.750000
App.ActiveDocument.C1265.Height=15.00
App.ActiveDocument.C1265.Angle=360.00 
App.ActiveDocument.C1265.Placement=Base.Placement(Base.Vector(-43.881073,-105.217942,486.194479),Base.Rotation(-0.811385,-0.061942,0.000000,0.581220))
App.ActiveDocument.addObject("Part::Cylinder","C1266")
App.ActiveDocument.C1266.Radius=0.750000
App.ActiveDocument.C1266.Height=15.00
App.ActiveDocument.C1266.Angle=360.00 
App.ActiveDocument.C1266.Placement=Base.Placement(Base.Vector(-44.003845,-106.401943,483.040691),Base.Rotation(-0.827595,-0.050074,0.000000,0.559088))
App.ActiveDocument.addObject("Part::Cylinder","C1267")
App.ActiveDocument.C1267.Radius=0.750000
App.ActiveDocument.C1267.Height=15.00
App.ActiveDocument.C1267.Angle=360.00 
App.ActiveDocument.C1267.Placement=Base.Placement(Base.Vector(-44.062337,-107.730526,480.007738),Base.Rotation(-0.841873,-0.044467,0.000000,0.537841))
App.ActiveDocument.addObject("Part::Cylinder","C1268")
App.ActiveDocument.C1268.Radius=0.750000
App.ActiveDocument.C1268.Height=15.00
App.ActiveDocument.C1268.Angle=360.00 
App.ActiveDocument.C1268.Placement=Base.Placement(Base.Vector(-44.230337,-109.238280,477.034293),Base.Rotation(-0.857234,-0.040220,0.000000,0.513354))
App.ActiveDocument.addObject("Part::Cylinder","C1269")
App.ActiveDocument.C1269.Radius=0.750000
App.ActiveDocument.C1269.Height=15.00
App.ActiveDocument.C1269.Angle=360.00 
App.ActiveDocument.C1269.Placement=Base.Placement(Base.Vector(-44.332855,-110.940874,474.102195),Base.Rotation(-0.873100,-0.033881,0.000000,0.486363))
App.ActiveDocument.addObject("Part::Cylinder","C1270")
App.ActiveDocument.C1270.Radius=0.750000
App.ActiveDocument.C1270.Height=15.00
App.ActiveDocument.C1270.Angle=360.00 
App.ActiveDocument.C1270.Placement=Base.Placement(Base.Vector(-44.142058,-112.798036,471.295039),Base.Rotation(-0.888399,-0.023810,0.000000,0.458454))
App.ActiveDocument.addObject("Part::Cylinder","C1271")
App.ActiveDocument.C1271.Radius=0.750000
App.ActiveDocument.C1271.Height=15.00
App.ActiveDocument.C1271.Angle=360.00 
App.ActiveDocument.C1271.Placement=Base.Placement(Base.Vector(-44.295215,-114.823744,468.649271),Base.Rotation(-0.903928,-0.017869,0.000000,0.427311))
App.ActiveDocument.addObject("Part::Cylinder","C1272")
App.ActiveDocument.C1272.Radius=0.750000
App.ActiveDocument.C1272.Height=15.00
App.ActiveDocument.C1272.Angle=360.00 
App.ActiveDocument.C1272.Placement=Base.Placement(Base.Vector(-44.560414,-137.428615,545.560256),Base.Rotation(-0.028018,-0.184337,0.000000,0.982464))
App.ActiveDocument.addObject("Part::Cylinder","C1273")
App.ActiveDocument.C1273.Radius=0.750000
App.ActiveDocument.C1273.Height=15.00
App.ActiveDocument.C1273.Angle=360.00 
App.ActiveDocument.C1273.Placement=Base.Placement(Base.Vector(-44.537521,-134.055464,545.264691),Base.Rotation(-0.056933,-0.184580,0.000000,0.981167))
App.ActiveDocument.addObject("Part::Cylinder","C1274")
App.ActiveDocument.C1274.Radius=0.750000
App.ActiveDocument.C1274.Height=15.00
App.ActiveDocument.C1274.Angle=360.00 
App.ActiveDocument.C1274.Placement=Base.Placement(Base.Vector(-44.542529,-130.752554,544.746064),Base.Rotation(-0.090713,-0.184924,0.000000,0.978557))
App.ActiveDocument.addObject("Part::Cylinder","C1275")
App.ActiveDocument.C1275.Radius=0.750000
App.ActiveDocument.C1275.Height=15.00
App.ActiveDocument.C1275.Angle=360.00 
App.ActiveDocument.C1275.Placement=Base.Placement(Base.Vector(-44.463563,-127.577580,544.039360),Base.Rotation(-0.124907,-0.184653,0.000000,0.974834))
App.ActiveDocument.addObject("Part::Cylinder","C1276")
App.ActiveDocument.C1276.Radius=0.750000
App.ActiveDocument.C1276.Height=15.00
App.ActiveDocument.C1276.Angle=360.00 
App.ActiveDocument.C1276.Placement=Base.Placement(Base.Vector(-44.444626,-124.517417,543.075173),Base.Rotation(-0.166202,-0.184106,0.000000,0.968753))
App.ActiveDocument.addObject("Part::Cylinder","C1277")
App.ActiveDocument.C1277.Radius=0.750000
App.ActiveDocument.C1277.Height=15.00
App.ActiveDocument.C1277.Angle=360.00 
App.ActiveDocument.C1277.Placement=Base.Placement(Base.Vector(-44.585138,-121.593577,541.797675),Base.Rotation(-0.207819,-0.186588,0.000000,0.960206))
App.ActiveDocument.addObject("Part::Cylinder","C1278")
App.ActiveDocument.C1278.Radius=0.750000
App.ActiveDocument.C1278.Height=15.00
App.ActiveDocument.C1278.Angle=360.00 
App.ActiveDocument.C1278.Placement=Base.Placement(Base.Vector(-44.570617,-118.874055,540.361048),Base.Rotation(-0.253215,-0.187342,0.000000,0.949097))
App.ActiveDocument.addObject("Part::Cylinder","C1279")
App.ActiveDocument.C1279.Radius=0.750000
App.ActiveDocument.C1279.Height=15.00
App.ActiveDocument.C1279.Angle=360.00 
App.ActiveDocument.C1279.Placement=Base.Placement(Base.Vector(-44.816925,-116.383637,538.598426),Base.Rotation(-0.293753,-0.192555,0.000000,0.936286))
App.ActiveDocument.addObject("Part::Cylinder","C1280")
App.ActiveDocument.C1280.Radius=0.750000
App.ActiveDocument.C1280.Height=15.00
App.ActiveDocument.C1280.Angle=360.00 
App.ActiveDocument.C1280.Placement=Base.Placement(Base.Vector(-44.818886,-114.062353,536.704125),Base.Rotation(-0.340724,-0.188574,0.000000,0.921057))
App.ActiveDocument.addObject("Part::Cylinder","C1281")
App.ActiveDocument.C1281.Radius=0.750000
App.ActiveDocument.C1281.Height=15.00
App.ActiveDocument.C1281.Angle=360.00 
App.ActiveDocument.C1281.Placement=Base.Placement(Base.Vector(-44.940636,-111.995122,534.588052),Base.Rotation(-0.383747,-0.191632,0.000000,0.903336))
App.ActiveDocument.addObject("Part::Cylinder","C1282")
App.ActiveDocument.C1282.Radius=0.750000
App.ActiveDocument.C1282.Height=15.00
App.ActiveDocument.C1282.Angle=360.00 
App.ActiveDocument.C1282.Placement=Base.Placement(Base.Vector(-44.933294,-110.107593,532.322478),Base.Rotation(-0.424419,-0.189046,0.000000,0.885511))
App.ActiveDocument.addObject("Part::Cylinder","C1283")
App.ActiveDocument.C1283.Radius=0.750000
App.ActiveDocument.C1283.Height=15.00
App.ActiveDocument.C1283.Angle=360.00 
App.ActiveDocument.C1283.Placement=Base.Placement(Base.Vector(-44.984398,-108.424321,529.837254),Base.Rotation(-0.463942,-0.188637,0.000000,0.865548))
App.ActiveDocument.addObject("Part::Cylinder","C1284")
App.ActiveDocument.C1284.Radius=0.750000
App.ActiveDocument.C1284.Height=15.00
App.ActiveDocument.C1284.Angle=360.00 
App.ActiveDocument.C1284.Placement=Base.Placement(Base.Vector(-45.173011,-106.993072,527.174708),Base.Rotation(-0.498052,-0.188726,0.000000,0.846361))
App.ActiveDocument.addObject("Part::Cylinder","C1285")
App.ActiveDocument.C1285.Radius=0.750000
App.ActiveDocument.C1285.Height=15.00
App.ActiveDocument.C1285.Angle=360.00 
App.ActiveDocument.C1285.Placement=Base.Placement(Base.Vector(-45.368656,-105.772456,524.375472),Base.Rotation(-0.531404,-0.189013,0.000000,0.825762))
App.ActiveDocument.addObject("Part::Cylinder","C1286")
App.ActiveDocument.C1286.Radius=0.750000
App.ActiveDocument.C1286.Height=15.00
App.ActiveDocument.C1286.Angle=360.00 
App.ActiveDocument.C1286.Placement=Base.Placement(Base.Vector(-45.399950,-104.684768,521.414751),Base.Rotation(-0.563220,-0.185297,0.000000,0.805263))
App.ActiveDocument.addObject("Part::Cylinder","C1287")
App.ActiveDocument.C1287.Radius=0.750000
App.ActiveDocument.C1287.Height=15.00
App.ActiveDocument.C1287.Angle=360.00 
App.ActiveDocument.C1287.Placement=Base.Placement(Base.Vector(-45.574214,-103.829032,518.262888),Base.Rotation(-0.591132,-0.185257,0.000000,0.785011))
App.ActiveDocument.addObject("Part::Cylinder","C1288")
App.ActiveDocument.C1288.Radius=0.750000
App.ActiveDocument.C1288.Height=15.00
App.ActiveDocument.C1288.Angle=360.00 
App.ActiveDocument.C1288.Placement=Base.Placement(Base.Vector(-45.739764,-103.189114,515.056003),Base.Rotation(-0.616636,-0.183543,0.000000,0.765554))
App.ActiveDocument.addObject("Part::Cylinder","C1289")
App.ActiveDocument.C1289.Radius=0.750000
App.ActiveDocument.C1289.Height=15.00
App.ActiveDocument.C1289.Angle=360.00 
App.ActiveDocument.C1289.Placement=Base.Placement(Base.Vector(-45.845529,-102.737659,511.801302),Base.Rotation(-0.641253,-0.180791,0.000000,0.745728))
App.ActiveDocument.addObject("Part::Cylinder","C1290")
App.ActiveDocument.C1290.Radius=0.750000
App.ActiveDocument.C1290.Height=15.00
App.ActiveDocument.C1290.Angle=360.00 
App.ActiveDocument.C1290.Placement=Base.Placement(Base.Vector(-46.041297,-102.508796,508.544428),Base.Rotation(-0.663493,-0.179313,0.000000,0.726377))
App.ActiveDocument.addObject("Part::Cylinder","C1291")
App.ActiveDocument.C1291.Radius=0.750000
App.ActiveDocument.C1291.Height=15.00
App.ActiveDocument.C1291.Angle=360.00 
App.ActiveDocument.C1291.Placement=Base.Placement(Base.Vector(-45.936828,-102.388296,505.248191),Base.Rotation(-0.685925,-0.171160,0.000000,0.707256))
App.ActiveDocument.addObject("Part::Cylinder","C1292")
App.ActiveDocument.C1292.Radius=0.750000
App.ActiveDocument.C1292.Height=15.00
App.ActiveDocument.C1292.Angle=360.00 
App.ActiveDocument.C1292.Placement=Base.Placement(Base.Vector(-46.338683,-102.583261,501.854305),Base.Rotation(-0.705505,-0.170031,0.000000,0.688006))
App.ActiveDocument.addObject("Part::Cylinder","C1293")
App.ActiveDocument.C1293.Radius=0.750000
App.ActiveDocument.C1293.Height=15.00
App.ActiveDocument.C1293.Angle=360.00 
App.ActiveDocument.C1293.Placement=Base.Placement(Base.Vector(-46.325856,-102.851515,498.558423),Base.Rotation(-0.725750,-0.162157,0.000000,0.668575))
App.ActiveDocument.addObject("Part::Cylinder","C1294")
App.ActiveDocument.C1294.Radius=0.750000
App.ActiveDocument.C1294.Height=15.00
App.ActiveDocument.C1294.Angle=360.00 
App.ActiveDocument.C1294.Placement=Base.Placement(Base.Vector(-46.449889,-103.331233,495.242981),Base.Rotation(-0.744111,-0.158259,0.000000,0.649040))
App.ActiveDocument.addObject("Part::Cylinder","C1295")
App.ActiveDocument.C1295.Radius=0.750000
App.ActiveDocument.C1295.Height=15.00
App.ActiveDocument.C1295.Angle=360.00 
App.ActiveDocument.C1295.Placement=Base.Placement(Base.Vector(-46.602323,-104.010112,491.860374),Base.Rotation(-0.762511,-0.154201,0.000000,0.628331))
App.ActiveDocument.addObject("Part::Cylinder","C1296")
App.ActiveDocument.C1296.Radius=0.750000
App.ActiveDocument.C1296.Height=15.00
App.ActiveDocument.C1296.Angle=360.00 
App.ActiveDocument.C1296.Placement=Base.Placement(Base.Vector(-46.803140,-104.868628,488.555630),Base.Rotation(-0.781045,-0.146204,0.000000,0.607119))
App.ActiveDocument.addObject("Part::Cylinder","C1297")
App.ActiveDocument.C1297.Radius=0.750000
App.ActiveDocument.C1297.Height=15.00
App.ActiveDocument.C1297.Angle=360.00 
App.ActiveDocument.C1297.Placement=Base.Placement(Base.Vector(-46.995197,-105.902912,485.304489),Base.Rotation(-0.800836,-0.132941,0.000000,0.583943))
App.ActiveDocument.addObject("Part::Cylinder","C1298")
App.ActiveDocument.C1298.Radius=0.750000
App.ActiveDocument.C1298.Height=15.00
App.ActiveDocument.C1298.Angle=360.00 
App.ActiveDocument.C1298.Placement=Base.Placement(Base.Vector(-47.199535,-107.085531,482.192095),Base.Rotation(-0.817753,-0.126291,0.000000,0.561543))
App.ActiveDocument.addObject("Part::Cylinder","C1299")
App.ActiveDocument.C1299.Radius=0.750000
App.ActiveDocument.C1299.Height=15.00
App.ActiveDocument.C1299.Angle=360.00 
App.ActiveDocument.C1299.Placement=Base.Placement(Base.Vector(-47.350071,-108.434635,479.145119),Base.Rotation(-0.834069,-0.121658,0.000000,0.538078))
App.ActiveDocument.addObject("Part::Cylinder","C1300")
App.ActiveDocument.C1300.Radius=0.750000
App.ActiveDocument.C1300.Height=15.00
App.ActiveDocument.C1300.Angle=360.00 
App.ActiveDocument.C1300.Placement=Base.Placement(Base.Vector(-47.522387,-109.919129,476.270585),Base.Rotation(-0.850903,-0.106061,0.000000,0.514505))
App.ActiveDocument.addObject("Part::Cylinder","C1301")
App.ActiveDocument.C1301.Radius=0.750000
App.ActiveDocument.C1301.Height=15.00
App.ActiveDocument.C1301.Angle=360.00 
App.ActiveDocument.C1301.Placement=Base.Placement(Base.Vector(-47.757561,-111.577042,473.486806),Base.Rotation(-0.869058,-0.097213,0.000000,0.485066))
App.ActiveDocument.addObject("Part::Cylinder","C1302")
App.ActiveDocument.C1302.Radius=0.750000
App.ActiveDocument.C1302.Height=15.00
App.ActiveDocument.C1302.Angle=360.00 
App.ActiveDocument.C1302.Placement=Base.Placement(Base.Vector(-47.535281,-113.394498,470.748680),Base.Rotation(-0.886092,-0.084128,0.000000,0.455810))
App.ActiveDocument.addObject("Part::Cylinder","C1303")
App.ActiveDocument.C1303.Radius=0.750000
App.ActiveDocument.C1303.Height=15.00
App.ActiveDocument.C1303.Angle=360.00 
App.ActiveDocument.C1303.Placement=Base.Placement(Base.Vector(-47.678535,-115.417212,468.155519),Base.Rotation(-0.901409,-0.081244,0.000000,0.425278))
App.ActiveDocument.addObject("Part::Cylinder","C1304")
App.ActiveDocument.C1304.Radius=0.750000
App.ActiveDocument.C1304.Height=15.00
App.ActiveDocument.C1304.Angle=360.00 
App.ActiveDocument.C1304.Placement=Base.Placement(Base.Vector(-47.627801,-137.427807,544.247813),Base.Rotation(-0.028014,-0.216071,0.000000,0.975976))
App.ActiveDocument.addObject("Part::Cylinder","C1305")
App.ActiveDocument.C1305.Radius=0.750000
App.ActiveDocument.C1305.Height=15.00
App.ActiveDocument.C1305.Angle=360.00 
App.ActiveDocument.C1305.Placement=Base.Placement(Base.Vector(-47.636415,-134.039681,543.931390),Base.Rotation(-0.058160,-0.216344,0.000000,0.974583))
App.ActiveDocument.addObject("Part::Cylinder","C1306")
App.ActiveDocument.C1306.Radius=0.750000
App.ActiveDocument.C1306.Height=15.00
App.ActiveDocument.C1306.Angle=360.00 
App.ActiveDocument.C1306.Placement=Base.Placement(Base.Vector(-47.610833,-130.747612,543.410141),Base.Rotation(-0.091457,-0.217136,0.000000,0.971848))
App.ActiveDocument.addObject("Part::Cylinder","C1307")
App.ActiveDocument.C1307.Radius=0.750000
App.ActiveDocument.C1307.Height=15.00
App.ActiveDocument.C1307.Angle=360.00 
App.ActiveDocument.C1307.Placement=Base.Placement(Base.Vector(-47.591769,-127.584322,542.662434),Base.Rotation(-0.125970,-0.217527,0.000000,0.967891))
App.ActiveDocument.addObject("Part::Cylinder","C1308")
App.ActiveDocument.C1308.Radius=0.750000
App.ActiveDocument.C1308.Height=15.00
App.ActiveDocument.C1308.Angle=360.00 
App.ActiveDocument.C1308.Placement=Base.Placement(Base.Vector(-47.511422,-124.614277,541.728660),Base.Rotation(-0.164276,-0.217732,0.000000,0.962084))
App.ActiveDocument.addObject("Part::Cylinder","C1309")
App.ActiveDocument.C1309.Radius=0.750000
App.ActiveDocument.C1309.Height=15.00
App.ActiveDocument.C1309.Angle=360.00 
App.ActiveDocument.C1309.Placement=Base.Placement(Base.Vector(-47.666944,-121.785073,540.439002),Base.Rotation(-0.207300,-0.219988,0.000000,0.953222))
App.ActiveDocument.addObject("Part::Cylinder","C1310")
App.ActiveDocument.C1310.Radius=0.750000
App.ActiveDocument.C1310.Height=15.00
App.ActiveDocument.C1310.Angle=360.00 
App.ActiveDocument.C1310.Placement=Base.Placement(Base.Vector(-47.662518,-119.063981,538.956844),Base.Rotation(-0.252715,-0.220041,0.000000,0.942187))
App.ActiveDocument.addObject("Part::Cylinder","C1311")
App.ActiveDocument.C1311.Radius=0.750000
App.ActiveDocument.C1311.Height=15.00
App.ActiveDocument.C1311.Angle=360.00 
App.ActiveDocument.C1311.Placement=Base.Placement(Base.Vector(-47.925922,-116.650709,537.161239),Base.Rotation(-0.295959,-0.225722,0.000000,0.928147))
App.ActiveDocument.addObject("Part::Cylinder","C1312")
App.ActiveDocument.C1312.Radius=0.750000
App.ActiveDocument.C1312.Height=15.00
App.ActiveDocument.C1312.Angle=360.00 
App.ActiveDocument.C1312.Placement=Base.Placement(Base.Vector(-47.955020,-114.365655,535.222092),Base.Rotation(-0.339360,-0.225876,0.000000,0.913135))
App.ActiveDocument.addObject("Part::Cylinder","C1313")
App.ActiveDocument.C1313.Radius=0.750000
App.ActiveDocument.C1313.Height=15.00
App.ActiveDocument.C1313.Angle=360.00 
App.ActiveDocument.C1313.Placement=Base.Placement(Base.Vector(-48.053864,-112.335004,533.069452),Base.Rotation(-0.382088,-0.227999,0.000000,0.895559))
App.ActiveDocument.addObject("Part::Cylinder","C1314")
App.ActiveDocument.C1314.Radius=0.750000
App.ActiveDocument.C1314.Height=15.00
App.ActiveDocument.C1314.Angle=360.00 
App.ActiveDocument.C1314.Placement=Base.Placement(Base.Vector(-48.006656,-110.460043,530.756607),Base.Rotation(-0.424280,-0.227174,0.000000,0.876572))
App.ActiveDocument.addObject("Part::Cylinder","C1315")
App.ActiveDocument.C1315.Radius=0.750000
App.ActiveDocument.C1315.Height=15.00
App.ActiveDocument.C1315.Angle=360.00 
App.ActiveDocument.C1315.Placement=Base.Placement(Base.Vector(-48.089404,-108.865489,528.268913),Base.Rotation(-0.461468,-0.228237,0.000000,0.857296))
App.ActiveDocument.addObject("Part::Cylinder","C1316")
App.ActiveDocument.C1316.Radius=0.750000
App.ActiveDocument.C1316.Height=15.00
App.ActiveDocument.C1316.Angle=360.00 
App.ActiveDocument.C1316.Placement=Base.Placement(Base.Vector(-48.351591,-107.543140,525.588544),Base.Rotation(-0.495285,-0.231277,0.000000,0.837379))
App.ActiveDocument.addObject("Part::Cylinder","C1317")
App.ActiveDocument.C1317.Radius=0.750000
App.ActiveDocument.C1317.Height=15.00
App.ActiveDocument.C1317.Angle=360.00 
App.ActiveDocument.C1317.Placement=Base.Placement(Base.Vector(-48.436066,-106.314496,522.702732),Base.Rotation(-0.526784,-0.228677,0.000000,0.818661))
App.ActiveDocument.addObject("Part::Cylinder","C1318")
App.ActiveDocument.C1318.Radius=0.750000
App.ActiveDocument.C1318.Height=15.00
App.ActiveDocument.C1318.Angle=360.00 
App.ActiveDocument.C1318.Placement=Base.Placement(Base.Vector(-48.541104,-105.354160,519.842083),Base.Rotation(-0.554808,-0.232788,0.000000,0.798748))
App.ActiveDocument.addObject("Part::Cylinder","C1319")
App.ActiveDocument.C1319.Radius=0.750000
App.ActiveDocument.C1319.Height=15.00
App.ActiveDocument.C1319.Angle=360.00 
App.ActiveDocument.C1319.Placement=Base.Placement(Base.Vector(-48.672038,-104.559616,516.744985),Base.Rotation(-0.581799,-0.231016,0.000000,0.779834))
App.ActiveDocument.addObject("Part::Cylinder","C1320")
App.ActiveDocument.C1320.Radius=0.750000
App.ActiveDocument.C1320.Height=15.00
App.ActiveDocument.C1320.Angle=360.00 
App.ActiveDocument.C1320.Placement=Base.Placement(Base.Vector(-48.837468,-103.974932,513.524216),Base.Rotation(-0.610254,-0.231316,0.000000,0.757682))
App.ActiveDocument.addObject("Part::Cylinder","C1321")
App.ActiveDocument.C1321.Radius=0.750000
App.ActiveDocument.C1321.Height=15.00
App.ActiveDocument.C1321.Angle=360.00 
App.ActiveDocument.C1321.Placement=Base.Placement(Base.Vector(-49.013833,-103.609028,510.361298),Base.Rotation(-0.628187,-0.234332,0.000000,0.741937))
App.ActiveDocument.addObject("Part::Cylinder","C1322")
App.ActiveDocument.C1322.Radius=0.750000
App.ActiveDocument.C1322.Height=15.00
App.ActiveDocument.C1322.Angle=360.00 
App.ActiveDocument.C1322.Placement=Base.Placement(Base.Vector(-49.042545,-103.371507,507.121139),Base.Rotation(-0.649970,-0.233374,0.000000,0.723240))
App.ActiveDocument.addObject("Part::Cylinder","C1323")
App.ActiveDocument.C1323.Radius=0.750000
App.ActiveDocument.C1323.Height=15.00
App.ActiveDocument.C1323.Angle=360.00 
App.ActiveDocument.C1323.Placement=Base.Placement(Base.Vector(-49.096463,-103.322977,503.928939),Base.Rotation(-0.670785,-0.230726,0.000000,0.704849))
App.ActiveDocument.addObject("Part::Cylinder","C1324")
App.ActiveDocument.C1324.Radius=0.750000
App.ActiveDocument.C1324.Height=15.00
App.ActiveDocument.C1324.Angle=360.00 
App.ActiveDocument.C1324.Placement=Base.Placement(Base.Vector(-49.375998,-103.532009,500.592619),Base.Rotation(-0.688541,-0.234535,0.000000,0.686225))
App.ActiveDocument.addObject("Part::Cylinder","C1325")
App.ActiveDocument.C1325.Radius=0.750000
App.ActiveDocument.C1325.Height=15.00
App.ActiveDocument.C1325.Angle=360.00 
App.ActiveDocument.C1325.Placement=Base.Placement(Base.Vector(-49.346409,-103.807013,497.327298),Base.Rotation(-0.708900,-0.227313,0.000000,0.667674))
App.ActiveDocument.addObject("Part::Cylinder","C1326")
App.ActiveDocument.C1326.Radius=0.750000
App.ActiveDocument.C1326.Height=15.00
App.ActiveDocument.C1326.Angle=360.00 
App.ActiveDocument.C1326.Placement=Base.Placement(Base.Vector(-49.487792,-104.306014,494.094352),Base.Rotation(-0.727199,-0.222690,0.000000,0.649300))
App.ActiveDocument.addObject("Part::Cylinder","C1327")
App.ActiveDocument.C1327.Radius=0.750000
App.ActiveDocument.C1327.Height=15.00
App.ActiveDocument.C1327.Angle=360.00 
App.ActiveDocument.C1327.Placement=Base.Placement(Base.Vector(-49.644172,-104.999736,490.765088),Base.Rotation(-0.744031,-0.223768,0.000000,0.629560))
App.ActiveDocument.addObject("Part::Cylinder","C1328")
App.ActiveDocument.C1328.Radius=0.750000
App.ActiveDocument.C1328.Height=15.00
App.ActiveDocument.C1328.Angle=360.00 
App.ActiveDocument.C1328.Placement=Base.Placement(Base.Vector(-49.826272,-105.853002,487.561006),Base.Rotation(-0.761874,-0.220035,0.000000,0.609206))
App.ActiveDocument.addObject("Part::Cylinder","C1329")
App.ActiveDocument.C1329.Radius=0.750000
App.ActiveDocument.C1329.Height=15.00
App.ActiveDocument.C1329.Angle=360.00 
App.ActiveDocument.C1329.Placement=Base.Placement(Base.Vector(-49.963171,-106.864055,484.390748),Base.Rotation(-0.778495,-0.218125,0.000000,0.588529))
App.ActiveDocument.addObject("Part::Cylinder","C1330")
App.ActiveDocument.C1330.Radius=0.750000
App.ActiveDocument.C1330.Height=15.00
App.ActiveDocument.C1330.Angle=360.00 
App.ActiveDocument.C1330.Placement=Base.Placement(Base.Vector(-50.195816,-108.027050,481.390179),Base.Rotation(-0.796215,-0.211631,0.000000,0.566793))
App.ActiveDocument.addObject("Part::Cylinder","C1331")
App.ActiveDocument.C1331.Radius=0.750000
App.ActiveDocument.C1331.Height=15.00
App.ActiveDocument.C1331.Angle=360.00 
App.ActiveDocument.C1331.Placement=Base.Placement(Base.Vector(-50.394919,-109.397824,478.334528),Base.Rotation(-0.816243,-0.201453,0.000000,0.541447))
App.ActiveDocument.addObject("Part::Cylinder","C1332")
App.ActiveDocument.C1332.Radius=0.750000
App.ActiveDocument.C1332.Height=15.00
App.ActiveDocument.C1332.Angle=360.00 
App.ActiveDocument.C1332.Placement=Base.Placement(Base.Vector(-50.641027,-110.913550,475.446597),Base.Rotation(-0.834807,-0.194401,0.000000,0.515078))
App.ActiveDocument.addObject("Part::Cylinder","C1333")
App.ActiveDocument.C1333.Radius=0.750000
App.ActiveDocument.C1333.Height=15.00
App.ActiveDocument.C1333.Angle=360.00 
App.ActiveDocument.C1333.Placement=Base.Placement(Base.Vector(-50.810112,-112.590873,472.651206),Base.Rotation(-0.853061,-0.184945,0.000000,0.487937))
App.ActiveDocument.addObject("Part::Cylinder","C1334")
App.ActiveDocument.C1334.Radius=0.750000
App.ActiveDocument.C1334.Height=15.00
App.ActiveDocument.C1334.Angle=360.00 
App.ActiveDocument.C1334.Placement=Base.Placement(Base.Vector(-50.796807,-114.357357,470.044024),Base.Rotation(-0.874127,-0.166808,0.000000,0.456155))
App.ActiveDocument.addObject("Part::Cylinder","C1335")
App.ActiveDocument.C1335.Radius=0.750000
App.ActiveDocument.C1335.Height=15.00
App.ActiveDocument.C1335.Angle=360.00 
App.ActiveDocument.C1335.Placement=Base.Placement(Base.Vector(-51.013399,-116.148218,467.800906),Base.Rotation(-0.890414,-0.158232,0.000000,0.426761))
App.ActiveDocument.addObject("Part::Cylinder","C1336")
App.ActiveDocument.C1336.Radius=0.750000
App.ActiveDocument.C1336.Height=15.00
App.ActiveDocument.C1336.Angle=360.00 
App.ActiveDocument.C1336.Placement=Base.Placement(Base.Vector(-50.591125,-137.453372,542.757018),Base.Rotation(-0.028457,-0.245812,0.000000,0.968900))
App.ActiveDocument.addObject("Part::Cylinder","C1337")
App.ActiveDocument.C1337.Radius=0.750000
App.ActiveDocument.C1337.Height=15.00
App.ActiveDocument.C1337.Angle=360.00 
App.ActiveDocument.C1337.Placement=Base.Placement(Base.Vector(-50.636322,-134.088481,542.413234),Base.Rotation(-0.058806,-0.246642,0.000000,0.967321))
App.ActiveDocument.addObject("Part::Cylinder","C1338")
App.ActiveDocument.C1338.Radius=0.750000
App.ActiveDocument.C1338.Height=15.00
App.ActiveDocument.C1338.Angle=360.00 
App.ActiveDocument.C1338.Placement=Base.Placement(Base.Vector(-50.604223,-130.812274,541.886497),Base.Rotation(-0.092302,-0.247251,0.000000,0.964545))
App.ActiveDocument.addObject("Part::Cylinder","C1339")
App.ActiveDocument.C1339.Radius=0.750000
App.ActiveDocument.C1339.Height=15.00
App.ActiveDocument.C1339.Angle=360.00 
App.ActiveDocument.C1339.Placement=Base.Placement(Base.Vector(-50.638378,-127.631445,541.077427),Base.Rotation(-0.129527,-0.249559,0.000000,0.959658))
App.ActiveDocument.addObject("Part::Cylinder","C1340")
App.ActiveDocument.C1340.Radius=0.750000
App.ActiveDocument.C1340.Height=15.00
App.ActiveDocument.C1340.Angle=360.00 
App.ActiveDocument.C1340.Placement=Base.Placement(Base.Vector(-50.528022,-124.644446,540.121786),Base.Rotation(-0.168019,-0.248179,0.000000,0.954032))
App.ActiveDocument.addObject("Part::Cylinder","C1341")
App.ActiveDocument.C1341.Radius=0.750000
App.ActiveDocument.C1341.Height=15.00
App.ActiveDocument.C1341.Angle=360.00 
App.ActiveDocument.C1341.Placement=Base.Placement(Base.Vector(-50.667907,-121.867743,538.796835),Base.Rotation(-0.207313,-0.251338,0.000000,0.945437))
App.ActiveDocument.addObject("Part::Cylinder","C1342")
App.ActiveDocument.C1342.Radius=0.750000
App.ActiveDocument.C1342.Height=15.00
App.ActiveDocument.C1342.Angle=360.00 
App.ActiveDocument.C1342.Placement=Base.Placement(Base.Vector(-50.770143,-119.324288,537.286669),Base.Rotation(-0.253118,-0.256201,0.000000,0.932894))
App.ActiveDocument.addObject("Part::Cylinder","C1343")
App.ActiveDocument.C1343.Radius=0.750000
App.ActiveDocument.C1343.Height=15.00
App.ActiveDocument.C1343.Angle=360.00 
App.ActiveDocument.C1343.Placement=Base.Placement(Base.Vector(-50.916237,-116.934550,535.489008),Base.Rotation(-0.297014,-0.259156,0.000000,0.919032))
App.ActiveDocument.addObject("Part::Cylinder","C1344")
App.ActiveDocument.C1344.Radius=0.750000
App.ActiveDocument.C1344.Height=15.00
App.ActiveDocument.C1344.Angle=360.00 
App.ActiveDocument.C1344.Placement=Base.Placement(Base.Vector(-50.988068,-114.761271,533.531164),Base.Rotation(-0.342159,-0.260526,0.000000,0.902803))
App.ActiveDocument.addObject("Part::Cylinder","C1345")
App.ActiveDocument.C1345.Radius=0.750000
App.ActiveDocument.C1345.Height=15.00
App.ActiveDocument.C1345.Angle=360.00 
App.ActiveDocument.C1345.Placement=Base.Placement(Base.Vector(-51.117871,-112.765467,531.277359),Base.Rotation(-0.382197,-0.263203,0.000000,0.885805))
App.ActiveDocument.addObject("Part::Cylinder","C1346")
App.ActiveDocument.C1346.Radius=0.750000
App.ActiveDocument.C1346.Height=15.00
App.ActiveDocument.C1346.Angle=360.00 
App.ActiveDocument.C1346.Placement=Base.Placement(Base.Vector(-51.040936,-110.941040,528.939119),Base.Rotation(-0.422489,-0.264782,0.000000,0.866830))
App.ActiveDocument.addObject("Part::Cylinder","C1347")
App.ActiveDocument.C1347.Radius=0.750000
App.ActiveDocument.C1347.Height=15.00
App.ActiveDocument.C1347.Angle=360.00 
App.ActiveDocument.C1347.Placement=Base.Placement(Base.Vector(-51.283603,-109.510280,526.403592),Base.Rotation(-0.456367,-0.268871,0.000000,0.848197))
App.ActiveDocument.addObject("Part::Cylinder","C1348")
App.ActiveDocument.C1348.Radius=0.750000
App.ActiveDocument.C1348.Height=15.00
App.ActiveDocument.C1348.Angle=360.00 
App.ActiveDocument.C1348.Placement=Base.Placement(Base.Vector(-51.353464,-108.203660,523.757189),Base.Rotation(-0.490457,-0.269783,0.000000,0.828655))
App.ActiveDocument.addObject("Part::Cylinder","C1349")
App.ActiveDocument.C1349.Radius=0.750000
App.ActiveDocument.C1349.Height=15.00
App.ActiveDocument.C1349.Angle=360.00 
App.ActiveDocument.C1349.Placement=Base.Placement(Base.Vector(-51.507380,-107.105760,520.890318),Base.Rotation(-0.520631,-0.273522,0.000000,0.808782))
App.ActiveDocument.addObject("Part::Cylinder","C1350")
App.ActiveDocument.C1350.Radius=0.750000
App.ActiveDocument.C1350.Height=15.00
App.ActiveDocument.C1350.Angle=360.00 
App.ActiveDocument.C1350.Placement=Base.Placement(Base.Vector(-51.568576,-106.193414,517.995843),Base.Rotation(-0.547910,-0.274755,0.000000,0.790129))
App.ActiveDocument.addObject("Part::Cylinder","C1351")
App.ActiveDocument.C1351.Radius=0.750000
App.ActiveDocument.C1351.Height=15.00
App.ActiveDocument.C1351.Angle=360.00 
App.ActiveDocument.C1351.Placement=Base.Placement(Base.Vector(-51.712720,-105.501014,514.948456),Base.Rotation(-0.572019,-0.279938,0.000000,0.770992))
App.ActiveDocument.addObject("Part::Cylinder","C1352")
App.ActiveDocument.C1352.Radius=0.750000
App.ActiveDocument.C1352.Height=15.00
App.ActiveDocument.C1352.Angle=360.00 
App.ActiveDocument.C1352.Placement=Base.Placement(Base.Vector(-51.851455,-105.010444,511.895028),Base.Rotation(-0.592641,-0.283855,0.000000,0.753792))
App.ActiveDocument.addObject("Part::Cylinder","C1353")
App.ActiveDocument.C1353.Radius=0.750000
App.ActiveDocument.C1353.Height=15.00
App.ActiveDocument.C1353.Angle=360.00 
App.ActiveDocument.C1353.Placement=Base.Placement(Base.Vector(-52.002285,-104.700721,508.717097),Base.Rotation(-0.614488,-0.286027,0.000000,0.735251))
App.ActiveDocument.addObject("Part::Cylinder","C1354")
App.ActiveDocument.C1354.Radius=0.750000
App.ActiveDocument.C1354.Height=15.00
App.ActiveDocument.C1354.Angle=360.00 
App.ActiveDocument.C1354.Placement=Base.Placement(Base.Vector(-51.977070,-104.492203,505.506131),Base.Rotation(-0.633627,-0.288313,0.000000,0.717909))
App.ActiveDocument.addObject("Part::Cylinder","C1355")
App.ActiveDocument.C1355.Radius=0.750000
App.ActiveDocument.C1355.Height=15.00
App.ActiveDocument.C1355.Angle=360.00 
App.ActiveDocument.C1355.Placement=Base.Placement(Base.Vector(-52.111448,-104.531971,502.456487),Base.Rotation(-0.650103,-0.293060,0.000000,0.701058))
App.ActiveDocument.addObject("Part::Cylinder","C1356")
App.ActiveDocument.C1356.Radius=0.750000
App.ActiveDocument.C1356.Height=15.00
App.ActiveDocument.C1356.Angle=360.00 
App.ActiveDocument.C1356.Placement=Base.Placement(Base.Vector(-52.223274,-104.736122,499.114227),Base.Rotation(-0.666830,-0.297388,0.000000,0.683300))
App.ActiveDocument.addObject("Part::Cylinder","C1357")
App.ActiveDocument.C1357.Radius=0.750000
App.ActiveDocument.C1357.Height=15.00
App.ActiveDocument.C1357.Angle=360.00 
App.ActiveDocument.C1357.Placement=Base.Placement(Base.Vector(-52.237431,-105.056989,495.921043),Base.Rotation(-0.686591,-0.293984,0.000000,0.664956))
App.ActiveDocument.addObject("Part::Cylinder","C1358")
App.ActiveDocument.C1358.Radius=0.750000
App.ActiveDocument.C1358.Height=15.00
App.ActiveDocument.C1358.Angle=360.00 
App.ActiveDocument.C1358.Placement=Base.Placement(Base.Vector(-52.329766,-105.592060,492.652015),Base.Rotation(-0.701829,-0.296282,0.000000,0.647807))
App.ActiveDocument.addObject("Part::Cylinder","C1359")
App.ActiveDocument.C1359.Radius=0.750000
App.ActiveDocument.C1359.Height=15.00
App.ActiveDocument.C1359.Angle=360.00 
App.ActiveDocument.C1359.Placement=Base.Placement(Base.Vector(-52.518325,-106.326508,489.446504),Base.Rotation(-0.716736,-0.301967,0.000000,0.628575))
App.ActiveDocument.addObject("Part::Cylinder","C1360")
App.ActiveDocument.C1360.Radius=0.750000
App.ActiveDocument.C1360.Height=15.00
App.ActiveDocument.C1360.Angle=360.00 
App.ActiveDocument.C1360.Placement=Base.Placement(Base.Vector(-52.543932,-107.156239,486.277254),Base.Rotation(-0.730609,-0.306203,0.000000,0.610287))
App.ActiveDocument.addObject("Part::Cylinder","C1361")
App.ActiveDocument.C1361.Radius=0.750000
App.ActiveDocument.C1361.Height=15.00
App.ActiveDocument.C1361.Angle=360.00 
App.ActiveDocument.C1361.Placement=Base.Placement(Base.Vector(-52.824690,-108.240622,483.201072),Base.Rotation(-0.744640,-0.311068,0.000000,0.590549))
App.ActiveDocument.addObject("Part::Cylinder","C1362")
App.ActiveDocument.C1362.Radius=0.750000
App.ActiveDocument.C1362.Height=15.00
App.ActiveDocument.C1362.Angle=360.00 
App.ActiveDocument.C1362.Placement=Base.Placement(Base.Vector(-52.825611,-109.385712,480.145298),Base.Rotation(-0.760626,-0.312418,0.000000,0.569072))
App.ActiveDocument.addObject("Part::Cylinder","C1363")
App.ActiveDocument.C1363.Radius=0.750000
App.ActiveDocument.C1363.Height=15.00
App.ActiveDocument.C1363.Angle=360.00 
App.ActiveDocument.C1363.Placement=Base.Placement(Base.Vector(-53.025011,-110.723670,477.284162),Base.Rotation(-0.774751,-0.314723,0.000000,0.548370))
App.ActiveDocument.addObject("Part::Cylinder","C1364")
App.ActiveDocument.C1364.Radius=0.750000
App.ActiveDocument.C1364.Height=15.00
App.ActiveDocument.C1364.Angle=360.00 
App.ActiveDocument.C1364.Placement=Base.Placement(Base.Vector(-53.241421,-112.276401,474.406931),Base.Rotation(-0.791701,-0.316425,0.000000,0.522575))
App.ActiveDocument.addObject("Part::Cylinder","C1365")
App.ActiveDocument.C1365.Radius=0.750000
App.ActiveDocument.C1365.Height=15.00
App.ActiveDocument.C1365.Angle=360.00 
App.ActiveDocument.C1365.Placement=Base.Placement(Base.Vector(-53.402945,-113.963404,471.663393),Base.Rotation(-0.814958,-0.303519,0.000000,0.493680))
App.ActiveDocument.addObject("Part::Cylinder","C1366")
App.ActiveDocument.C1366.Radius=0.750000
App.ActiveDocument.C1366.Height=15.00
App.ActiveDocument.C1366.Angle=360.00 
App.ActiveDocument.C1366.Placement=Base.Placement(Base.Vector(-53.584187,-115.771154,469.117230),Base.Rotation(-0.834496,-0.299631,0.000000,0.462425))
App.ActiveDocument.addObject("Part::Cylinder","C1367")
App.ActiveDocument.C1367.Radius=0.750000
App.ActiveDocument.C1367.Height=15.00
App.ActiveDocument.C1367.Angle=360.00 
App.ActiveDocument.C1367.Placement=Base.Placement(Base.Vector(-53.631552,-117.341109,467.140084),Base.Rotation(-0.849767,-0.293132,0.000000,0.438144))
App.ActiveDocument.addObject("Part::Cylinder","C1368")
App.ActiveDocument.C1368.Radius=0.750000
App.ActiveDocument.C1368.Height=15.00
App.ActiveDocument.C1368.Angle=360.00 
App.ActiveDocument.C1368.Placement=Base.Placement(Base.Vector(-53.626190,-137.468336,540.989772),Base.Rotation(-0.028765,-0.274623,0.000000,0.961122))
App.ActiveDocument.addObject("Part::Cylinder","C1369")
App.ActiveDocument.C1369.Radius=0.750000
App.ActiveDocument.C1369.Height=15.00
App.ActiveDocument.C1369.Angle=360.00 
App.ActiveDocument.C1369.Placement=Base.Placement(Base.Vector(-53.551294,-134.105478,540.703680),Base.Rotation(-0.058949,-0.274570,0.000000,0.959758))
App.ActiveDocument.addObject("Part::Cylinder","C1370")
App.ActiveDocument.C1370.Radius=0.750000
App.ActiveDocument.C1370.Height=15.00
App.ActiveDocument.C1370.Angle=360.00 
App.ActiveDocument.C1370.Placement=Base.Placement(Base.Vector(-53.578393,-130.850707,540.123308),Base.Rotation(-0.092791,-0.276475,0.000000,0.956531))
App.ActiveDocument.addObject("Part::Cylinder","C1371")
App.ActiveDocument.C1371.Radius=0.750000
App.ActiveDocument.C1371.Height=15.00
App.ActiveDocument.C1371.Angle=360.00 
App.ActiveDocument.C1371.Placement=Base.Placement(Base.Vector(-53.566141,-127.686357,539.309982),Base.Rotation(-0.132590,-0.277587,0.000000,0.951507))
App.ActiveDocument.addObject("Part::Cylinder","C1372")
App.ActiveDocument.C1372.Radius=0.750000
App.ActiveDocument.C1372.Height=15.00
App.ActiveDocument.C1372.Angle=360.00 
App.ActiveDocument.C1372.Placement=Base.Placement(Base.Vector(-53.555485,-124.741451,538.262626),Base.Rotation(-0.171276,-0.281485,0.000000,0.944156))
App.ActiveDocument.addObject("Part::Cylinder","C1373")
App.ActiveDocument.C1373.Radius=0.750000
App.ActiveDocument.C1373.Height=15.00
App.ActiveDocument.C1373.Angle=360.00 
App.ActiveDocument.C1373.Placement=Base.Placement(Base.Vector(-53.636714,-122.003524,536.917574),Base.Rotation(-0.212325,-0.282951,0.000000,0.935338))
App.ActiveDocument.addObject("Part::Cylinder","C1374")
App.ActiveDocument.C1374.Radius=0.750000
App.ActiveDocument.C1374.Height=15.00
App.ActiveDocument.C1374.Angle=360.00 
App.ActiveDocument.C1374.Placement=Base.Placement(Base.Vector(-53.814634,-119.551349,535.311112),Base.Rotation(-0.255402,-0.287309,0.000000,0.923159))
App.ActiveDocument.addObject("Part::Cylinder","C1375")
App.ActiveDocument.C1375.Radius=0.750000
App.ActiveDocument.C1375.Height=15.00
App.ActiveDocument.C1375.Angle=360.00 
App.ActiveDocument.C1375.Placement=Base.Placement(Base.Vector(-53.913654,-117.304704,533.547119),Base.Rotation(-0.297630,-0.290769,0.000000,0.909324))
App.ActiveDocument.addObject("Part::Cylinder","C1376")
App.ActiveDocument.C1376.Radius=0.750000
App.ActiveDocument.C1376.Height=15.00
App.ActiveDocument.C1376.Angle=360.00 
App.ActiveDocument.C1376.Placement=Base.Placement(Base.Vector(-53.968736,-115.199522,531.544962),Base.Rotation(-0.342262,-0.294001,0.000000,0.892424))
App.ActiveDocument.addObject("Part::Cylinder","C1377")
App.ActiveDocument.C1377.Radius=0.750000
App.ActiveDocument.C1377.Height=15.00
App.ActiveDocument.C1377.Angle=360.00 
App.ActiveDocument.C1377.Placement=Base.Placement(Base.Vector(-54.082434,-113.326878,529.297663),Base.Rotation(-0.385057,-0.297327,0.000000,0.873686))
App.ActiveDocument.addObject("Part::Cylinder","C1378")
App.ActiveDocument.C1378.Radius=0.750000
App.ActiveDocument.C1378.Height=15.00
App.ActiveDocument.C1378.Angle=360.00 
App.ActiveDocument.C1378.Placement=Base.Placement(Base.Vector(-54.068647,-111.631629,526.932369),Base.Rotation(-0.422080,-0.299136,0.000000,0.855784))
App.ActiveDocument.addObject("Part::Cylinder","C1379")
App.ActiveDocument.C1379.Radius=0.750000
App.ActiveDocument.C1379.Height=15.00
App.ActiveDocument.C1379.Angle=360.00 
App.ActiveDocument.C1379.Placement=Base.Placement(Base.Vector(-54.259252,-110.286514,524.397265),Base.Rotation(-0.453252,-0.304231,0.000000,0.837858))
App.ActiveDocument.addObject("Part::Cylinder","C1380")
App.ActiveDocument.C1380.Radius=0.750000
App.ActiveDocument.C1380.Height=15.00
App.ActiveDocument.C1380.Angle=360.00 
App.ActiveDocument.C1380.Placement=Base.Placement(Base.Vector(-54.324064,-109.048692,521.684160),Base.Rotation(-0.486324,-0.308778,0.000000,0.817402))
App.ActiveDocument.addObject("Part::Cylinder","C1381")
App.ActiveDocument.C1381.Radius=0.750000
App.ActiveDocument.C1381.Height=15.00
App.ActiveDocument.C1381.Angle=360.00 
App.ActiveDocument.C1381.Placement=Base.Placement(Base.Vector(-54.501046,-108.081504,518.821282),Base.Rotation(-0.514027,-0.314678,0.000000,0.797969))
App.ActiveDocument.addObject("Part::Cylinder","C1382")
App.ActiveDocument.C1382.Radius=0.750000
App.ActiveDocument.C1382.Height=15.00
App.ActiveDocument.C1382.Angle=360.00 
App.ActiveDocument.C1382.Placement=Base.Placement(Base.Vector(-54.641420,-107.314322,515.922864),Base.Rotation(-0.539031,-0.320183,0.000000,0.779056))
App.ActiveDocument.addObject("Part::Cylinder","C1383")
App.ActiveDocument.C1383.Radius=0.750000
App.ActiveDocument.C1383.Height=15.00
App.ActiveDocument.C1383.Angle=360.00 
App.ActiveDocument.C1383.Placement=Base.Placement(Base.Vector(-54.717623,-106.698081,512.927571),Base.Rotation(-0.559958,-0.326616,0.000000,0.761426))
App.ActiveDocument.addObject("Part::Cylinder","C1384")
App.ActiveDocument.C1384.Radius=0.750000
App.ActiveDocument.C1384.Height=15.00
App.ActiveDocument.C1384.Angle=360.00 
App.ActiveDocument.C1384.Placement=Base.Placement(Base.Vector(-54.760858,-106.263200,509.951333),Base.Rotation(-0.580237,-0.331294,0.000000,0.744022))
App.ActiveDocument.addObject("Part::Cylinder","C1385")
App.ActiveDocument.C1385.Radius=0.750000
App.ActiveDocument.C1385.Height=15.00
App.ActiveDocument.C1385.Angle=360.00 
App.ActiveDocument.C1385.Placement=Base.Placement(Base.Vector(-54.848490,-106.015757,506.753272),Base.Rotation(-0.598740,-0.337123,0.000000,0.726539))
App.ActiveDocument.addObject("Part::Cylinder","C1386")
App.ActiveDocument.C1386.Radius=0.750000
App.ActiveDocument.C1386.Height=15.00
App.ActiveDocument.C1386.Angle=360.00 
App.ActiveDocument.C1386.Placement=Base.Placement(Base.Vector(-55.009356,-105.993046,503.675612),Base.Rotation(-0.614434,-0.344737,0.000000,0.709668))
App.ActiveDocument.addObject("Part::Cylinder","C1387")
App.ActiveDocument.C1387.Radius=0.750000
App.ActiveDocument.C1387.Height=15.00
App.ActiveDocument.C1387.Angle=360.00 
App.ActiveDocument.C1387.Placement=Base.Placement(Base.Vector(-54.913501,-105.994507,500.614209),Base.Rotation(-0.628573,-0.352310,0.000000,0.693378))
App.ActiveDocument.addObject("Part::Cylinder","C1388")
App.ActiveDocument.C1388.Radius=0.750000
App.ActiveDocument.C1388.Height=15.00
App.ActiveDocument.C1388.Angle=360.00 
App.ActiveDocument.C1388.Placement=Base.Placement(Base.Vector(-55.054999,-106.296973,497.420991),Base.Rotation(-0.640554,-0.361867,0.000000,0.677306))
App.ActiveDocument.addObject("Part::Cylinder","C1389")
App.ActiveDocument.C1389.Radius=0.750000
App.ActiveDocument.C1389.Height=15.00
App.ActiveDocument.C1389.Angle=360.00 
App.ActiveDocument.C1389.Placement=Base.Placement(Base.Vector(-54.891042,-106.577882,494.331027),Base.Rotation(-0.655267,-0.366106,0.000000,0.660750))
App.ActiveDocument.addObject("Part::Cylinder","C1390")
App.ActiveDocument.C1390.Radius=0.750000
App.ActiveDocument.C1390.Height=15.00
App.ActiveDocument.C1390.Angle=360.00 
App.ActiveDocument.C1390.Placement=Base.Placement(Base.Vector(-55.019383,-107.177355,491.268347),Base.Rotation(-0.666685,-0.374406,0.000000,0.644478))
App.ActiveDocument.addObject("Part::Cylinder","C1391")
App.ActiveDocument.C1391.Radius=0.750000
App.ActiveDocument.C1391.Height=15.00
App.ActiveDocument.C1391.Angle=360.00 
App.ActiveDocument.C1391.Placement=Base.Placement(Base.Vector(-55.167355,-107.956103,488.155663),Base.Rotation(-0.677693,-0.383492,0.000000,0.627429))
App.ActiveDocument.addObject("Part::Cylinder","C1392")
App.ActiveDocument.C1392.Radius=0.750000
App.ActiveDocument.C1392.Height=15.00
App.ActiveDocument.C1392.Angle=360.00 
App.ActiveDocument.C1392.Placement=Base.Placement(Base.Vector(-55.182125,-108.808166,485.099461),Base.Rotation(-0.685236,-0.398192,0.000000,0.609831))
App.ActiveDocument.addObject("Part::Cylinder","C1393")
App.ActiveDocument.C1393.Radius=0.750000
App.ActiveDocument.C1393.Height=15.00
App.ActiveDocument.C1393.Angle=360.00 
App.ActiveDocument.C1393.Placement=Base.Placement(Base.Vector(-55.254278,-109.874857,482.026222),Base.Rotation(-0.696718,-0.405598,0.000000,0.591670))
App.ActiveDocument.addObject("Part::Cylinder","C1394")
App.ActiveDocument.C1394.Radius=0.750000
App.ActiveDocument.C1394.Height=15.00
App.ActiveDocument.C1394.Angle=360.00 
App.ActiveDocument.C1394.Placement=Base.Placement(Base.Vector(-55.252805,-111.068351,478.994309),Base.Rotation(-0.702900,-0.422530,0.000000,0.572189))
App.ActiveDocument.addObject("Part::Cylinder","C1395")
App.ActiveDocument.C1395.Radius=0.750000
App.ActiveDocument.C1395.Height=15.00
App.ActiveDocument.C1395.Angle=360.00 
App.ActiveDocument.C1395.Placement=Base.Placement(Base.Vector(-55.343911,-112.394988,476.229819),Base.Rotation(-0.704896,-0.442999,0.000000,0.553961))
App.ActiveDocument.addObject("Part::Cylinder","C1396")
App.ActiveDocument.C1396.Radius=0.750000
App.ActiveDocument.C1396.Height=15.00
App.ActiveDocument.C1396.Angle=360.00 
App.ActiveDocument.C1396.Placement=Base.Placement(Base.Vector(-55.295570,-113.874491,473.389237),Base.Rotation(-0.710713,-0.458777,0.000000,0.533301))
App.ActiveDocument.addObject("Part::Cylinder","C1397")
App.ActiveDocument.C1397.Radius=0.750000
App.ActiveDocument.C1397.Height=15.00
App.ActiveDocument.C1397.Angle=360.00 
App.ActiveDocument.C1397.Placement=Base.Placement(Base.Vector(-55.201048,-115.481433,470.673183),Base.Rotation(-0.713882,-0.479934,0.000000,0.509937))
App.ActiveDocument.addObject("Part::Cylinder","C1398")
App.ActiveDocument.C1398.Radius=0.750000
App.ActiveDocument.C1398.Height=15.00
App.ActiveDocument.C1398.Angle=360.00 
App.ActiveDocument.C1398.Placement=Base.Placement(Base.Vector(-55.426355,-117.350477,468.239173),Base.Rotation(-0.721262,-0.495524,0.000000,0.483981))
App.ActiveDocument.addObject("Part::Cylinder","C1399")
App.ActiveDocument.C1399.Radius=0.750000
App.ActiveDocument.C1399.Height=15.00
App.ActiveDocument.C1399.Angle=360.00 
App.ActiveDocument.C1399.Placement=Base.Placement(Base.Vector(-55.540503,-118.955939,466.322644),Base.Rotation(-0.681162,-0.557196,0.000000,0.474922))
App.ActiveDocument.addObject("Part::Cylinder","C1400")
App.ActiveDocument.C1400.Radius=0.750000
App.ActiveDocument.C1400.Height=15.00
App.ActiveDocument.C1400.Angle=360.00 
App.ActiveDocument.C1400.Placement=Base.Placement(Base.Vector(-56.501507,-137.512249,539.082621),Base.Rotation(-0.028956,-0.301902,0.000000,0.952899))
App.ActiveDocument.addObject("Part::Cylinder","C1401")
App.ActiveDocument.C1401.Radius=0.750000
App.ActiveDocument.C1401.Height=15.00
App.ActiveDocument.C1401.Angle=360.00 
App.ActiveDocument.C1401.Placement=Base.Placement(Base.Vector(-56.406609,-134.160793,538.804803),Base.Rotation(-0.060117,-0.302698,0.000000,0.951189))
App.ActiveDocument.addObject("Part::Cylinder","C1402")
App.ActiveDocument.C1402.Radius=0.750000
App.ActiveDocument.C1402.Height=15.00
App.ActiveDocument.C1402.Angle=360.00 
App.ActiveDocument.C1402.Placement=Base.Placement(Base.Vector(-56.409286,-130.832367,538.195380),Base.Rotation(-0.095301,-0.303143,0.000000,0.948168))
App.ActiveDocument.addObject("Part::Cylinder","C1403")
App.ActiveDocument.C1403.Radius=0.750000
App.ActiveDocument.C1403.Height=15.00
App.ActiveDocument.C1403.Angle=360.00 
App.ActiveDocument.C1403.Placement=Base.Placement(Base.Vector(-56.445237,-127.744752,537.320792),Base.Rotation(-0.136901,-0.306227,0.000000,0.942063))
App.ActiveDocument.addObject("Part::Cylinder","C1404")
App.ActiveDocument.C1404.Radius=0.750000
App.ActiveDocument.C1404.Height=15.00
App.ActiveDocument.C1404.Angle=360.00 
App.ActiveDocument.C1404.Placement=Base.Placement(Base.Vector(-56.491475,-124.795469,536.161652),Base.Rotation(-0.175704,-0.309837,0.000000,0.934414))
App.ActiveDocument.addObject("Part::Cylinder","C1405")
App.ActiveDocument.C1405.Radius=0.750000
App.ActiveDocument.C1405.Height=15.00
App.ActiveDocument.C1405.Angle=360.00 
App.ActiveDocument.C1405.Placement=Base.Placement(Base.Vector(-56.566204,-122.167673,534.777154),Base.Rotation(-0.218079,-0.313243,0.000000,0.924295))
App.ActiveDocument.addObject("Part::Cylinder","C1406")
App.ActiveDocument.C1406.Radius=0.750000
App.ActiveDocument.C1406.Height=15.00
App.ActiveDocument.C1406.Angle=360.00 
App.ActiveDocument.C1406.Placement=Base.Placement(Base.Vector(-56.802549,-119.871008,533.102370),Base.Rotation(-0.261291,-0.318412,0.000000,0.911230))
App.ActiveDocument.addObject("Part::Cylinder","C1407")
App.ActiveDocument.C1407.Radius=0.750000
App.ActiveDocument.C1407.Height=15.00
App.ActiveDocument.C1407.Angle=360.00 
App.ActiveDocument.C1407.Placement=Base.Placement(Base.Vector(-56.773509,-117.648548,531.336895),Base.Rotation(-0.306605,-0.321756,0.000000,0.895805))
App.ActiveDocument.addObject("Part::Cylinder","C1408")
App.ActiveDocument.C1408.Radius=0.750000
App.ActiveDocument.C1408.Height=15.00
App.ActiveDocument.C1408.Angle=360.00 
App.ActiveDocument.C1408.Placement=Base.Placement(Base.Vector(-56.915027,-115.724598,529.274195),Base.Rotation(-0.347264,-0.325683,0.000000,0.879396))
App.ActiveDocument.addObject("Part::Cylinder","C1409")
App.ActiveDocument.C1409.Radius=0.750000
App.ActiveDocument.C1409.Height=15.00
App.ActiveDocument.C1409.Angle=360.00 
App.ActiveDocument.C1409.Placement=Base.Placement(Base.Vector(-56.950483,-113.941959,527.026817),Base.Rotation(-0.387305,-0.328953,0.000000,0.861269))
App.ActiveDocument.addObject("Part::Cylinder","C1410")
App.ActiveDocument.C1410.Radius=0.750000
App.ActiveDocument.C1410.Height=15.00
App.ActiveDocument.C1410.Angle=360.00 
App.ActiveDocument.C1410.Placement=Base.Placement(Base.Vector(-57.055620,-112.535992,524.769505),Base.Rotation(-0.419806,-0.334344,0.000000,0.843787))
App.ActiveDocument.addObject("Part::Cylinder","C1411")
App.ActiveDocument.C1411.Radius=0.750000
App.ActiveDocument.C1411.Height=15.00
App.ActiveDocument.C1411.Angle=360.00 
App.ActiveDocument.C1411.Placement=Base.Placement(Base.Vector(-57.215068,-111.252277,522.139126),Base.Rotation(-0.452265,-0.339232,0.000000,0.824850))
App.ActiveDocument.addObject("Part::Cylinder","C1412")
App.ActiveDocument.C1412.Radius=0.750000
App.ActiveDocument.C1412.Height=15.00
App.ActiveDocument.C1412.Angle=360.00 
App.ActiveDocument.C1412.Placement=Base.Placement(Base.Vector(-57.366285,-110.221459,519.485843),Base.Rotation(-0.481397,-0.346742,0.000000,0.805002))
App.ActiveDocument.addObject("Part::Cylinder","C1413")
App.ActiveDocument.C1413.Radius=0.750000
App.ActiveDocument.C1413.Height=15.00
App.ActiveDocument.C1413.Angle=360.00 
App.ActiveDocument.C1413.Placement=Base.Placement(Base.Vector(-57.518072,-109.380176,516.672847),Base.Rotation(-0.507549,-0.354189,0.000000,0.785458))
App.ActiveDocument.addObject("Part::Cylinder","C1414")
App.ActiveDocument.C1414.Radius=0.750000
App.ActiveDocument.C1414.Height=15.00
App.ActiveDocument.C1414.Angle=360.00 
App.ActiveDocument.C1414.Placement=Base.Placement(Base.Vector(-57.597721,-108.683127,513.752538),Base.Rotation(-0.528357,-0.360239,0.000000,0.768809))
App.ActiveDocument.addObject("Part::Cylinder","C1415")
App.ActiveDocument.C1415.Radius=0.750000
App.ActiveDocument.C1415.Height=15.00
App.ActiveDocument.C1415.Angle=360.00 
App.ActiveDocument.C1415.Placement=Base.Placement(Base.Vector(-57.687528,-108.190816,510.737872),Base.Rotation(-0.549931,-0.369602,0.000000,0.748979))
App.ActiveDocument.addObject("Part::Cylinder","C1416")
App.ActiveDocument.C1416.Radius=0.750000
App.ActiveDocument.C1416.Height=15.00
App.ActiveDocument.C1416.Angle=360.00 
App.ActiveDocument.C1416.Placement=Base.Placement(Base.Vector(-57.661961,-107.827817,507.835680),Base.Rotation(-0.566083,-0.377579,0.000000,0.732792))
App.ActiveDocument.addObject("Part::Cylinder","C1417")
App.ActiveDocument.C1417.Radius=0.750000
App.ActiveDocument.C1417.Height=15.00
App.ActiveDocument.C1417.Angle=360.00 
App.ActiveDocument.C1417.Placement=Base.Placement(Base.Vector(-57.825756,-107.756180,504.757445),Base.Rotation(-0.580452,-0.388582,0.000000,0.715597))
App.ActiveDocument.addObject("Part::Cylinder","C1418")
App.ActiveDocument.C1418.Radius=0.750000
App.ActiveDocument.C1418.Height=15.00
App.ActiveDocument.C1418.Angle=360.00 
App.ActiveDocument.C1418.Placement=Base.Placement(Base.Vector(-57.819053,-107.747511,501.731846),Base.Rotation(-0.593461,-0.398186,0.000000,0.699465))
App.ActiveDocument.addObject("Part::Cylinder","C1419")
App.ActiveDocument.C1419.Radius=0.750000
App.ActiveDocument.C1419.Height=15.00
App.ActiveDocument.C1419.Angle=360.00 
App.ActiveDocument.C1419.Placement=Base.Placement(Base.Vector(-57.796982,-107.894286,498.650265),Base.Rotation(-0.603598,-0.410110,0.000000,0.683725))
App.ActiveDocument.addObject("Part::Cylinder","C1420")
App.ActiveDocument.C1420.Radius=0.750000
App.ActiveDocument.C1420.Height=15.00
App.ActiveDocument.C1420.Angle=360.00 
App.ActiveDocument.C1420.Placement=Base.Placement(Base.Vector(-57.677144,-108.148628,495.522192),Base.Rotation(-0.613473,-0.422000,0.000000,0.667508))
App.ActiveDocument.addObject("Part::Cylinder","C1421")
App.ActiveDocument.C1421.Radius=0.750000
App.ActiveDocument.C1421.Height=15.00
App.ActiveDocument.C1421.Angle=360.00 
App.ActiveDocument.C1421.Placement=Base.Placement(Base.Vector(-57.617057,-108.561190,492.620346),Base.Rotation(-0.619812,-0.436605,0.000000,0.652081))
App.ActiveDocument.addObject("Part::Cylinder","C1422")
App.ActiveDocument.C1422.Radius=0.750000
App.ActiveDocument.C1422.Height=15.00
App.ActiveDocument.C1422.Angle=360.00 
App.ActiveDocument.C1422.Placement=Base.Placement(Base.Vector(-57.656048,-109.215278,489.622031),Base.Rotation(-0.626544,-0.449653,0.000000,0.636596))
App.ActiveDocument.addObject("Part::Cylinder","C1423")
App.ActiveDocument.C1423.Radius=0.750000
App.ActiveDocument.C1423.Height=15.00
App.ActiveDocument.C1423.Angle=360.00 
App.ActiveDocument.C1423.Placement=Base.Placement(Base.Vector(-57.645761,-110.018498,486.548366),Base.Rotation(-0.627519,-0.470857,0.000000,0.620092))
App.ActiveDocument.addObject("Part::Cylinder","C1424")
App.ActiveDocument.C1424.Radius=0.750000
App.ActiveDocument.C1424.Height=15.00
App.ActiveDocument.C1424.Angle=360.00 
App.ActiveDocument.C1424.Placement=Base.Placement(Base.Vector(-57.574164,-110.924711,483.550963),Base.Rotation(-0.630665,-0.485751,0.000000,0.605234))
App.ActiveDocument.addObject("Part::Cylinder","C1425")
App.ActiveDocument.C1425.Radius=0.750000
App.ActiveDocument.C1425.Height=15.00
App.ActiveDocument.C1425.Angle=360.00 
App.ActiveDocument.C1425.Placement=Base.Placement(Base.Vector(-57.515913,-111.984487,480.653640),Base.Rotation(-0.629617,-0.506800,0.000000,0.588843))
App.ActiveDocument.addObject("Part::Cylinder","C1426")
App.ActiveDocument.C1426.Radius=0.750000
App.ActiveDocument.C1426.Height=15.00
App.ActiveDocument.C1426.Angle=360.00 
App.ActiveDocument.C1426.Placement=Base.Placement(Base.Vector(-57.467070,-113.151292,477.938543),Base.Rotation(-0.622486,-0.531468,0.000000,0.574502))
App.ActiveDocument.addObject("Part::Cylinder","C1427")
App.ActiveDocument.C1427.Radius=0.750000
App.ActiveDocument.C1427.Height=15.00
App.ActiveDocument.C1427.Angle=360.00 
App.ActiveDocument.C1427.Placement=Base.Placement(Base.Vector(-57.342665,-114.485298,475.152094),Base.Rotation(-0.615919,-0.557705,0.000000,0.556425))
App.ActiveDocument.addObject("Part::Cylinder","C1428")
App.ActiveDocument.C1428.Radius=0.750000
App.ActiveDocument.C1428.Height=15.00
App.ActiveDocument.C1428.Angle=360.00 
App.ActiveDocument.C1428.Placement=Base.Placement(Base.Vector(-57.136858,-115.905963,472.447683),Base.Rotation(-0.603150,-0.587680,0.000000,0.539297))
App.ActiveDocument.addObject("Part::Cylinder","C1429")
App.ActiveDocument.C1429.Radius=0.750000
App.ActiveDocument.C1429.Height=15.00
App.ActiveDocument.C1429.Angle=360.00 
App.ActiveDocument.C1429.Placement=Base.Placement(Base.Vector(-57.059944,-117.475076,470.065682),Base.Rotation(-0.574427,-0.628054,0.000000,0.524959))
App.ActiveDocument.addObject("Part::Cylinder","C1430")
App.ActiveDocument.C1430.Radius=0.750000
App.ActiveDocument.C1430.Height=15.00
App.ActiveDocument.C1430.Angle=360.00 
App.ActiveDocument.C1430.Placement=Base.Placement(Base.Vector(-56.994999,-119.044824,468.015927),Base.Rotation(-0.533009,-0.674227,0.000000,0.511194))
App.ActiveDocument.addObject("Part::Cylinder","C1431")
App.ActiveDocument.C1431.Radius=0.750000
App.ActiveDocument.C1431.Height=15.00
App.ActiveDocument.C1431.Angle=360.00 
App.ActiveDocument.C1431.Placement=Base.Placement(Base.Vector(-56.810569,-120.653936,466.058552),Base.Rotation(-0.482213,-0.718667,0.000000,0.500987))
App.ActiveDocument.addObject("Part::Cylinder","C1432")
App.ActiveDocument.C1432.Radius=0.750000
App.ActiveDocument.C1432.Height=15.00
App.ActiveDocument.C1432.Angle=360.00 
App.ActiveDocument.C1432.Placement=Base.Placement(Base.Vector(-59.331527,-137.522873,536.964627),Base.Rotation(-0.029657,-0.328388,0.000000,0.944077))
App.ActiveDocument.addObject("Part::Cylinder","C1433")
App.ActiveDocument.C1433.Radius=0.750000
App.ActiveDocument.C1433.Height=15.00
App.ActiveDocument.C1433.Angle=360.00 
App.ActiveDocument.C1433.Placement=Base.Placement(Base.Vector(-59.154094,-134.168375,536.740847),Base.Rotation(-0.061559,-0.327910,0.000000,0.942701))
App.ActiveDocument.addObject("Part::Cylinder","C1434")
App.ActiveDocument.C1434.Radius=0.750000
App.ActiveDocument.C1434.Height=15.00
App.ActiveDocument.C1434.Angle=360.00 
App.ActiveDocument.C1434.Placement=Base.Placement(Base.Vector(-59.213583,-130.919720,536.065243),Base.Rotation(-0.097800,-0.329972,0.000000,0.938911))
App.ActiveDocument.addObject("Part::Cylinder","C1435")
App.ActiveDocument.C1435.Radius=0.750000
App.ActiveDocument.C1435.Height=15.00
App.ActiveDocument.C1435.Angle=360.00 
App.ActiveDocument.C1435.Placement=Base.Placement(Base.Vector(-59.268302,-127.901619,535.142010),Base.Rotation(-0.137049,-0.333291,0.000000,0.932810))
App.ActiveDocument.addObject("Part::Cylinder","C1436")
App.ActiveDocument.C1436.Radius=0.750000
App.ActiveDocument.C1436.Height=15.00
App.ActiveDocument.C1436.Angle=360.00 
App.ActiveDocument.C1436.Placement=Base.Placement(Base.Vector(-59.340733,-125.084625,533.941094),Base.Rotation(-0.180414,-0.335788,0.000000,0.924498))
App.ActiveDocument.addObject("Part::Cylinder","C1437")
App.ActiveDocument.C1437.Radius=0.750000
App.ActiveDocument.C1437.Height=15.00
App.ActiveDocument.C1437.Angle=360.00 
App.ActiveDocument.C1437.Placement=Base.Placement(Base.Vector(-59.460136,-122.546051,532.473761),Base.Rotation(-0.223582,-0.341986,0.000000,0.912719))
App.ActiveDocument.addObject("Part::Cylinder","C1438")
App.ActiveDocument.C1438.Radius=0.750000
App.ActiveDocument.C1438.Height=15.00
App.ActiveDocument.C1438.Angle=360.00 
App.ActiveDocument.C1438.Placement=Base.Placement(Base.Vector(-59.613890,-120.238113,530.731196),Base.Rotation(-0.268188,-0.346460,0.000000,0.898911))
App.ActiveDocument.addObject("Part::Cylinder","C1439")
App.ActiveDocument.C1439.Radius=0.750000
App.ActiveDocument.C1439.Height=15.00
App.ActiveDocument.C1439.Angle=360.00 
App.ActiveDocument.C1439.Placement=Base.Placement(Base.Vector(-59.676953,-118.176732,528.865217),Base.Rotation(-0.310454,-0.349798,0.000000,0.883889))
App.ActiveDocument.addObject("Part::Cylinder","C1440")
App.ActiveDocument.C1440.Radius=0.750000
App.ActiveDocument.C1440.Height=15.00
App.ActiveDocument.C1440.Angle=360.00 
App.ActiveDocument.C1440.Placement=Base.Placement(Base.Vector(-59.774397,-116.383629,526.794243),Base.Rotation(-0.350884,-0.355440,0.000000,0.866339))
App.ActiveDocument.addObject("Part::Cylinder","C1441")
App.ActiveDocument.C1441.Radius=0.750000
App.ActiveDocument.C1441.Height=15.00
App.ActiveDocument.C1441.Angle=360.00 
App.ActiveDocument.C1441.Placement=Base.Placement(Base.Vector(-59.922574,-114.864140,524.549097),Base.Rotation(-0.388851,-0.363342,0.000000,0.846627))
App.ActiveDocument.addObject("Part::Cylinder","C1442")
App.ActiveDocument.C1442.Radius=0.750000
App.ActiveDocument.C1442.Height=15.00
App.ActiveDocument.C1442.Angle=360.00 
App.ActiveDocument.C1442.Placement=Base.Placement(Base.Vector(-60.037448,-113.501451,522.086966),Base.Rotation(-0.423383,-0.366642,0.000000,0.828445))
App.ActiveDocument.addObject("Part::Cylinder","C1443")
App.ActiveDocument.C1443.Radius=0.750000
App.ActiveDocument.C1443.Height=15.00
App.ActiveDocument.C1443.Angle=360.00 
App.ActiveDocument.C1443.Placement=Base.Placement(Base.Vector(-60.253861,-112.521728,519.652352),Base.Rotation(-0.451338,-0.374915,0.000000,0.809773))
App.ActiveDocument.addObject("Part::Cylinder","C1444")
App.ActiveDocument.C1444.Radius=0.750000
App.ActiveDocument.C1444.Height=15.00
App.ActiveDocument.C1444.Angle=360.00 
App.ActiveDocument.C1444.Placement=Base.Placement(Base.Vector(-60.400741,-111.662874,517.077149),Base.Rotation(-0.475789,-0.382027,0.000000,0.792263))
App.ActiveDocument.addObject("Part::Cylinder","C1445")
App.ActiveDocument.C1445.Radius=0.750000
App.ActiveDocument.C1445.Height=15.00
App.ActiveDocument.C1445.Angle=360.00 
App.ActiveDocument.C1445.Placement=Base.Placement(Base.Vector(-60.409080,-110.866307,514.319210),Base.Rotation(-0.500472,-0.389009,0.000000,0.773434))
App.ActiveDocument.addObject("Part::Cylinder","C1446")
App.ActiveDocument.C1446.Radius=0.750000
App.ActiveDocument.C1446.Height=15.00
App.ActiveDocument.C1446.Angle=360.00 
App.ActiveDocument.C1446.Placement=Base.Placement(Base.Vector(-60.524671,-110.350975,511.481307),Base.Rotation(-0.521102,-0.399642,0.000000,0.754148))
App.ActiveDocument.addObject("Part::Cylinder","C1447")
App.ActiveDocument.C1447.Radius=0.750000
App.ActiveDocument.C1447.Height=15.00
App.ActiveDocument.C1447.Angle=360.00 
App.ActiveDocument.C1447.Placement=Base.Placement(Base.Vector(-60.525149,-109.939492,508.553846),Base.Rotation(-0.539025,-0.408078,0.000000,0.736834))
App.ActiveDocument.addObject("Part::Cylinder","C1448")
App.ActiveDocument.C1448.Radius=0.750000
App.ActiveDocument.C1448.Height=15.00
App.ActiveDocument.C1448.Angle=360.00 
App.ActiveDocument.C1448.Placement=Base.Placement(Base.Vector(-60.603679,-109.780054,505.691889),Base.Rotation(-0.552064,-0.420846,0.000000,0.719801))
App.ActiveDocument.addObject("Part::Cylinder","C1449")
App.ActiveDocument.C1449.Radius=0.750000
App.ActiveDocument.C1449.Height=15.00
App.ActiveDocument.C1449.Angle=360.00 
App.ActiveDocument.C1449.Placement=Base.Placement(Base.Vector(-60.599066,-109.732483,502.614792),Base.Rotation(-0.565118,-0.432894,0.000000,0.702313))
App.ActiveDocument.addObject("Part::Cylinder","C1450")
App.ActiveDocument.C1450.Radius=0.750000
App.ActiveDocument.C1450.Height=15.00
App.ActiveDocument.C1450.Angle=360.00 
App.ActiveDocument.C1450.Placement=Base.Placement(Base.Vector(-60.607586,-109.866738,499.719848),Base.Rotation(-0.573960,-0.446379,0.000000,0.686524))
App.ActiveDocument.addObject("Part::Cylinder","C1451")
App.ActiveDocument.C1451.Radius=0.750000
App.ActiveDocument.C1451.Height=15.00
App.ActiveDocument.C1451.Angle=360.00 
App.ActiveDocument.C1451.Placement=Base.Placement(Base.Vector(-60.446019,-110.056709,496.594838),Base.Rotation(-0.582298,-0.459817,0.000000,0.670446))
App.ActiveDocument.addObject("Part::Cylinder","C1452")
App.ActiveDocument.C1452.Radius=0.750000
App.ActiveDocument.C1452.Height=15.00
App.ActiveDocument.C1452.Angle=360.00 
App.ActiveDocument.C1452.Placement=Base.Placement(Base.Vector(-60.405400,-110.483427,493.670290),Base.Rotation(-0.586379,-0.476888,0.000000,0.654781))
App.ActiveDocument.addObject("Part::Cylinder","C1453")
App.ActiveDocument.C1453.Radius=0.750000
App.ActiveDocument.C1453.Height=15.00
App.ActiveDocument.C1453.Angle=360.00 
App.ActiveDocument.C1453.Placement=Base.Placement(Base.Vector(-60.301854,-111.014860,490.761093),Base.Rotation(-0.588797,-0.494325,0.000000,0.639500))
App.ActiveDocument.addObject("Part::Cylinder","C1454")
App.ActiveDocument.C1454.Radius=0.750000
App.ActiveDocument.C1454.Height=15.00
App.ActiveDocument.C1454.Angle=360.00 
App.ActiveDocument.C1454.Placement=Base.Placement(Base.Vector(-60.301592,-111.751358,488.010194),Base.Rotation(-0.587202,-0.513643,0.000000,0.625592))
App.ActiveDocument.addObject("Part::Cylinder","C1455")
App.ActiveDocument.C1455.Radius=0.750000
App.ActiveDocument.C1455.Height=15.00
App.ActiveDocument.C1455.Angle=360.00 
App.ActiveDocument.C1455.Placement=Base.Placement(Base.Vector(-60.104959,-112.529759,485.095020),Base.Rotation(-0.584643,-0.535014,0.000000,0.609879))
App.ActiveDocument.addObject("Part::Cylinder","C1456")
App.ActiveDocument.C1456.Radius=0.750000
App.ActiveDocument.C1456.Height=15.00
App.ActiveDocument.C1456.Angle=360.00 
App.ActiveDocument.C1456.Placement=Base.Placement(Base.Vector(-60.055839,-113.539572,482.390365),Base.Rotation(-0.578182,-0.558004,0.000000,0.595262))
App.ActiveDocument.addObject("Part::Cylinder","C1457")
App.ActiveDocument.C1457.Radius=0.750000
App.ActiveDocument.C1457.Height=15.00
App.ActiveDocument.C1457.Angle=360.00 
App.ActiveDocument.C1457.Placement=Base.Placement(Base.Vector(-59.893509,-114.611691,479.704159),Base.Rotation(-0.567085,-0.584641,0.000000,0.580180))
App.ActiveDocument.addObject("Part::Cylinder","C1458")
App.ActiveDocument.C1458.Radius=0.750000
App.ActiveDocument.C1458.Height=15.00
App.ActiveDocument.C1458.Angle=360.00 
App.ActiveDocument.C1458.Placement=Base.Placement(Base.Vector(-59.723665,-115.826092,477.102719),Base.Rotation(-0.550751,-0.613342,0.000000,0.566114))
App.ActiveDocument.addObject("Part::Cylinder","C1459")
App.ActiveDocument.C1459.Radius=0.750000
App.ActiveDocument.C1459.Height=15.00
App.ActiveDocument.C1459.Angle=360.00 
App.ActiveDocument.C1459.Placement=Base.Placement(Base.Vector(-59.362300,-117.110865,474.385646),Base.Rotation(-0.529783,-0.645937,0.000000,0.549631))
App.ActiveDocument.addObject("Part::Cylinder","C1460")
App.ActiveDocument.C1460.Radius=0.750000
App.ActiveDocument.C1460.Height=15.00
App.ActiveDocument.C1460.Angle=360.00 
App.ActiveDocument.C1460.Placement=Base.Placement(Base.Vector(-59.172055,-118.609599,472.021719),Base.Rotation(-0.493691,-0.686039,0.000000,0.534433))
App.ActiveDocument.addObject("Part::Cylinder","C1461")
App.ActiveDocument.C1461.Radius=0.750000
App.ActiveDocument.C1461.Height=15.00
App.ActiveDocument.C1461.Angle=360.00 
App.ActiveDocument.C1461.Placement=Base.Placement(Base.Vector(-59.053204,-120.257712,469.957263),Base.Rotation(-0.451445,-0.725426,0.000000,0.519572))
App.ActiveDocument.addObject("Part::Cylinder","C1462")
App.ActiveDocument.C1462.Radius=0.750000
App.ActiveDocument.C1462.Height=15.00
App.ActiveDocument.C1462.Angle=360.00 
App.ActiveDocument.C1462.Placement=Base.Placement(Base.Vector(-58.817652,-121.947308,468.012540),Base.Rotation(-0.401142,-0.763827,0.000000,0.505622))
App.ActiveDocument.addObject("Part::Cylinder","C1463")
App.ActiveDocument.C1463.Radius=0.750000
App.ActiveDocument.C1463.Height=15.00
App.ActiveDocument.C1463.Angle=360.00 
App.ActiveDocument.C1463.Placement=Base.Placement(Base.Vector(-58.361588,-123.443461,466.199430),Base.Rotation(-0.344005,-0.799177,0.000000,0.492927))
App.ActiveDocument.addObject("Part::Cylinder","C1464")
App.ActiveDocument.C1464.Radius=0.750000
App.ActiveDocument.C1464.Height=15.00
App.ActiveDocument.C1464.Angle=360.00 
App.ActiveDocument.C1464.Placement=Base.Placement(Base.Vector(-61.993543,-137.572016,534.745205),Base.Rotation(-0.029390,-0.352226,0.000000,0.935454))
App.ActiveDocument.addObject("Part::Cylinder","C1465")
App.ActiveDocument.C1465.Radius=0.750000
App.ActiveDocument.C1465.Height=15.00
App.ActiveDocument.C1465.Angle=360.00 
App.ActiveDocument.C1465.Placement=Base.Placement(Base.Vector(-61.821238,-134.291695,534.523292),Base.Rotation(-0.061809,-0.351875,0.000000,0.934004))
App.ActiveDocument.addObject("Part::Cylinder","C1466")
App.ActiveDocument.C1466.Radius=0.750000
App.ActiveDocument.C1466.Height=15.00
App.ActiveDocument.C1466.Angle=360.00 
App.ActiveDocument.C1466.Placement=Base.Placement(Base.Vector(-61.913144,-131.055363,533.781133),Base.Rotation(-0.099135,-0.355223,0.000000,0.929510))
App.ActiveDocument.addObject("Part::Cylinder","C1467")
App.ActiveDocument.C1467.Radius=0.750000
App.ActiveDocument.C1467.Height=15.00
App.ActiveDocument.C1467.Angle=360.00 
App.ActiveDocument.C1467.Placement=Base.Placement(Base.Vector(-61.992324,-128.093306,532.787883),Base.Rotation(-0.141232,-0.359150,0.000000,0.922532))
App.ActiveDocument.addObject("Part::Cylinder","C1468")
App.ActiveDocument.C1468.Radius=0.750000
App.ActiveDocument.C1468.Height=15.00
App.ActiveDocument.C1468.Angle=360.00 
App.ActiveDocument.C1468.Placement=Base.Placement(Base.Vector(-62.075426,-125.377549,531.531841),Base.Rotation(-0.183350,-0.362183,0.000000,0.913896))
App.ActiveDocument.addObject("Part::Cylinder","C1469")
App.ActiveDocument.C1469.Radius=0.750000
App.ActiveDocument.C1469.Height=15.00
App.ActiveDocument.C1469.Angle=360.00 
App.ActiveDocument.C1469.Placement=Base.Placement(Base.Vector(-62.227963,-122.982084,529.994201),Base.Rotation(-0.230253,-0.367157,0.000000,0.901210))
App.ActiveDocument.addObject("Part::Cylinder","C1470")
App.ActiveDocument.C1470.Radius=0.750000
App.ActiveDocument.C1470.Height=15.00
App.ActiveDocument.C1470.Angle=360.00 
App.ActiveDocument.C1470.Placement=Base.Placement(Base.Vector(-62.388126,-120.806541,528.194311),Base.Rotation(-0.273372,-0.373821,0.000000,0.886299))
App.ActiveDocument.addObject("Part::Cylinder","C1471")
App.ActiveDocument.C1471.Radius=0.750000
App.ActiveDocument.C1471.Height=15.00
App.ActiveDocument.C1471.Angle=360.00 
App.ActiveDocument.C1471.Placement=Base.Placement(Base.Vector(-62.443626,-118.841466,526.253087),Base.Rotation(-0.318033,-0.378291,0.000000,0.869339))
App.ActiveDocument.addObject("Part::Cylinder","C1472")
App.ActiveDocument.C1472.Radius=0.750000
App.ActiveDocument.C1472.Height=15.00
App.ActiveDocument.C1472.Angle=360.00 
App.ActiveDocument.C1472.Placement=Base.Placement(Base.Vector(-62.706601,-117.274283,524.013742),Base.Rotation(-0.356954,-0.384351,0.000000,0.851386))
App.ActiveDocument.addObject("Part::Cylinder","C1473")
App.ActiveDocument.C1473.Radius=0.750000
App.ActiveDocument.C1473.Height=15.00
App.ActiveDocument.C1473.Angle=360.00 
App.ActiveDocument.C1473.Placement=Base.Placement(Base.Vector(-62.820127,-115.823707,521.620574),Base.Rotation(-0.394981,-0.390868,0.000000,0.831392))
App.ActiveDocument.addObject("Part::Cylinder","C1474")
App.ActiveDocument.C1474.Radius=0.750000
App.ActiveDocument.C1474.Height=15.00
App.ActiveDocument.C1474.Angle=360.00 
App.ActiveDocument.C1474.Placement=Base.Placement(Base.Vector(-63.026840,-114.790557,519.254860),Base.Rotation(-0.425641,-0.398532,0.000000,0.812405))
App.ActiveDocument.addObject("Part::Cylinder","C1475")
App.ActiveDocument.C1475.Radius=0.750000
App.ActiveDocument.C1475.Height=15.00
App.ActiveDocument.C1475.Angle=360.00 
App.ActiveDocument.C1475.Placement=Base.Placement(Base.Vector(-63.212838,-113.967212,516.836835),Base.Rotation(-0.452529,-0.405876,0.000000,0.794029))
App.ActiveDocument.addObject("Part::Cylinder","C1476")
App.ActiveDocument.C1476.Radius=0.750000
App.ActiveDocument.C1476.Height=15.00
App.ActiveDocument.C1476.Angle=360.00 
App.ActiveDocument.C1476.Placement=Base.Placement(Base.Vector(-63.305694,-113.236421,514.264163),Base.Rotation(-0.476669,-0.414523,0.000000,0.775214))
App.ActiveDocument.addObject("Part::Cylinder","C1477")
App.ActiveDocument.C1477.Radius=0.750000
App.ActiveDocument.C1477.Height=15.00
App.ActiveDocument.C1477.Angle=360.00 
App.ActiveDocument.C1477.Placement=Base.Placement(Base.Vector(-63.320773,-112.646590,511.682800),Base.Rotation(-0.497818,-0.423415,0.000000,0.756899))
App.ActiveDocument.addObject("Part::Cylinder","C1478")
App.ActiveDocument.C1478.Radius=0.750000
App.ActiveDocument.C1478.Height=15.00
App.ActiveDocument.C1478.Angle=360.00 
App.ActiveDocument.C1478.Placement=Base.Placement(Base.Vector(-63.370898,-112.243764,508.812694),Base.Rotation(-0.516465,-0.433685,0.000000,0.738364))
App.ActiveDocument.addObject("Part::Cylinder","C1479")
App.ActiveDocument.C1479.Radius=0.750000
App.ActiveDocument.C1479.Height=15.00
App.ActiveDocument.C1479.Angle=360.00 
App.ActiveDocument.C1479.Placement=Base.Placement(Base.Vector(-63.279638,-111.929022,505.951011),Base.Rotation(-0.533083,-0.444452,0.000000,0.719920))
App.ActiveDocument.addObject("Part::Cylinder","C1480")
App.ActiveDocument.C1480.Radius=0.750000
App.ActiveDocument.C1480.Height=15.00
App.ActiveDocument.C1480.Angle=360.00 
App.ActiveDocument.C1480.Placement=Base.Placement(Base.Vector(-63.344975,-111.935286,503.071823),Base.Rotation(-0.543327,-0.458613,0.000000,0.703186))
App.ActiveDocument.addObject("Part::Cylinder","C1481")
App.ActiveDocument.C1481.Radius=0.750000
App.ActiveDocument.C1481.Height=15.00
App.ActiveDocument.C1481.Angle=360.00 
App.ActiveDocument.C1481.Placement=Base.Placement(Base.Vector(-63.438457,-112.143626,500.269798),Base.Rotation(-0.552918,-0.472299,0.000000,0.686452))
App.ActiveDocument.addObject("Part::Cylinder","C1482")
App.ActiveDocument.C1482.Radius=0.750000
App.ActiveDocument.C1482.Height=15.00
App.ActiveDocument.C1482.Angle=360.00 
App.ActiveDocument.C1482.Placement=Base.Placement(Base.Vector(-63.232587,-112.259813,497.472734),Base.Rotation(-0.559717,-0.486845,0.000000,0.670596))
App.ActiveDocument.addObject("Part::Cylinder","C1483")
App.ActiveDocument.C1483.Radius=0.750000
App.ActiveDocument.C1483.Height=15.00
App.ActiveDocument.C1483.Angle=360.00 
App.ActiveDocument.C1483.Placement=Base.Placement(Base.Vector(-63.226265,-112.724149,494.608804),Base.Rotation(-0.562040,-0.504023,0.000000,0.655799))
App.ActiveDocument.addObject("Part::Cylinder","C1484")
App.ActiveDocument.C1484.Radius=0.750000
App.ActiveDocument.C1484.Height=15.00
App.ActiveDocument.C1484.Angle=360.00 
App.ActiveDocument.C1484.Placement=Base.Placement(Base.Vector(-63.043603,-113.198849,491.753046),Base.Rotation(-0.564009,-0.523646,0.000000,0.638505))
App.ActiveDocument.addObject("Part::Cylinder","C1485")
App.ActiveDocument.C1485.Radius=0.750000
App.ActiveDocument.C1485.Height=15.00
App.ActiveDocument.C1485.Angle=360.00 
App.ActiveDocument.C1485.Placement=Base.Placement(Base.Vector(-62.947226,-113.888075,489.019755),Base.Rotation(-0.562651,-0.543558,0.000000,0.622871))
App.ActiveDocument.addObject("Part::Cylinder","C1486")
App.ActiveDocument.C1486.Radius=0.750000
App.ActiveDocument.C1486.Height=15.00
App.ActiveDocument.C1486.Angle=360.00 
App.ActiveDocument.C1486.Placement=Base.Placement(Base.Vector(-62.747141,-114.650506,486.276928),Base.Rotation(-0.557992,-0.563937,0.000000,0.608786))
App.ActiveDocument.addObject("Part::Cylinder","C1487")
App.ActiveDocument.C1487.Radius=0.750000
App.ActiveDocument.C1487.Height=15.00
App.ActiveDocument.C1487.Angle=360.00 
App.ActiveDocument.C1487.Placement=Base.Placement(Base.Vector(-62.671351,-115.662194,483.677864),Base.Rotation(-0.549358,-0.589066,0.000000,0.592627))
App.ActiveDocument.addObject("Part::Cylinder","C1488")
App.ActiveDocument.C1488.Radius=0.750000
App.ActiveDocument.C1488.Height=15.00
App.ActiveDocument.C1488.Angle=360.00 
App.ActiveDocument.C1488.Placement=Base.Placement(Base.Vector(-62.455301,-116.737878,481.036744),Base.Rotation(-0.536511,-0.615691,0.000000,0.577131))
App.ActiveDocument.addObject("Part::Cylinder","C1489")
App.ActiveDocument.C1489.Radius=0.750000
App.ActiveDocument.C1489.Height=15.00
App.ActiveDocument.C1489.Angle=360.00 
App.ActiveDocument.C1489.Placement=Base.Placement(Base.Vector(-62.237307,-117.891119,478.624006),Base.Rotation(-0.520558,-0.642834,0.000000,0.561947))
App.ActiveDocument.addObject("Part::Cylinder","C1490")
App.ActiveDocument.C1490.Radius=0.750000
App.ActiveDocument.C1490.Height=15.00
App.ActiveDocument.C1490.Angle=360.00 
App.ActiveDocument.C1490.Placement=Base.Placement(Base.Vector(-61.988817,-119.107608,476.379244),Base.Rotation(-0.496646,-0.675527,0.000000,0.544982))
App.ActiveDocument.addObject("Part::Cylinder","C1491")
App.ActiveDocument.C1491.Radius=0.750000
App.ActiveDocument.C1491.Height=15.00
App.ActiveDocument.C1491.Angle=360.00 
App.ActiveDocument.C1491.Placement=Base.Placement(Base.Vector(-61.733421,-120.614226,474.069297),Base.Rotation(-0.472959,-0.702832,0.000000,0.531354))
App.ActiveDocument.addObject("Part::Cylinder","C1492")
App.ActiveDocument.C1492.Radius=0.750000
App.ActiveDocument.C1492.Height=15.00
App.ActiveDocument.C1492.Angle=360.00 
App.ActiveDocument.C1492.Placement=Base.Placement(Base.Vector(-61.548127,-121.983634,472.342537),Base.Rotation(-0.435950,-0.739178,0.000000,0.513384))
App.ActiveDocument.addObject("Part::Cylinder","C1493")
App.ActiveDocument.C1493.Radius=0.750000
App.ActiveDocument.C1493.Height=15.00
App.ActiveDocument.C1493.Angle=360.00 
App.ActiveDocument.C1493.Placement=Base.Placement(Base.Vector(-61.498220,-123.790029,470.718569),Base.Rotation(-0.393846,-0.775075,0.000000,0.494110))
App.ActiveDocument.addObject("Part::Cylinder","C1494")
App.ActiveDocument.C1494.Radius=0.750000
App.ActiveDocument.C1494.Height=15.00
App.ActiveDocument.C1494.Angle=360.00 
App.ActiveDocument.C1494.Placement=Base.Placement(Base.Vector(-61.061055,-125.546500,468.904192),Base.Rotation(-0.336096,-0.814104,0.000000,0.473575))
App.ActiveDocument.addObject("Part::Cylinder","C1495")
App.ActiveDocument.C1495.Radius=0.750000
App.ActiveDocument.C1495.Height=15.00
App.ActiveDocument.C1495.Angle=360.00 
App.ActiveDocument.C1495.Placement=Base.Placement(Base.Vector(-59.951026,-126.637265,466.824742),Base.Rotation(-0.271604,-0.844813,0.000000,0.461002))
App.ActiveDocument.addObject("Part::Cylinder","C1496")
App.ActiveDocument.C1496.Radius=0.750000
App.ActiveDocument.C1496.Height=15.00
App.ActiveDocument.C1496.Angle=360.00 
App.ActiveDocument.C1496.Placement=Base.Placement(Base.Vector(-64.615693,-137.630389,532.325601),Base.Rotation(-0.030070,-0.375805,0.000000,0.926211))
App.ActiveDocument.addObject("Part::Cylinder","C1497")
App.ActiveDocument.C1497.Radius=0.750000
App.ActiveDocument.C1497.Height=15.00
App.ActiveDocument.C1497.Angle=360.00 
App.ActiveDocument.C1497.Placement=Base.Placement(Base.Vector(-64.398511,-134.409996,532.146478),Base.Rotation(-0.063929,-0.375022,0.000000,0.924809))
App.ActiveDocument.addObject("Part::Cylinder","C1498")
App.ActiveDocument.C1498.Radius=0.750000
App.ActiveDocument.C1498.Height=15.00
App.ActiveDocument.C1498.Angle=360.00 
App.ActiveDocument.C1498.Placement=Base.Placement(Base.Vector(-64.521004,-131.295412,531.351766),Base.Rotation(-0.103682,-0.378209,0.000000,0.919896))
App.ActiveDocument.addObject("Part::Cylinder","C1499")
App.ActiveDocument.C1499.Radius=0.750000
App.ActiveDocument.C1499.Height=15.00
App.ActiveDocument.C1499.Angle=360.00 
App.ActiveDocument.C1499.Placement=Base.Placement(Base.Vector(-64.609369,-128.419053,530.313172),Base.Rotation(-0.141513,-0.381880,0.000000,0.913314))
App.ActiveDocument.addObject("Part::Cylinder","C1500")
App.ActiveDocument.C1500.Radius=0.750000
App.ActiveDocument.C1500.Height=15.00
App.ActiveDocument.C1500.Angle=360.00 
App.ActiveDocument.C1500.Placement=Base.Placement(Base.Vector(-64.744084,-125.846388,528.978444),Base.Rotation(-0.182433,-0.387168,0.000000,0.903780))
App.ActiveDocument.addObject("Part::Cylinder","C1501")
App.ActiveDocument.C1501.Radius=0.750000
App.ActiveDocument.C1501.Height=15.00
App.ActiveDocument.C1501.Angle=360.00 
App.ActiveDocument.C1501.Placement=Base.Placement(Base.Vector(-64.892563,-123.570744,527.396184),Base.Rotation(-0.230506,-0.392672,0.000000,0.890323))
App.ActiveDocument.addObject("Part::Cylinder","C1502")
App.ActiveDocument.C1502.Radius=0.750000
App.ActiveDocument.C1502.Height=15.00
App.ActiveDocument.C1502.Angle=360.00 
App.ActiveDocument.C1502.Placement=Base.Placement(Base.Vector(-65.080429,-121.596380,525.565869),Base.Rotation(-0.275683,-0.399513,0.000000,0.874293))
App.ActiveDocument.addObject("Part::Cylinder","C1503")
App.ActiveDocument.C1503.Radius=0.750000
App.ActiveDocument.C1503.Height=15.00
App.ActiveDocument.C1503.Angle=360.00 
App.ActiveDocument.C1503.Placement=Base.Placement(Base.Vector(-65.155756,-119.861252,523.671528),Base.Rotation(-0.319481,-0.402841,0.000000,0.857701))
App.ActiveDocument.addObject("Part::Cylinder","C1504")
App.ActiveDocument.C1504.Radius=0.750000
App.ActiveDocument.C1504.Height=15.00
App.ActiveDocument.C1504.Angle=360.00 
App.ActiveDocument.C1504.Placement=Base.Placement(Base.Vector(-65.441974,-118.441777,521.343387),Base.Rotation(-0.360495,-0.411620,0.000000,0.837026))
App.ActiveDocument.addObject("Part::Cylinder","C1505")
App.ActiveDocument.C1505.Radius=0.750000
App.ActiveDocument.C1505.Height=15.00
App.ActiveDocument.C1505.Angle=360.00 
App.ActiveDocument.C1505.Placement=Base.Placement(Base.Vector(-65.737218,-117.323197,518.907200),Base.Rotation(-0.396616,-0.417967,0.000000,0.817313))
App.ActiveDocument.addObject("Part::Cylinder","C1506")
App.ActiveDocument.C1506.Radius=0.750000
App.ActiveDocument.C1506.Height=15.00
App.ActiveDocument.C1506.Angle=360.00 
App.ActiveDocument.C1506.Placement=Base.Placement(Base.Vector(-65.952223,-116.388547,516.367500),Base.Rotation(-0.428155,-0.427963,0.000000,0.795946))
App.ActiveDocument.addObject("Part::Cylinder","C1507")
App.ActiveDocument.C1507.Radius=0.750000
App.ActiveDocument.C1507.Height=15.00
App.ActiveDocument.C1507.Angle=360.00 
App.ActiveDocument.C1507.Placement=Base.Placement(Base.Vector(-66.005957,-115.572713,513.819117),Base.Rotation(-0.455102,-0.435914,0.000000,0.776441))
App.ActiveDocument.addObject("Part::Cylinder","C1508")
App.ActiveDocument.C1508.Radius=0.750000
App.ActiveDocument.C1508.Height=15.00
App.ActiveDocument.C1508.Angle=360.00 
App.ActiveDocument.C1508.Placement=Base.Placement(Base.Vector(-66.167962,-115.087378,511.209931),Base.Rotation(-0.477578,-0.445108,0.000000,0.757495))
App.ActiveDocument.addObject("Part::Cylinder","C1509")
App.ActiveDocument.C1509.Radius=0.750000
App.ActiveDocument.C1509.Height=15.00
App.ActiveDocument.C1509.Angle=360.00 
App.ActiveDocument.C1509.Placement=Base.Placement(Base.Vector(-66.132338,-114.655182,508.765198),Base.Rotation(-0.498309,-0.454895,0.000000,0.738078))
App.ActiveDocument.addObject("Part::Cylinder","C1510")
App.ActiveDocument.C1510.Radius=0.750000
App.ActiveDocument.C1510.Height=15.00
App.ActiveDocument.C1510.Angle=360.00 
App.ActiveDocument.C1510.Placement=Base.Placement(Base.Vector(-66.074359,-114.367667,506.137081),Base.Rotation(-0.514328,-0.464486,0.000000,0.720916))
App.ActiveDocument.addObject("Part::Cylinder","C1511")
App.ActiveDocument.C1511.Radius=0.750000
App.ActiveDocument.C1511.Height=15.00
App.ActiveDocument.C1511.Angle=360.00 
App.ActiveDocument.C1511.Placement=Base.Placement(Base.Vector(-65.992422,-114.242050,503.319877),Base.Rotation(-0.528353,-0.477018,0.000000,0.702351))
App.ActiveDocument.addObject("Part::Cylinder","C1512")
App.ActiveDocument.C1512.Radius=0.750000
App.ActiveDocument.C1512.Height=15.00
App.ActiveDocument.C1512.Angle=360.00 
App.ActiveDocument.C1512.Placement=Base.Placement(Base.Vector(-66.197511,-114.560344,500.647038),Base.Rotation(-0.536578,-0.492035,0.000000,0.685555))
App.ActiveDocument.addObject("Part::Cylinder","C1513")
App.ActiveDocument.C1513.Radius=0.750000
App.ActiveDocument.C1513.Height=15.00
App.ActiveDocument.C1513.Angle=360.00 
App.ActiveDocument.C1513.Placement=Base.Placement(Base.Vector(-65.980349,-114.707120,497.676125),Base.Rotation(-0.545244,-0.507358,0.000000,0.667305))
App.ActiveDocument.addObject("Part::Cylinder","C1514")
App.ActiveDocument.C1514.Radius=0.750000
App.ActiveDocument.C1514.Height=15.00
App.ActiveDocument.C1514.Angle=360.00 
App.ActiveDocument.C1514.Placement=Base.Placement(Base.Vector(-65.880035,-115.109674,494.953823),Base.Rotation(-0.549657,-0.524141,0.000000,0.650502))
App.ActiveDocument.addObject("Part::Cylinder","C1515")
App.ActiveDocument.C1515.Radius=0.750000
App.ActiveDocument.C1515.Height=15.00
App.ActiveDocument.C1515.Angle=360.00 
App.ActiveDocument.C1515.Placement=Base.Placement(Base.Vector(-65.766556,-115.656415,492.299622),Base.Rotation(-0.551130,-0.542348,0.000000,0.634124))
App.ActiveDocument.addObject("Part::Cylinder","C1516")
App.ActiveDocument.C1516.Radius=0.750000
App.ActiveDocument.C1516.Height=15.00
App.ActiveDocument.C1516.Angle=360.00 
App.ActiveDocument.C1516.Placement=Base.Placement(Base.Vector(-65.650811,-116.320617,489.798719),Base.Rotation(-0.549813,-0.561174,0.000000,0.618700))
App.ActiveDocument.addObject("Part::Cylinder","C1517")
App.ActiveDocument.C1517.Radius=0.750000
App.ActiveDocument.C1517.Height=15.00
App.ActiveDocument.C1517.Angle=360.00 
App.ActiveDocument.C1517.Placement=Base.Placement(Base.Vector(-65.551756,-117.163273,487.309074),Base.Rotation(-0.545544,-0.582315,0.000000,0.602736))
App.ActiveDocument.addObject("Part::Cylinder","C1518")
App.ActiveDocument.C1518.Radius=0.750000
App.ActiveDocument.C1518.Height=15.00
App.ActiveDocument.C1518.Angle=360.00 
App.ActiveDocument.C1518.Placement=Base.Placement(Base.Vector(-65.328743,-118.024879,484.870034),Base.Rotation(-0.538636,-0.604198,0.000000,0.587210))
App.ActiveDocument.addObject("Part::Cylinder","C1519")
App.ActiveDocument.C1519.Radius=0.750000
App.ActiveDocument.C1519.Height=15.00
App.ActiveDocument.C1519.Angle=360.00 
App.ActiveDocument.C1519.Placement=Base.Placement(Base.Vector(-65.164116,-119.183675,482.359982),Base.Rotation(-0.527244,-0.630267,0.000000,0.569892))
App.ActiveDocument.addObject("Part::Cylinder","C1520")
App.ActiveDocument.C1520.Radius=0.750000
App.ActiveDocument.C1520.Height=15.00
App.ActiveDocument.C1520.Angle=360.00 
App.ActiveDocument.C1520.Placement=Base.Placement(Base.Vector(-64.922042,-120.312800,480.108871),Base.Rotation(-0.511639,-0.658252,0.000000,0.552204))
App.ActiveDocument.addObject("Part::Cylinder","C1521")
App.ActiveDocument.C1521.Radius=0.750000
App.ActiveDocument.C1521.Height=15.00
App.ActiveDocument.C1521.Angle=360.00 
App.ActiveDocument.C1521.Placement=Base.Placement(Base.Vector(-64.688068,-121.617564,477.938102),Base.Rotation(-0.493620,-0.685020,0.000000,0.535805))
App.ActiveDocument.addObject("Part::Cylinder","C1522")
App.ActiveDocument.C1522.Radius=0.750000
App.ActiveDocument.C1522.Height=15.00
App.ActiveDocument.C1522.Angle=360.00 
App.ActiveDocument.C1522.Placement=Base.Placement(Base.Vector(-64.412907,-123.077494,475.832572),Base.Rotation(-0.469577,-0.715331,0.000000,0.517493))
App.ActiveDocument.addObject("Part::Cylinder","C1523")
App.ActiveDocument.C1523.Radius=0.750000
App.ActiveDocument.C1523.Height=15.00
App.ActiveDocument.C1523.Angle=360.00 
App.ActiveDocument.C1523.Placement=Base.Placement(Base.Vector(-64.100579,-124.509875,474.000316),Base.Rotation(-0.437559,-0.749607,0.000000,0.496620))
App.ActiveDocument.addObject("Part::Cylinder","C1524")
App.ActiveDocument.C1524.Radius=0.750000
App.ActiveDocument.C1524.Height=15.00
App.ActiveDocument.C1524.Angle=360.00 
App.ActiveDocument.C1524.Placement=Base.Placement(Base.Vector(-64.322164,-126.985621,472.436015),Base.Rotation(-0.398488,-0.788388,0.000000,0.468670))
App.ActiveDocument.addObject("Part::Cylinder","C1525")
App.ActiveDocument.C1525.Radius=0.750000
App.ActiveDocument.C1525.Height=15.00
App.ActiveDocument.C1525.Angle=360.00 
App.ActiveDocument.C1525.Placement=Base.Placement(Base.Vector(-63.551532,-128.967557,470.347108),Base.Rotation(-0.330173,-0.835840,0.000000,0.438587))
App.ActiveDocument.addObject("Part::Cylinder","C1526")
App.ActiveDocument.C1526.Radius=0.750000
App.ActiveDocument.C1526.Height=15.00
App.ActiveDocument.C1526.Angle=360.00 
App.ActiveDocument.C1526.Placement=Base.Placement(Base.Vector(-61.961776,-130.023235,468.078493),Base.Rotation(-0.241565,-0.875384,0.000000,0.418747))
App.ActiveDocument.addObject("Part::Cylinder","C1527")
App.ActiveDocument.C1527.Radius=0.750000
App.ActiveDocument.C1527.Height=15.00
App.ActiveDocument.C1527.Angle=360.00 
App.ActiveDocument.C1527.Placement=Base.Placement(Base.Vector(-67.083845,-137.702977,529.813098),Base.Rotation(-0.031626,-0.398080,0.000000,0.916805))
App.ActiveDocument.addObject("Part::Cylinder","C1528")
App.ActiveDocument.C1528.Radius=0.750000
App.ActiveDocument.C1528.Height=15.00
App.ActiveDocument.C1528.Angle=360.00 
App.ActiveDocument.C1528.Placement=Base.Placement(Base.Vector(-66.843289,-134.471356,529.650889),Base.Rotation(-0.066031,-0.397151,0.000000,0.915375))
App.ActiveDocument.addObject("Part::Cylinder","C1529")
App.ActiveDocument.C1529.Radius=0.750000
App.ActiveDocument.C1529.Height=15.00
App.ActiveDocument.C1529.Angle=360.00 
App.ActiveDocument.C1529.Placement=Base.Placement(Base.Vector(-67.037863,-131.419875,528.722188),Base.Rotation(-0.106688,-0.401759,0.000000,0.909510))
App.ActiveDocument.addObject("Part::Cylinder","C1530")
App.ActiveDocument.C1530.Radius=0.750000
App.ActiveDocument.C1530.Height=15.00
App.ActiveDocument.C1530.Angle=360.00 
App.ActiveDocument.C1530.Placement=Base.Placement(Base.Vector(-67.166266,-128.653992,527.576511),Base.Rotation(-0.150632,-0.406608,0.000000,0.901099))
App.ActiveDocument.addObject("Part::Cylinder","C1531")
App.ActiveDocument.C1531.Radius=0.750000
App.ActiveDocument.C1531.Height=15.00
App.ActiveDocument.C1531.Angle=360.00 
App.ActiveDocument.C1531.Placement=Base.Placement(Base.Vector(-67.278038,-126.165335,526.170431),Base.Rotation(-0.200846,-0.411313,0.000000,0.889091))
App.ActiveDocument.addObject("Part::Cylinder","C1532")
App.ActiveDocument.C1532.Radius=0.750000
App.ActiveDocument.C1532.Height=15.00
App.ActiveDocument.C1532.Angle=360.00 
App.ActiveDocument.C1532.Placement=Base.Placement(Base.Vector(-67.578480,-124.080176,524.334987),Base.Rotation(-0.246471,-0.417760,0.000000,0.874488))
App.ActiveDocument.addObject("Part::Cylinder","C1533")
App.ActiveDocument.C1533.Radius=0.750000
App.ActiveDocument.C1533.Height=15.00
App.ActiveDocument.C1533.Angle=360.00 
App.ActiveDocument.C1533.Placement=Base.Placement(Base.Vector(-67.677955,-122.180283,522.443985),Base.Rotation(-0.287925,-0.424724,0.000000,0.858317))
App.ActiveDocument.addObject("Part::Cylinder","C1534")
App.ActiveDocument.C1534.Radius=0.750000
App.ActiveDocument.C1534.Height=15.00
App.ActiveDocument.C1534.Angle=360.00 
App.ActiveDocument.C1534.Placement=Base.Placement(Base.Vector(-67.936952,-120.862125,520.460207),Base.Rotation(-0.328315,-0.431328,0.000000,0.840336))
App.ActiveDocument.addObject("Part::Cylinder","C1535")
App.ActiveDocument.C1535.Radius=0.750000
App.ActiveDocument.C1535.Height=15.00
App.ActiveDocument.C1535.Angle=360.00 
App.ActiveDocument.C1535.Placement=Base.Placement(Base.Vector(-68.261441,-119.796918,518.230777),Base.Rotation(-0.364008,-0.439706,0.000000,0.821070))
App.ActiveDocument.addObject("Part::Cylinder","C1536")
App.ActiveDocument.C1536.Radius=0.750000
App.ActiveDocument.C1536.Height=15.00
App.ActiveDocument.C1536.Angle=360.00 
App.ActiveDocument.C1536.Placement=Base.Placement(Base.Vector(-68.476330,-118.835439,515.836940),Base.Rotation(-0.400263,-0.447533,0.000000,0.799689))
App.ActiveDocument.addObject("Part::Cylinder","C1537")
App.ActiveDocument.C1537.Radius=0.750000
App.ActiveDocument.C1537.Height=15.00
App.ActiveDocument.C1537.Angle=360.00 
App.ActiveDocument.C1537.Placement=Base.Placement(Base.Vector(-68.622735,-118.062817,513.367542),Base.Rotation(-0.431260,-0.455993,0.000000,0.778515))
App.ActiveDocument.addObject("Part::Cylinder","C1538")
App.ActiveDocument.C1538.Radius=0.750000
App.ActiveDocument.C1538.Height=15.00
App.ActiveDocument.C1538.Angle=360.00 
App.ActiveDocument.C1538.Placement=Base.Placement(Base.Vector(-68.757765,-117.509066,510.760838),Base.Rotation(-0.456608,-0.463792,0.000000,0.759214))
App.ActiveDocument.addObject("Part::Cylinder","C1539")
App.ActiveDocument.C1539.Radius=0.750000
App.ActiveDocument.C1539.Height=15.00
App.ActiveDocument.C1539.Angle=360.00 
App.ActiveDocument.C1539.Placement=Base.Placement(Base.Vector(-68.812821,-117.131505,508.208174),Base.Rotation(-0.478896,-0.474528,0.000000,0.738567))
App.ActiveDocument.addObject("Part::Cylinder","C1540")
App.ActiveDocument.C1540.Radius=0.750000
App.ActiveDocument.C1540.Height=15.00
App.ActiveDocument.C1540.Angle=360.00 
App.ActiveDocument.C1540.Placement=Base.Placement(Base.Vector(-68.696071,-116.799983,505.727560),Base.Rotation(-0.499343,-0.483404,0.000000,0.719011))
App.ActiveDocument.addObject("Part::Cylinder","C1541")
App.ActiveDocument.C1541.Radius=0.750000
App.ActiveDocument.C1541.Height=15.00
App.ActiveDocument.C1541.Angle=360.00 
App.ActiveDocument.C1541.Placement=Base.Placement(Base.Vector(-68.607876,-116.681277,503.227929),Base.Rotation(-0.513956,-0.494616,0.000000,0.700860))
App.ActiveDocument.addObject("Part::Cylinder","C1542")
App.ActiveDocument.C1542.Radius=0.750000
App.ActiveDocument.C1542.Height=15.00
App.ActiveDocument.C1542.Angle=360.00 
App.ActiveDocument.C1542.Placement=Base.Placement(Base.Vector(-68.785888,-116.988856,500.776606),Base.Rotation(-0.522396,-0.508045,0.000000,0.684830))
App.ActiveDocument.addObject("Part::Cylinder","C1543")
App.ActiveDocument.C1543.Radius=0.750000
App.ActiveDocument.C1543.Height=15.00
App.ActiveDocument.C1543.Angle=360.00 
App.ActiveDocument.C1543.Placement=Base.Placement(Base.Vector(-68.766727,-117.312858,498.046399),Base.Rotation(-0.532893,-0.522827,0.000000,0.665340))
App.ActiveDocument.addObject("Part::Cylinder","C1544")
App.ActiveDocument.C1544.Radius=0.750000
App.ActiveDocument.C1544.Height=15.00
App.ActiveDocument.C1544.Angle=360.00 
App.ActiveDocument.C1544.Placement=Base.Placement(Base.Vector(-68.540684,-117.627134,495.316350),Base.Rotation(-0.539545,-0.539939,0.000000,0.646032))
App.ActiveDocument.addObject("Part::Cylinder","C1545")
App.ActiveDocument.C1545.Radius=0.750000
App.ActiveDocument.C1545.Height=15.00
App.ActiveDocument.C1545.Angle=360.00 
App.ActiveDocument.C1545.Placement=Base.Placement(Base.Vector(-68.345497,-118.131259,492.700570),Base.Rotation(-0.542458,-0.555568,0.000000,0.630146))
App.ActiveDocument.addObject("Part::Cylinder","C1546")
App.ActiveDocument.C1546.Radius=0.750000
App.ActiveDocument.C1546.Height=15.00
App.ActiveDocument.C1546.Angle=360.00 
App.ActiveDocument.C1546.Placement=Base.Placement(Base.Vector(-68.255394,-118.898605,490.174979),Base.Rotation(-0.542637,-0.574703,0.000000,0.612586))
App.ActiveDocument.addObject("Part::Cylinder","C1547")
App.ActiveDocument.C1547.Radius=0.750000
App.ActiveDocument.C1547.Height=15.00
App.ActiveDocument.C1547.Angle=360.00 
App.ActiveDocument.C1547.Placement=Base.Placement(Base.Vector(-68.263161,-119.798097,488.022516),Base.Rotation(-0.539939,-0.594656,0.000000,0.595692))
App.ActiveDocument.addObject("Part::Cylinder","C1548")
App.ActiveDocument.C1548.Radius=0.750000
App.ActiveDocument.C1548.Height=15.00
App.ActiveDocument.C1548.Angle=360.00 
App.ActiveDocument.C1548.Placement=Base.Placement(Base.Vector(-68.250717,-120.836719,485.873949),Base.Rotation(-0.535011,-0.614870,0.000000,0.579395))
App.ActiveDocument.addObject("Part::Cylinder","C1549")
App.ActiveDocument.C1549.Radius=0.750000
App.ActiveDocument.C1549.Height=15.00
App.ActiveDocument.C1549.Angle=360.00 
App.ActiveDocument.C1549.Placement=Base.Placement(Base.Vector(-67.909847,-121.789228,483.529685),Base.Rotation(-0.526376,-0.638560,0.000000,0.561399))
App.ActiveDocument.addObject("Part::Cylinder","C1550")
App.ActiveDocument.C1550.Radius=0.750000
App.ActiveDocument.C1550.Height=15.00
App.ActiveDocument.C1550.Angle=360.00 
App.ActiveDocument.C1550.Placement=Base.Placement(Base.Vector(-67.583074,-122.901452,481.291303),Base.Rotation(-0.514907,-0.663102,0.000000,0.543292))
App.ActiveDocument.addObject("Part::Cylinder","C1551")
App.ActiveDocument.C1551.Radius=0.750000
App.ActiveDocument.C1551.Height=15.00
App.ActiveDocument.C1551.Angle=360.00 
App.ActiveDocument.C1551.Placement=Base.Placement(Base.Vector(-67.317278,-124.214966,479.204192),Base.Rotation(-0.496722,-0.692863,0.000000,0.522692))
App.ActiveDocument.addObject("Part::Cylinder","C1552")
App.ActiveDocument.C1552.Radius=0.750000
App.ActiveDocument.C1552.Height=15.00
App.ActiveDocument.C1552.Angle=360.00 
App.ActiveDocument.C1552.Placement=Base.Placement(Base.Vector(-67.211608,-125.681188,477.485523),Base.Rotation(-0.478813,-0.719069,0.000000,0.503664))
App.ActiveDocument.addObject("Part::Cylinder","C1553")
App.ActiveDocument.C1553.Radius=0.750000
App.ActiveDocument.C1553.Height=15.00
App.ActiveDocument.C1553.Angle=360.00 
App.ActiveDocument.C1553.Placement=Base.Placement(Base.Vector(-66.796702,-127.175945,475.573514),Base.Rotation(-0.449761,-0.753796,0.000000,0.479068))
App.ActiveDocument.addObject("Part::Cylinder","C1554")
App.ActiveDocument.C1554.Radius=0.750000
App.ActiveDocument.C1554.Height=15.00
App.ActiveDocument.C1554.Angle=360.00 
App.ActiveDocument.C1554.Placement=Base.Placement(Base.Vector(-67.202938,-129.927795,474.156773),Base.Rotation(-0.404495,-0.798675,0.000000,0.445535))
App.ActiveDocument.addObject("Part::Cylinder","C1555")
App.ActiveDocument.C1555.Radius=0.750000
App.ActiveDocument.C1555.Height=15.00
App.ActiveDocument.C1555.Angle=360.00 
App.ActiveDocument.C1555.Placement=Base.Placement(Base.Vector(-66.245992,-131.943811,472.038194),Base.Rotation(-0.336544,-0.845516,0.000000,0.414536))
App.ActiveDocument.addObject("Part::Cylinder","C1556")
App.ActiveDocument.C1556.Radius=0.750000
App.ActiveDocument.C1556.Height=15.00
App.ActiveDocument.C1556.Angle=360.00 
App.ActiveDocument.C1556.Placement=Base.Placement(Base.Vector(-64.372044,-133.100342,469.712467),Base.Rotation(-0.251440,-0.885979,0.000000,0.389639))
App.ActiveDocument.addObject("Part::Cylinder","C1557")
App.ActiveDocument.C1557.Radius=0.750000
App.ActiveDocument.C1557.Height=15.00
App.ActiveDocument.C1557.Angle=360.00 
App.ActiveDocument.C1557.Placement=Base.Placement(Base.Vector(-69.395631,-137.732151,527.210061),Base.Rotation(-0.032796,-0.421374,0.000000,0.906294))
App.ActiveDocument.addObject("Part::Cylinder","C1558")
App.ActiveDocument.C1558.Radius=0.750000
App.ActiveDocument.C1558.Height=15.00
App.ActiveDocument.C1558.Angle=360.00 
App.ActiveDocument.C1558.Placement=Base.Placement(Base.Vector(-69.229571,-134.485008,526.945749),Base.Rotation(-0.069425,-0.421009,0.000000,0.904396))
App.ActiveDocument.addObject("Part::Cylinder","C1559")
App.ActiveDocument.C1559.Radius=0.750000
App.ActiveDocument.C1559.Height=15.00
App.ActiveDocument.C1559.Angle=360.00 
App.ActiveDocument.C1559.Placement=Base.Placement(Base.Vector(-69.417949,-131.580403,525.962824),Base.Rotation(-0.111437,-0.426306,0.000000,0.897689))
App.ActiveDocument.addObject("Part::Cylinder","C1560")
App.ActiveDocument.C1560.Radius=0.750000
App.ActiveDocument.C1560.Height=15.00
App.ActiveDocument.C1560.Angle=360.00 
App.ActiveDocument.C1560.Placement=Base.Placement(Base.Vector(-69.558742,-128.908192,524.714168),Base.Rotation(-0.158278,-0.431304,0.000000,0.888215))
App.ActiveDocument.addObject("Part::Cylinder","C1561")
App.ActiveDocument.C1561.Radius=0.750000
App.ActiveDocument.C1561.Height=15.00
App.ActiveDocument.C1561.Angle=360.00 
App.ActiveDocument.C1561.Placement=Base.Placement(Base.Vector(-69.759824,-126.683103,523.174899),Base.Rotation(-0.202129,-0.436858,0.000000,0.876527))
App.ActiveDocument.addObject("Part::Cylinder","C1562")
App.ActiveDocument.C1562.Radius=0.750000
App.ActiveDocument.C1562.Height=15.00
App.ActiveDocument.C1562.Angle=360.00 
App.ActiveDocument.C1562.Placement=Base.Placement(Base.Vector(-69.983995,-124.819570,521.397329),Base.Rotation(-0.249822,-0.444096,0.000000,0.860446))
App.ActiveDocument.addObject("Part::Cylinder","C1563")
App.ActiveDocument.C1563.Radius=0.750000
App.ActiveDocument.C1563.Height=15.00
App.ActiveDocument.C1563.Angle=360.00 
App.ActiveDocument.C1563.Placement=Base.Placement(Base.Vector(-70.338167,-123.385504,519.337198),Base.Rotation(-0.291168,-0.451852,0.000000,0.843238))
App.ActiveDocument.addObject("Part::Cylinder","C1564")
App.ActiveDocument.C1564.Radius=0.750000
App.ActiveDocument.C1564.Height=15.00
App.ActiveDocument.C1564.Angle=360.00 
App.ActiveDocument.C1564.Placement=Base.Placement(Base.Vector(-70.611930,-122.226630,517.256331),Base.Rotation(-0.332015,-0.461151,0.000000,0.822864))
App.ActiveDocument.addObject("Part::Cylinder","C1565")
App.ActiveDocument.C1565.Radius=0.750000
App.ActiveDocument.C1565.Height=15.00
App.ActiveDocument.C1565.Angle=360.00 
App.ActiveDocument.C1565.Placement=Base.Placement(Base.Vector(-70.874717,-121.310981,515.031989),Base.Rotation(-0.368466,-0.466996,0.000000,0.803833))
App.ActiveDocument.addObject("Part::Cylinder","C1566")
App.ActiveDocument.C1566.Radius=0.750000
App.ActiveDocument.C1566.Height=15.00
App.ActiveDocument.C1566.Angle=360.00 
App.ActiveDocument.C1566.Placement=Base.Placement(Base.Vector(-71.111242,-120.598416,512.645139),Base.Rotation(-0.402286,-0.476035,0.000000,0.782021))
App.ActiveDocument.addObject("Part::Cylinder","C1567")
App.ActiveDocument.C1567.Radius=0.750000
App.ActiveDocument.C1567.Height=15.00
App.ActiveDocument.C1567.Angle=360.00 
App.ActiveDocument.C1567.Placement=Base.Placement(Base.Vector(-71.143215,-119.916997,510.207059),Base.Rotation(-0.434389,-0.484454,0.000000,0.759349))
App.ActiveDocument.addObject("Part::Cylinder","C1568")
App.ActiveDocument.C1568.Radius=0.750000
App.ActiveDocument.C1568.Height=15.00
App.ActiveDocument.C1568.Angle=360.00 
App.ActiveDocument.C1568.Placement=Base.Placement(Base.Vector(-71.437041,-119.770706,507.700873),Base.Rotation(-0.454409,-0.494186,0.000000,0.741143))
App.ActiveDocument.addObject("Part::Cylinder","C1569")
App.ActiveDocument.C1569.Radius=0.750000
App.ActiveDocument.C1569.Height=15.00
App.ActiveDocument.C1569.Angle=360.00 
App.ActiveDocument.C1569.Placement=Base.Placement(Base.Vector(-71.257196,-119.346611,505.127301),Base.Rotation(-0.481847,-0.502989,0.000000,0.717514))
App.ActiveDocument.addObject("Part::Cylinder","C1570")
App.ActiveDocument.C1570.Radius=0.750000
App.ActiveDocument.C1570.Height=15.00
App.ActiveDocument.C1570.Angle=360.00 
App.ActiveDocument.C1570.Placement=Base.Placement(Base.Vector(-71.009423,-119.077344,502.728249),Base.Rotation(-0.499469,-0.512159,0.000000,0.698730))
App.ActiveDocument.addObject("Part::Cylinder","C1571")
App.ActiveDocument.C1571.Radius=0.750000
App.ActiveDocument.C1571.Height=15.00
App.ActiveDocument.C1571.Angle=360.00 
App.ActiveDocument.C1571.Placement=Base.Placement(Base.Vector(-71.653588,-119.975909,499.812962),Base.Rotation(-0.508685,-0.530461,0.000000,0.678123))
App.ActiveDocument.addObject("Part::Cylinder","C1572")
App.ActiveDocument.C1572.Radius=0.750000
App.ActiveDocument.C1572.Height=15.00
App.ActiveDocument.C1572.Angle=360.00 
App.ActiveDocument.C1572.Placement=Base.Placement(Base.Vector(-71.324715,-120.129414,496.835464),Base.Rotation(-0.524277,-0.546218,0.000000,0.653284))
App.ActiveDocument.addObject("Part::Cylinder","C1573")
App.ActiveDocument.C1573.Radius=0.750000
App.ActiveDocument.C1573.Height=15.00
App.ActiveDocument.C1573.Angle=360.00 
App.ActiveDocument.C1573.Placement=Base.Placement(Base.Vector(-71.229072,-120.782550,493.876945),Base.Rotation(-0.531497,-0.564724,0.000000,0.631346))
App.ActiveDocument.addObject("Part::Cylinder","C1574")
App.ActiveDocument.C1574.Radius=0.750000
App.ActiveDocument.C1574.Height=15.00
App.ActiveDocument.C1574.Angle=360.00 
App.ActiveDocument.C1574.Placement=Base.Placement(Base.Vector(-71.027439,-121.510165,491.130839),Base.Rotation(-0.535473,-0.583823,0.000000,0.610262))
App.ActiveDocument.addObject("Part::Cylinder","C1575")
App.ActiveDocument.C1575.Radius=0.750000
App.ActiveDocument.C1575.Height=15.00
App.ActiveDocument.C1575.Angle=360.00 
App.ActiveDocument.C1575.Placement=Base.Placement(Base.Vector(-70.897342,-122.436754,488.662479),Base.Rotation(-0.534927,-0.603941,0.000000,0.590855))
App.ActiveDocument.addObject("Part::Cylinder","C1576")
App.ActiveDocument.C1576.Radius=0.750000
App.ActiveDocument.C1576.Height=15.00
App.ActiveDocument.C1576.Angle=360.00 
App.ActiveDocument.C1576.Placement=Base.Placement(Base.Vector(-70.799521,-123.559223,486.313505),Base.Rotation(-0.531575,-0.625246,0.000000,0.571398))
App.ActiveDocument.addObject("Part::Cylinder","C1577")
App.ActiveDocument.C1577.Radius=0.750000
App.ActiveDocument.C1577.Height=15.00
App.ActiveDocument.C1577.Angle=360.00 
App.ActiveDocument.C1577.Placement=Base.Placement(Base.Vector(-70.345595,-124.478080,483.980230),Base.Rotation(-0.523818,-0.650848,0.000000,0.549556))
App.ActiveDocument.addObject("Part::Cylinder","C1578")
App.ActiveDocument.C1578.Radius=0.750000
App.ActiveDocument.C1578.Height=15.00
App.ActiveDocument.C1578.Angle=360.00 
App.ActiveDocument.C1578.Placement=Base.Placement(Base.Vector(-69.956776,-125.603921,481.795387),Base.Rotation(-0.512800,-0.675455,0.000000,0.529902))
App.ActiveDocument.addObject("Part::Cylinder","C1579")
App.ActiveDocument.C1579.Radius=0.750000
App.ActiveDocument.C1579.Height=15.00
App.ActiveDocument.C1579.Angle=360.00 
App.ActiveDocument.C1579.Placement=Base.Placement(Base.Vector(-70.311530,-127.808654,479.884305),Base.Rotation(-0.492314,-0.710315,0.000000,0.503070))
App.ActiveDocument.addObject("Part::Cylinder","C1580")
App.ActiveDocument.C1580.Radius=0.750000
App.ActiveDocument.C1580.Height=15.00
App.ActiveDocument.C1580.Angle=360.00 
App.ActiveDocument.C1580.Placement=Base.Placement(Base.Vector(-69.848346,-129.442658,477.772728),Base.Rotation(-0.459462,-0.750857,0.000000,0.474457))
App.ActiveDocument.addObject("Part::Cylinder","C1581")
App.ActiveDocument.C1581.Radius=0.750000
App.ActiveDocument.C1581.Height=15.00
App.ActiveDocument.C1581.Angle=360.00 
App.ActiveDocument.C1581.Placement=Base.Placement(Base.Vector(-70.068813,-132.095829,476.205334),Base.Rotation(-0.401620,-0.801301,0.000000,0.443416))
App.ActiveDocument.addObject("Part::Cylinder","C1582")
App.ActiveDocument.C1582.Radius=0.750000
App.ActiveDocument.C1582.Height=15.00
App.ActiveDocument.C1582.Angle=360.00 
App.ActiveDocument.C1582.Placement=Base.Placement(Base.Vector(-68.868002,-133.812992,474.024176),Base.Rotation(-0.325826,-0.852857,0.000000,0.408011))
App.ActiveDocument.addObject("Part::Cylinder","C1583")
App.ActiveDocument.C1583.Radius=0.750000
App.ActiveDocument.C1583.Height=15.00
App.ActiveDocument.C1583.Angle=360.00 
App.ActiveDocument.C1583.Placement=Base.Placement(Base.Vector(-67.172468,-135.462905,471.760058),Base.Rotation(-0.246521,-0.891885,0.000000,0.379168))
App.ActiveDocument.addObject("Part::Cylinder","C1584")
App.ActiveDocument.C1584.Radius=0.750000
App.ActiveDocument.C1584.Height=15.00
App.ActiveDocument.C1584.Angle=360.00 
App.ActiveDocument.C1584.Placement=Base.Placement(Base.Vector(-71.546150,-137.770672,524.524473),Base.Rotation(-0.033822,-0.444884,0.000000,0.894949))
App.ActiveDocument.addObject("Part::Cylinder","C1585")
App.ActiveDocument.C1585.Radius=0.750000
App.ActiveDocument.C1585.Height=15.00
App.ActiveDocument.C1585.Angle=360.00 
App.ActiveDocument.C1585.Placement=Base.Placement(Base.Vector(-71.469481,-134.618248,524.135119),Base.Rotation(-0.072833,-0.445662,0.000000,0.892234))
App.ActiveDocument.addObject("Part::Cylinder","C1586")
App.ActiveDocument.C1586.Radius=0.750000
App.ActiveDocument.C1586.Height=15.00
App.ActiveDocument.C1586.Angle=360.00 
App.ActiveDocument.C1586.Placement=Base.Placement(Base.Vector(-71.711196,-131.792367,522.992315),Base.Rotation(-0.116857,-0.451603,0.000000,0.884533))
App.ActiveDocument.addObject("Part::Cylinder","C1587")
App.ActiveDocument.C1587.Radius=0.750000
App.ActiveDocument.C1587.Height=15.00
App.ActiveDocument.C1587.Angle=360.00 
App.ActiveDocument.C1587.Placement=Base.Placement(Base.Vector(-71.841692,-129.316369,521.696613),Base.Rotation(-0.161295,-0.456320,0.000000,0.875075))
App.ActiveDocument.addObject("Part::Cylinder","C1588")
App.ActiveDocument.C1588.Radius=0.750000
App.ActiveDocument.C1588.Height=15.00
App.ActiveDocument.C1588.Angle=360.00 
App.ActiveDocument.C1588.Placement=Base.Placement(Base.Vector(-72.141607,-127.379574,519.989069),Base.Rotation(-0.210754,-0.465851,0.000000,0.859398))
App.ActiveDocument.addObject("Part::Cylinder","C1589")
App.ActiveDocument.C1589.Radius=0.750000
App.ActiveDocument.C1589.Height=15.00
App.ActiveDocument.C1589.Angle=360.00 
App.ActiveDocument.C1589.Placement=Base.Placement(Base.Vector(-72.509183,-125.872215,518.040115),Base.Rotation(-0.251791,-0.474416,0.000000,0.843523))
App.ActiveDocument.addObject("Part::Cylinder","C1590")
App.ActiveDocument.C1590.Radius=0.750000
App.ActiveDocument.C1590.Height=15.00
App.ActiveDocument.C1590.Angle=360.00 
App.ActiveDocument.C1590.Placement=Base.Placement(Base.Vector(-72.789594,-124.608790,515.986510),Base.Rotation(-0.295388,-0.482379,0.000000,0.824655))
App.ActiveDocument.addObject("Part::Cylinder","C1591")
App.ActiveDocument.C1591.Radius=0.750000
App.ActiveDocument.C1591.Height=15.00
App.ActiveDocument.C1591.Angle=360.00 
App.ActiveDocument.C1591.Placement=Base.Placement(Base.Vector(-73.020525,-123.583712,513.801690),Base.Rotation(-0.337789,-0.491036,0.000000,0.802983))
App.ActiveDocument.addObject("Part::Cylinder","C1592")
App.ActiveDocument.C1592.Radius=0.750000
App.ActiveDocument.C1592.Height=15.00
App.ActiveDocument.C1592.Angle=360.00 
App.ActiveDocument.C1592.Placement=Base.Placement(Base.Vector(-73.369814,-123.001064,511.475779),Base.Rotation(-0.368400,-0.498983,0.000000,0.784409))
App.ActiveDocument.addObject("Part::Cylinder","C1593")
App.ActiveDocument.C1593.Radius=0.750000
App.ActiveDocument.C1593.Height=15.00
App.ActiveDocument.C1593.Angle=360.00 
App.ActiveDocument.C1593.Placement=Base.Placement(Base.Vector(-73.413597,-122.370397,509.324257),Base.Rotation(-0.405086,-0.506874,0.000000,0.760910))
App.ActiveDocument.addObject("Part::Cylinder","C1594")
App.ActiveDocument.C1594.Radius=0.750000
App.ActiveDocument.C1594.Height=15.00
App.ActiveDocument.C1594.Angle=360.00 
App.ActiveDocument.C1594.Placement=Base.Placement(Base.Vector(-73.809180,-122.283227,506.261202),Base.Rotation(-0.433518,-0.520664,0.000000,0.735508))
App.ActiveDocument.addObject("Part::Cylinder","C1595")
App.ActiveDocument.C1595.Radius=0.750000
App.ActiveDocument.C1595.Height=15.00
App.ActiveDocument.C1595.Angle=360.00 
App.ActiveDocument.C1595.Placement=Base.Placement(Base.Vector(-73.649818,-121.908869,503.324851),Base.Rotation(-0.466333,-0.529313,0.000000,0.708774))
App.ActiveDocument.addObject("Part::Cylinder","C1596")
App.ActiveDocument.C1596.Radius=0.750000
App.ActiveDocument.C1596.Height=15.00
App.ActiveDocument.C1596.Angle=360.00 
App.ActiveDocument.C1596.Placement=Base.Placement(Base.Vector(-73.926339,-122.303741,500.893224),Base.Rotation(-0.481894,-0.543230,0.000000,0.687516))
App.ActiveDocument.addObject("Part::Cylinder","C1597")
App.ActiveDocument.C1597.Radius=0.750000
App.ActiveDocument.C1597.Height=15.00
App.ActiveDocument.C1597.Angle=360.00 
App.ActiveDocument.C1597.Placement=Base.Placement(Base.Vector(-73.984186,-122.781162,497.875505),Base.Rotation(-0.497973,-0.558973,0.000000,0.663002))
App.ActiveDocument.addObject("Part::Cylinder","C1598")
App.ActiveDocument.C1598.Radius=0.750000
App.ActiveDocument.C1598.Height=15.00
App.ActiveDocument.C1598.Angle=360.00 
App.ActiveDocument.C1598.Placement=Base.Placement(Base.Vector(-73.901191,-123.296944,495.218896),Base.Rotation(-0.510349,-0.574666,0.000000,0.639768))
App.ActiveDocument.addObject("Part::Cylinder","C1599")
App.ActiveDocument.C1599.Radius=0.750000
App.ActiveDocument.C1599.Height=15.00
App.ActiveDocument.C1599.Angle=360.00 
App.ActiveDocument.C1599.Placement=Base.Placement(Base.Vector(-73.740650,-123.997256,492.514136),Base.Rotation(-0.518970,-0.591885,0.000000,0.616719))
App.ActiveDocument.addObject("Part::Cylinder","C1600")
App.ActiveDocument.C1600.Radius=0.750000
App.ActiveDocument.C1600.Height=15.00
App.ActiveDocument.C1600.Angle=360.00 
App.ActiveDocument.C1600.Placement=Base.Placement(Base.Vector(-73.657539,-124.947227,490.037436),Base.Rotation(-0.520621,-0.612834,0.000000,0.594465))
App.ActiveDocument.addObject("Part::Cylinder","C1601")
App.ActiveDocument.C1601.Radius=0.750000
App.ActiveDocument.C1601.Height=15.00
App.ActiveDocument.C1601.Angle=360.00 
App.ActiveDocument.C1601.Placement=Base.Placement(Base.Vector(-73.514595,-126.028129,487.657022),Base.Rotation(-0.519226,-0.635406,0.000000,0.571544))
App.ActiveDocument.addObject("Part::Cylinder","C1602")
App.ActiveDocument.C1602.Radius=0.750000
App.ActiveDocument.C1602.Height=15.00
App.ActiveDocument.C1602.Angle=360.00 
App.ActiveDocument.C1602.Placement=Base.Placement(Base.Vector(-73.017031,-127.055463,485.099850),Base.Rotation(-0.513933,-0.661190,0.000000,0.546535))
App.ActiveDocument.addObject("Part::Cylinder","C1603")
App.ActiveDocument.C1603.Radius=0.750000
App.ActiveDocument.C1603.Height=15.00
App.ActiveDocument.C1603.Angle=360.00 
App.ActiveDocument.C1603.Placement=Base.Placement(Base.Vector(-72.579314,-128.257203,482.820248),Base.Rotation(-0.502434,-0.686467,0.000000,0.525665))
App.ActiveDocument.addObject("Part::Cylinder","C1604")
App.ActiveDocument.C1604.Radius=0.750000
App.ActiveDocument.C1604.Height=15.00
App.ActiveDocument.C1604.Angle=360.00 
App.ActiveDocument.C1604.Placement=Base.Placement(Base.Vector(-72.970533,-130.575686,481.045033),Base.Rotation(-0.462338,-0.735175,0.000000,0.495744))
App.ActiveDocument.addObject("Part::Cylinder","C1605")
App.ActiveDocument.C1605.Radius=0.750000
App.ActiveDocument.C1605.Height=15.00
App.ActiveDocument.C1605.Angle=360.00 
App.ActiveDocument.C1605.Placement=Base.Placement(Base.Vector(-72.498137,-132.190177,479.109438),Base.Rotation(-0.418035,-0.779385,0.000000,0.466697))
App.ActiveDocument.addObject("Part::Cylinder","C1606")
App.ActiveDocument.C1606.Radius=0.750000
App.ActiveDocument.C1606.Height=15.00
App.ActiveDocument.C1606.Angle=360.00 
App.ActiveDocument.C1606.Placement=Base.Placement(Base.Vector(-72.246978,-134.530951,477.442913),Base.Rotation(-0.334035,-0.835352,0.000000,0.436586))
App.ActiveDocument.addObject("Part::Cylinder","C1607")
App.ActiveDocument.C1607.Radius=0.750000
App.ActiveDocument.C1607.Height=15.00
App.ActiveDocument.C1607.Angle=360.00 
App.ActiveDocument.C1607.Placement=Base.Placement(Base.Vector(-70.887808,-136.274504,475.244817),Base.Rotation(-0.258572,-0.875800,0.000000,0.407573))
App.ActiveDocument.addObject("Part::Cylinder","C1608")
App.ActiveDocument.C1608.Radius=0.750000
App.ActiveDocument.C1608.Height=15.00
App.ActiveDocument.C1608.Angle=360.00 
App.ActiveDocument.C1608.Placement=Base.Placement(Base.Vector(-69.266383,-137.803326,473.198327),Base.Rotation(-0.200268,-0.900747,0.000000,0.385418))
App.ActiveDocument.addObject("Part::Cylinder","C1609")
App.ActiveDocument.C1609.Radius=0.750000
App.ActiveDocument.C1609.Height=15.00
App.ActiveDocument.C1609.Angle=360.00 
App.ActiveDocument.C1609.Placement=Base.Placement(Base.Vector(-73.512611,-137.831169,521.783964),Base.Rotation(-0.034097,-0.469149,0.000000,0.882460))
App.ActiveDocument.addObject("Part::Cylinder","C1610")
App.ActiveDocument.C1610.Radius=0.750000
App.ActiveDocument.C1610.Height=15.00
App.ActiveDocument.C1610.Angle=360.00 
App.ActiveDocument.C1610.Placement=Base.Placement(Base.Vector(-73.561642,-134.781432,521.182241),Base.Rotation(-0.077508,-0.472080,0.000000,0.878142))
App.ActiveDocument.addObject("Part::Cylinder","C1611")
App.ActiveDocument.C1611.Radius=0.750000
App.ActiveDocument.C1611.Height=15.00
App.ActiveDocument.C1611.Angle=360.00 
App.ActiveDocument.C1611.Placement=Base.Placement(Base.Vector(-73.809203,-132.007371,519.895334),Base.Rotation(-0.122946,-0.480187,0.000000,0.868507))
App.ActiveDocument.addObject("Part::Cylinder","C1612")
App.ActiveDocument.C1612.Radius=0.750000
App.ActiveDocument.C1612.Height=15.00
App.ActiveDocument.C1612.Angle=360.00 
App.ActiveDocument.C1612.Placement=Base.Placement(Base.Vector(-74.038863,-129.850242,518.417137),Base.Rotation(-0.169188,-0.486954,0.000000,0.856884))
App.ActiveDocument.addObject("Part::Cylinder","C1613")
App.ActiveDocument.C1613.Radius=0.750000
App.ActiveDocument.C1613.Height=15.00
App.ActiveDocument.C1613.Angle=360.00 
App.ActiveDocument.C1613.Placement=Base.Placement(Base.Vector(-74.405471,-128.178018,516.508743),Base.Rotation(-0.211681,-0.495632,0.000000,0.842342))
App.ActiveDocument.addObject("Part::Cylinder","C1614")
App.ActiveDocument.C1614.Radius=0.750000
App.ActiveDocument.C1614.Height=15.00
App.ActiveDocument.C1614.Angle=360.00 
App.ActiveDocument.C1614.Placement=Base.Placement(Base.Vector(-74.742125,-126.923363,514.507747),Base.Rotation(-0.257928,-0.505946,0.000000,0.823099))
App.ActiveDocument.addObject("Part::Cylinder","C1615")
App.ActiveDocument.C1615.Radius=0.750000
App.ActiveDocument.C1615.Height=15.00
App.ActiveDocument.C1615.Angle=360.00 
App.ActiveDocument.C1615.Placement=Base.Placement(Base.Vector(-74.948844,-125.862397,512.495854),Base.Rotation(-0.298170,-0.515181,0.000000,0.803544))
App.ActiveDocument.addObject("Part::Cylinder","C1616")
App.ActiveDocument.C1616.Radius=0.750000
App.ActiveDocument.C1616.Height=15.00
App.ActiveDocument.C1616.Angle=360.00 
App.ActiveDocument.C1616.Placement=Base.Placement(Base.Vector(-75.266970,-125.298993,510.403491),Base.Rotation(-0.329517,-0.524146,0.000000,0.785296))
App.ActiveDocument.addObject("Part::Cylinder","C1617")
App.ActiveDocument.C1617.Radius=0.750000
App.ActiveDocument.C1617.Height=15.00
App.ActiveDocument.C1617.Angle=360.00 
App.ActiveDocument.C1617.Placement=Base.Placement(Base.Vector(-75.514259,-124.860932,508.139406),Base.Rotation(-0.369246,-0.532493,0.000000,0.761649))
App.ActiveDocument.addObject("Part::Cylinder","C1618")
App.ActiveDocument.C1618.Radius=0.750000
App.ActiveDocument.C1618.Height=15.00
App.ActiveDocument.C1618.Angle=360.00 
App.ActiveDocument.C1618.Placement=Base.Placement(Base.Vector(-75.942982,-124.836722,505.020256),Base.Rotation(-0.400103,-0.548016,0.000000,0.734572))
App.ActiveDocument.addObject("Part::Cylinder","C1619")
App.ActiveDocument.C1619.Radius=0.750000
App.ActiveDocument.C1619.Height=15.00
App.ActiveDocument.C1619.Angle=360.00 
App.ActiveDocument.C1619.Placement=Base.Placement(Base.Vector(-76.008467,-124.746417,502.234765),Base.Rotation(-0.431241,-0.560079,0.000000,0.707349))
App.ActiveDocument.addObject("Part::Cylinder","C1620")
App.ActiveDocument.C1620.Radius=0.750000
App.ActiveDocument.C1620.Height=15.00
App.ActiveDocument.C1620.Angle=360.00 
App.ActiveDocument.C1620.Placement=Base.Placement(Base.Vector(-76.220120,-125.180282,499.469279),Base.Rotation(-0.450982,-0.575055,0.000000,0.682588))
App.ActiveDocument.addObject("Part::Cylinder","C1621")
App.ActiveDocument.C1621.Radius=0.750000
App.ActiveDocument.C1621.Height=15.00
App.ActiveDocument.C1621.Angle=360.00 
App.ActiveDocument.C1621.Placement=Base.Placement(Base.Vector(-76.281630,-125.745177,496.668371),Base.Rotation(-0.470059,-0.592706,0.000000,0.654022))
App.ActiveDocument.addObject("Part::Cylinder","C1622")
App.ActiveDocument.C1622.Radius=0.750000
App.ActiveDocument.C1622.Height=15.00
App.ActiveDocument.C1622.Angle=360.00 
App.ActiveDocument.C1622.Placement=Base.Placement(Base.Vector(-76.203124,-126.446211,493.883514),Base.Rotation(-0.482009,-0.611658,0.000000,0.627329))
App.ActiveDocument.addObject("Part::Cylinder","C1623")
App.ActiveDocument.C1623.Radius=0.750000
App.ActiveDocument.C1623.Height=15.00
App.ActiveDocument.C1623.Angle=360.00 
App.ActiveDocument.C1623.Placement=Base.Placement(Base.Vector(-76.013663,-127.257236,491.268469),Base.Rotation(-0.486766,-0.630073,0.000000,0.605035))
App.ActiveDocument.addObject("Part::Cylinder","C1624")
App.ActiveDocument.C1624.Radius=0.750000
App.ActiveDocument.C1624.Height=15.00
App.ActiveDocument.C1624.Angle=360.00 
App.ActiveDocument.C1624.Placement=Base.Placement(Base.Vector(-75.884623,-128.362158,488.839424),Base.Rotation(-0.481651,-0.659550,0.000000,0.577067))
App.ActiveDocument.addObject("Part::Cylinder","C1625")
App.ActiveDocument.C1625.Radius=0.750000
App.ActiveDocument.C1625.Height=15.00
App.ActiveDocument.C1625.Angle=360.00 
App.ActiveDocument.C1625.Placement=Base.Placement(Base.Vector(-75.420149,-129.377478,486.345426),Base.Rotation(-0.474499,-0.685698,0.000000,0.551968))
App.ActiveDocument.addObject("Part::Cylinder","C1626")
App.ActiveDocument.C1626.Radius=0.750000
App.ActiveDocument.C1626.Height=15.00
App.ActiveDocument.C1626.Angle=360.00 
App.ActiveDocument.C1626.Placement=Base.Placement(Base.Vector(-74.958952,-130.549989,484.111432),Base.Rotation(-0.456443,-0.718095,0.000000,0.525357))
App.ActiveDocument.addObject("Part::Cylinder","C1627")
App.ActiveDocument.C1627.Radius=0.750000
App.ActiveDocument.C1627.Height=15.00
App.ActiveDocument.C1627.Angle=360.00 
App.ActiveDocument.C1627.Placement=Base.Placement(Base.Vector(-75.184866,-132.801348,482.418192),Base.Rotation(-0.390533,-0.773186,0.000000,0.499667))
App.ActiveDocument.addObject("Part::Cylinder","C1628")
App.ActiveDocument.C1628.Radius=0.750000
App.ActiveDocument.C1628.Height=15.00
App.ActiveDocument.C1628.Angle=360.00 
App.ActiveDocument.C1628.Placement=Base.Placement(Base.Vector(-74.527284,-134.491766,480.366737),Base.Rotation(-0.325359,-0.821102,0.000000,0.468971))
App.ActiveDocument.addObject("Part::Cylinder","C1629")
App.ActiveDocument.C1629.Radius=0.750000
App.ActiveDocument.C1629.Height=15.00
App.ActiveDocument.C1629.Angle=360.00 
App.ActiveDocument.C1629.Placement=Base.Placement(Base.Vector(-73.868888,-136.561952,478.643996),Base.Rotation(-0.188598,-0.874888,0.000000,0.446097))
App.ActiveDocument.addObject("Part::Cylinder","C1630")
App.ActiveDocument.C1630.Radius=0.750000
App.ActiveDocument.C1630.Height=15.00
App.ActiveDocument.C1630.Angle=360.00 
App.ActiveDocument.C1630.Placement=Base.Placement(Base.Vector(-72.355497,-138.221851,476.431371),Base.Rotation(-0.110145,-0.900378,0.000000,0.420936))
App.ActiveDocument.addObject("Part::Cylinder","C1631")
App.ActiveDocument.C1631.Radius=0.750000
App.ActiveDocument.C1631.Height=15.00
App.ActiveDocument.C1631.Angle=360.00 
App.ActiveDocument.C1631.Placement=Base.Placement(Base.Vector(-70.657462,-138.780428,474.436564),Base.Rotation(-0.086903,-0.911663,0.000000,0.401645))
App.ActiveDocument.addObject("Part::Cylinder","C1632")
App.ActiveDocument.C1632.Radius=0.750000
App.ActiveDocument.C1632.Height=15.00
App.ActiveDocument.C1632.Angle=360.00 
App.ActiveDocument.C1632.Placement=Base.Placement(Base.Vector(-75.342543,-137.914954,518.895977),Base.Rotation(-0.035640,-0.495296,0.000000,0.867993))
App.ActiveDocument.addObject("Part::Cylinder","C1633")
App.ActiveDocument.C1633.Radius=0.750000
App.ActiveDocument.C1633.Height=15.00
App.ActiveDocument.C1633.Angle=360.00 
App.ActiveDocument.C1633.Placement=Base.Placement(Base.Vector(-75.448611,-134.950237,518.135773),Base.Rotation(-0.078112,-0.499937,0.000000,0.862532))
App.ActiveDocument.addObject("Part::Cylinder","C1634")
App.ActiveDocument.C1634.Radius=0.750000
App.ActiveDocument.C1634.Height=15.00
App.ActiveDocument.C1634.Angle=360.00 
App.ActiveDocument.C1634.Placement=Base.Placement(Base.Vector(-75.748909,-132.526581,516.702560),Base.Rotation(-0.127129,-0.506045,0.000000,0.853086))
App.ActiveDocument.addObject("Part::Cylinder","C1635")
App.ActiveDocument.C1635.Radius=0.750000
App.ActiveDocument.C1635.Height=15.00
App.ActiveDocument.C1635.Angle=360.00 
App.ActiveDocument.C1635.Placement=Base.Placement(Base.Vector(-76.124615,-130.692151,514.901477),Base.Rotation(-0.168646,-0.520749,0.000000,0.836886))
App.ActiveDocument.addObject("Part::Cylinder","C1636")
App.ActiveDocument.C1636.Radius=0.750000
App.ActiveDocument.C1636.Height=15.00
App.ActiveDocument.C1636.Angle=360.00 
App.ActiveDocument.C1636.Placement=Base.Placement(Base.Vector(-76.427361,-129.210717,512.952492),Base.Rotation(-0.214722,-0.530795,0.000000,0.819848))
App.ActiveDocument.addObject("Part::Cylinder","C1637")
App.ActiveDocument.C1637.Radius=0.750000
App.ActiveDocument.C1637.Height=15.00
App.ActiveDocument.C1637.Angle=360.00 
App.ActiveDocument.C1637.Placement=Base.Placement(Base.Vector(-76.667678,-128.028224,510.831878),Base.Rotation(-0.259113,-0.541335,0.000000,0.799885))
App.ActiveDocument.addObject("Part::Cylinder","C1638")
App.ActiveDocument.C1638.Radius=0.750000
App.ActiveDocument.C1638.Height=15.00
App.ActiveDocument.C1638.Angle=360.00 
App.ActiveDocument.C1638.Placement=Base.Placement(Base.Vector(-77.261998,-127.689076,508.042356),Base.Rotation(-0.298330,-0.557893,0.000000,0.774438))
App.ActiveDocument.addObject("Part::Cylinder","C1639")
App.ActiveDocument.C1639.Radius=0.750000
App.ActiveDocument.C1639.Height=15.00
App.ActiveDocument.C1639.Angle=360.00 
App.ActiveDocument.C1639.Placement=Base.Placement(Base.Vector(-77.556467,-127.352187,505.527978),Base.Rotation(-0.335321,-0.569439,0.000000,0.750533))
App.ActiveDocument.addObject("Part::Cylinder","C1640")
App.ActiveDocument.C1640.Radius=0.750000
App.ActiveDocument.C1640.Height=15.00
App.ActiveDocument.C1640.Angle=360.00 
App.ActiveDocument.C1640.Placement=Base.Placement(Base.Vector(-77.822604,-127.342230,502.678797),Base.Rotation(-0.367138,-0.587681,0.000000,0.721000))
App.ActiveDocument.addObject("Part::Cylinder","C1641")
App.ActiveDocument.C1641.Radius=0.750000
App.ActiveDocument.C1641.Height=15.00
App.ActiveDocument.C1641.Angle=360.00 
App.ActiveDocument.C1641.Placement=Base.Placement(Base.Vector(-78.009356,-127.598416,500.108516),Base.Rotation(-0.389691,-0.602920,0.000000,0.696152))
App.ActiveDocument.addObject("Part::Cylinder","C1642")
App.ActiveDocument.C1642.Radius=0.750000
App.ActiveDocument.C1642.Height=15.00
App.ActiveDocument.C1642.Angle=360.00 
App.ActiveDocument.C1642.Placement=Base.Placement(Base.Vector(-78.139863,-128.110158,497.568004),Base.Rotation(-0.400949,-0.621681,0.000000,0.672869))
App.ActiveDocument.addObject("Part::Cylinder","C1643")
App.ActiveDocument.C1643.Radius=0.750000
App.ActiveDocument.C1643.Height=15.00
App.ActiveDocument.C1643.Angle=360.00 
App.ActiveDocument.C1643.Placement=Base.Placement(Base.Vector(-78.110964,-128.721502,494.961539),Base.Rotation(-0.413575,-0.643198,0.000000,0.644400))
App.ActiveDocument.addObject("Part::Cylinder","C1644")
App.ActiveDocument.C1644.Radius=0.750000
App.ActiveDocument.C1644.Height=15.00
App.ActiveDocument.C1644.Angle=360.00 
App.ActiveDocument.C1644.Placement=Base.Placement(Base.Vector(-78.055140,-129.570004,492.531136),Base.Rotation(-0.419178,-0.665243,0.000000,0.617852))
App.ActiveDocument.addObject("Part::Cylinder","C1645")
App.ActiveDocument.C1645.Radius=0.750000
App.ActiveDocument.C1645.Height=15.00
App.ActiveDocument.C1645.Angle=360.00 
App.ActiveDocument.C1645.Placement=Base.Placement(Base.Vector(-77.849601,-130.478137,490.189643),Base.Rotation(-0.413770,-0.691149,0.000000,0.592543))
App.ActiveDocument.addObject("Part::Cylinder","C1646")
App.ActiveDocument.C1646.Radius=0.750000
App.ActiveDocument.C1646.Height=15.00
App.ActiveDocument.C1646.Angle=360.00 
App.ActiveDocument.C1646.Placement=Base.Placement(Base.Vector(-77.380627,-131.369602,487.779882),Base.Rotation(-0.388538,-0.728595,0.000000,0.564081))
App.ActiveDocument.addObject("Part::Cylinder","C1647")
App.ActiveDocument.C1647.Radius=0.750000
App.ActiveDocument.C1647.Height=15.00
App.ActiveDocument.C1647.Angle=360.00 
App.ActiveDocument.C1647.Placement=Base.Placement(Base.Vector(-76.917613,-132.566271,485.534324),Base.Rotation(-0.371088,-0.758309,0.000000,0.535967))
App.ActiveDocument.addObject("Part::Cylinder","C1648")
App.ActiveDocument.C1648.Radius=0.750000
App.ActiveDocument.C1648.Height=15.00
App.ActiveDocument.C1648.Angle=360.00 
App.ActiveDocument.C1648.Placement=Base.Placement(Base.Vector(-76.804123,-134.567547,483.867105),Base.Rotation(-0.257624,-0.818893,0.000000,0.512878))
App.ActiveDocument.addObject("Part::Cylinder","C1649")
App.ActiveDocument.C1649.Radius=0.750000
App.ActiveDocument.C1649.Height=15.00
App.ActiveDocument.C1649.Angle=360.00 
App.ActiveDocument.C1649.Placement=Base.Placement(Base.Vector(-75.974452,-136.241884,481.749347),Base.Rotation(-0.171695,-0.857031,0.000000,0.485817))
App.ActiveDocument.addObject("Part::Cylinder","C1650")
App.ActiveDocument.C1650.Radius=0.750000
App.ActiveDocument.C1650.Height=15.00
App.ActiveDocument.C1650.Angle=360.00 
App.ActiveDocument.C1650.Placement=Base.Placement(Base.Vector(-75.227362,-138.249489,480.188013),Base.Rotation(-0.074366,-0.881120,0.000000,0.467009))
App.ActiveDocument.addObject("Part::Cylinder","C1651")
App.ActiveDocument.C1651.Radius=0.750000
App.ActiveDocument.C1651.Height=15.00
App.ActiveDocument.C1651.Angle=360.00 
App.ActiveDocument.C1651.Placement=Base.Placement(Base.Vector(-73.908134,-138.685703,478.291836),Base.Rotation(-0.070057,-0.893092,0.000000,0.444385))
App.ActiveDocument.addObject("Part::Cylinder","C1652")
App.ActiveDocument.C1652.Radius=0.750000
App.ActiveDocument.C1652.Height=15.00
App.ActiveDocument.C1652.Angle=360.00 
App.ActiveDocument.C1652.Placement=Base.Placement(Base.Vector(-76.966598,-137.958024,515.932448),Base.Rotation(-0.037393,-0.523669,0.000000,0.851101))
App.ActiveDocument.addObject("Part::Cylinder","C1653")
App.ActiveDocument.C1653.Radius=0.750000
App.ActiveDocument.C1653.Height=15.00
App.ActiveDocument.C1653.Angle=360.00 
App.ActiveDocument.C1653.Placement=Base.Placement(Base.Vector(-77.181336,-135.183856,514.868140),Base.Rotation(-0.081176,-0.531337,0.000000,0.843262))
App.ActiveDocument.addObject("Part::Cylinder","C1654")
App.ActiveDocument.C1654.Radius=0.750000
App.ActiveDocument.C1654.Height=15.00
App.ActiveDocument.C1654.Angle=360.00 
App.ActiveDocument.C1654.Placement=Base.Placement(Base.Vector(-77.581220,-133.102234,513.102593),Base.Rotation(-0.123876,-0.544017,0.000000,0.829879))
App.ActiveDocument.addObject("Part::Cylinder","C1655")
App.ActiveDocument.C1655.Radius=0.750000
App.ActiveDocument.C1655.Height=15.00
App.ActiveDocument.C1655.Angle=360.00 
App.ActiveDocument.C1655.Placement=Base.Placement(Base.Vector(-77.924253,-131.583469,511.201921),Base.Rotation(-0.166694,-0.555259,0.000000,0.814801))
App.ActiveDocument.addObject("Part::Cylinder","C1656")
App.ActiveDocument.C1656.Radius=0.750000
App.ActiveDocument.C1656.Height=15.00
App.ActiveDocument.C1656.Angle=360.00 
App.ActiveDocument.C1656.Placement=Base.Placement(Base.Vector(-78.155795,-130.409892,509.307082),Base.Rotation(-0.214681,-0.568318,0.000000,0.794309))
App.ActiveDocument.addObject("Part::Cylinder","C1657")
App.ActiveDocument.C1657.Radius=0.750000
App.ActiveDocument.C1657.Height=15.00
App.ActiveDocument.C1657.Angle=360.00 
App.ActiveDocument.C1657.Placement=Base.Placement(Base.Vector(-78.795041,-130.163776,506.320593),Base.Rotation(-0.235862,-0.592397,0.000000,0.770347))
App.ActiveDocument.addObject("Part::Cylinder","C1658")
App.ActiveDocument.C1658.Radius=0.750000
App.ActiveDocument.C1658.Height=15.00
App.ActiveDocument.C1658.Angle=360.00 
App.ActiveDocument.C1658.Placement=Base.Placement(Base.Vector(-79.044609,-129.743591,503.596754),Base.Rotation(-0.273138,-0.611696,0.000000,0.742445))
App.ActiveDocument.addObject("Part::Cylinder","C1659")
App.ActiveDocument.C1659.Radius=0.750000
App.ActiveDocument.C1659.Height=15.00
App.ActiveDocument.C1659.Angle=360.00 
App.ActiveDocument.C1659.Placement=Base.Placement(Base.Vector(-79.371963,-130.041795,500.809243),Base.Rotation(-0.302453,-0.633429,0.000000,0.712243))
App.ActiveDocument.addObject("Part::Cylinder","C1660")
App.ActiveDocument.C1660.Radius=0.750000
App.ActiveDocument.C1660.Height=15.00
App.ActiveDocument.C1660.Angle=360.00 
App.ActiveDocument.C1660.Placement=Base.Placement(Base.Vector(-79.548076,-130.507123,498.206228),Base.Rotation(-0.315000,-0.655446,0.000000,0.686415))
App.ActiveDocument.addObject("Part::Cylinder","C1661")
App.ActiveDocument.C1661.Radius=0.750000
App.ActiveDocument.C1661.Height=15.00
App.ActiveDocument.C1661.Angle=360.00 
App.ActiveDocument.C1661.Placement=Base.Placement(Base.Vector(-79.525112,-130.983596,495.771885),Base.Rotation(-0.322156,-0.679886,0.000000,0.658765))
App.ActiveDocument.addObject("Part::Cylinder","C1662")
App.ActiveDocument.C1662.Radius=0.750000
App.ActiveDocument.C1662.Height=15.00
App.ActiveDocument.C1662.Angle=360.00 
App.ActiveDocument.C1662.Placement=Base.Placement(Base.Vector(-79.396403,-131.668945,493.355492),Base.Rotation(-0.313522,-0.706577,0.000000,0.634392))
App.ActiveDocument.addObject("Part::Cylinder","C1663")
App.ActiveDocument.C1663.Radius=0.750000
App.ActiveDocument.C1663.Height=15.00
App.ActiveDocument.C1663.Angle=360.00 
App.ActiveDocument.C1663.Placement=Base.Placement(Base.Vector(-79.142431,-132.481368,491.047314),Base.Rotation(-0.301122,-0.737005,0.000000,0.605103))
App.ActiveDocument.addObject("Part::Cylinder","C1664")
App.ActiveDocument.C1664.Radius=0.750000
App.ActiveDocument.C1664.Height=15.00
App.ActiveDocument.C1664.Angle=360.00 
App.ActiveDocument.C1664.Placement=Base.Placement(Base.Vector(-78.803732,-133.359572,489.011682),Base.Rotation(-0.273973,-0.767323,0.000000,0.579789))
App.ActiveDocument.addObject("Part::Cylinder","C1665")
App.ActiveDocument.C1665.Radius=0.750000
App.ActiveDocument.C1665.Height=15.00
App.ActiveDocument.C1665.Angle=360.00 
App.ActiveDocument.C1665.Placement=Base.Placement(Base.Vector(-78.224229,-134.292088,486.818821),Base.Rotation(-0.234693,-0.799639,0.000000,0.552717))
App.ActiveDocument.addObject("Part::Cylinder","C1666")
App.ActiveDocument.C1666.Radius=0.750000
App.ActiveDocument.C1666.Height=15.00
App.ActiveDocument.C1666.Angle=360.00 
App.ActiveDocument.C1666.Placement=Base.Placement(Base.Vector(-78.029883,-136.509060,485.359795),Base.Rotation(-0.127250,-0.835724,0.000000,0.534203))
App.ActiveDocument.addObject("Part::Cylinder","C1667")
App.ActiveDocument.C1667.Radius=0.750000
App.ActiveDocument.C1667.Height=15.00
App.ActiveDocument.C1667.Angle=360.00 
App.ActiveDocument.C1667.Placement=Base.Placement(Base.Vector(-77.258749,-138.115452,483.502290),Base.Rotation(-0.068628,-0.857863,0.000000,0.509275))
App.ActiveDocument.addObject("Part::Cylinder","C1668")
App.ActiveDocument.C1668.Radius=0.750000
App.ActiveDocument.C1668.Height=15.00
App.ActiveDocument.C1668.Angle=360.00 
App.ActiveDocument.C1668.Placement=Base.Placement(Base.Vector(-78.397098,-138.149297,512.860940),Base.Rotation(-0.037460,-0.554208,0.000000,0.831535))
App.ActiveDocument.addObject("Part::Cylinder","C1669")
App.ActiveDocument.C1669.Radius=0.750000
App.ActiveDocument.C1669.Height=15.00
App.ActiveDocument.C1669.Angle=360.00 
App.ActiveDocument.C1669.Placement=Base.Placement(Base.Vector(-78.757314,-135.857466,511.382619),Base.Rotation(-0.077210,-0.566209,0.000000,0.820638))
App.ActiveDocument.addObject("Part::Cylinder","C1670")
App.ActiveDocument.C1670.Radius=0.750000
App.ActiveDocument.C1670.Height=15.00
App.ActiveDocument.C1670.Angle=360.00 
App.ActiveDocument.C1670.Placement=Base.Placement(Base.Vector(-79.116310,-134.036981,509.477197),Base.Rotation(-0.116736,-0.581916,0.000000,0.804827))
App.ActiveDocument.addObject("Part::Cylinder","C1671")
App.ActiveDocument.C1671.Radius=0.750000
App.ActiveDocument.C1671.Height=15.00
App.ActiveDocument.C1671.Angle=360.00 
App.ActiveDocument.C1671.Placement=Base.Placement(Base.Vector(-79.334355,-132.488942,507.431458),Base.Rotation(-0.163608,-0.597057,0.000000,0.785338))
App.ActiveDocument.addObject("Part::Cylinder","C1672")
App.ActiveDocument.C1672.Radius=0.750000
App.ActiveDocument.C1672.Height=15.00
App.ActiveDocument.C1672.Angle=360.00 
App.ActiveDocument.C1672.Placement=Base.Placement(Base.Vector(-79.977937,-132.709097,504.585574),Base.Rotation(-0.180573,-0.624473,0.000000,0.759886))
App.ActiveDocument.addObject("Part::Cylinder","C1673")
App.ActiveDocument.C1673.Radius=0.750000
App.ActiveDocument.C1673.Height=15.00
App.ActiveDocument.C1673.Angle=360.00 
App.ActiveDocument.C1673.Placement=Base.Placement(Base.Vector(-80.211609,-132.339733,501.842705),Base.Rotation(-0.200564,-0.648151,0.000000,0.734625))
App.ActiveDocument.addObject("Part::Cylinder","C1674")
App.ActiveDocument.C1674.Radius=0.750000
App.ActiveDocument.C1674.Height=15.00
App.ActiveDocument.C1674.Angle=360.00 
App.ActiveDocument.C1674.Placement=Base.Placement(Base.Vector(-80.451626,-132.791262,499.175047),Base.Rotation(-0.207989,-0.677712,0.000000,0.705299))
App.ActiveDocument.addObject("Part::Cylinder","C1675")
App.ActiveDocument.C1675.Radius=0.750000
App.ActiveDocument.C1675.Height=15.00
App.ActiveDocument.C1675.Angle=360.00 
App.ActiveDocument.C1675.Placement=Base.Placement(Base.Vector(-80.466200,-133.257288,496.532968),Base.Rotation(-0.210314,-0.706326,0.000000,0.675922))
App.ActiveDocument.addObject("Part::Cylinder","C1676")
App.ActiveDocument.C1676.Radius=0.750000
App.ActiveDocument.C1676.Height=15.00
App.ActiveDocument.C1676.Angle=360.00 
App.ActiveDocument.C1676.Placement=Base.Placement(Base.Vector(-80.311536,-133.766805,494.205835),Base.Rotation(-0.201188,-0.737492,0.000000,0.644693))
App.ActiveDocument.addObject("Part::Cylinder","C1677")
App.ActiveDocument.C1677.Radius=0.750000
App.ActiveDocument.C1677.Height=15.00
App.ActiveDocument.C1677.Angle=360.00 
App.ActiveDocument.C1677.Placement=Base.Placement(Base.Vector(-80.023896,-134.541083,491.854778),Base.Rotation(-0.191468,-0.763803,0.000000,0.616397))
App.ActiveDocument.addObject("Part::Cylinder","C1678")
App.ActiveDocument.C1678.Radius=0.750000
App.ActiveDocument.C1678.Height=15.00
App.ActiveDocument.C1678.Angle=360.00 
App.ActiveDocument.C1678.Placement=Base.Placement(Base.Vector(-79.688155,-135.523055,489.916797),Base.Rotation(-0.148374,-0.790561,0.000000,0.594137))
App.ActiveDocument.addObject("Part::Cylinder","C1679")
App.ActiveDocument.C1679.Radius=0.750000
App.ActiveDocument.C1679.Height=15.00
App.ActiveDocument.C1679.Angle=360.00 
App.ActiveDocument.C1679.Placement=Base.Placement(Base.Vector(-79.121862,-136.525008,487.833076),Base.Rotation(-0.116112,-0.815490,0.000000,0.567004))
App.ActiveDocument.addObject("Part::Cylinder","C1680")
App.ActiveDocument.C1680.Radius=0.750000
App.ActiveDocument.C1680.Height=15.00
App.ActiveDocument.C1680.Angle=360.00 
App.ActiveDocument.C1680.Placement=Base.Placement(Base.Vector(-78.960958,-138.604813,486.965265),Base.Rotation(-0.050660,-0.830260,0.000000,0.555070))
App.ActiveDocument.addObject("Part::Cylinder","C1681")
App.ActiveDocument.C1681.Radius=0.750000
App.ActiveDocument.C1681.Height=15.00
App.ActiveDocument.C1681.Angle=360.00 
App.ActiveDocument.C1681.Placement=Base.Placement(Base.Vector(-79.599142,-138.459915,509.681557),Base.Rotation(-0.035497,-0.586419,0.000000,0.809229))
App.ActiveDocument.addObject("Part::Cylinder","C1682")
App.ActiveDocument.C1682.Radius=0.750000
App.ActiveDocument.C1682.Height=15.00
App.ActiveDocument.C1682.Angle=360.00 
App.ActiveDocument.C1682.Placement=Base.Placement(Base.Vector(-80.042120,-136.635800,507.688409),Base.Rotation(-0.068624,-0.605470,0.000000,0.792904))
App.ActiveDocument.addObject("Part::Cylinder","C1683")
App.ActiveDocument.C1683.Radius=0.750000
App.ActiveDocument.C1683.Height=15.00
App.ActiveDocument.C1683.Angle=360.00 
App.ActiveDocument.C1683.Placement=Base.Placement(Base.Vector(-80.280070,-135.019627,505.750964),Base.Rotation(-0.104619,-0.623018,0.000000,0.775179))
App.ActiveDocument.addObject("Part::Cylinder","C1684")
App.ActiveDocument.C1684.Radius=0.750000
App.ActiveDocument.C1684.Height=15.00
App.ActiveDocument.C1684.Angle=360.00 
App.ActiveDocument.C1684.Placement=Base.Placement(Base.Vector(-80.798093,-135.324323,502.848338),Base.Rotation(-0.107301,-0.655490,0.000000,0.747543))
App.ActiveDocument.addObject("Part::Cylinder","C1685")
App.ActiveDocument.C1685.Radius=0.750000
App.ActiveDocument.C1685.Height=15.00
App.ActiveDocument.C1685.Angle=360.00 
App.ActiveDocument.C1685.Placement=Base.Placement(Base.Vector(-81.014126,-135.292460,500.187023),Base.Rotation(-0.116792,-0.684819,0.000000,0.719293))
App.ActiveDocument.addObject("Part::Cylinder","C1686")
App.ActiveDocument.C1686.Radius=0.750000
App.ActiveDocument.C1686.Height=15.00
App.ActiveDocument.C1686.Angle=360.00 
App.ActiveDocument.C1686.Placement=Base.Placement(Base.Vector(-81.090595,-135.806828,497.688003),Base.Rotation(-0.108612,-0.713850,0.000000,0.691825))
App.ActiveDocument.addObject("Part::Cylinder","C1687")
App.ActiveDocument.C1687.Radius=0.750000
App.ActiveDocument.C1687.Height=15.00
App.ActiveDocument.C1687.Angle=360.00 
App.ActiveDocument.C1687.Placement=Base.Placement(Base.Vector(-80.957249,-136.327003,495.182063),Base.Rotation(-0.098134,-0.743732,0.000000,0.661236))
App.ActiveDocument.addObject("Part::Cylinder","C1688")
App.ActiveDocument.C1688.Radius=0.750000
App.ActiveDocument.C1688.Height=15.00
App.ActiveDocument.C1688.Angle=360.00 
App.ActiveDocument.C1688.Placement=Base.Placement(Base.Vector(-80.670065,-136.974649,492.925653),Base.Rotation(-0.083140,-0.768772,0.000000,0.634096))
App.ActiveDocument.addObject("Part::Cylinder","C1689")
App.ActiveDocument.C1689.Radius=0.750000
App.ActiveDocument.C1689.Height=15.00
App.ActiveDocument.C1689.Angle=360.00 
App.ActiveDocument.C1689.Placement=Base.Placement(Base.Vector(-80.343914,-138.081896,491.094761),Base.Rotation(-0.059492,-0.790511,0.000000,0.609552))
App.ActiveDocument.addObject("Part::Cylinder","C1690")
App.ActiveDocument.C1690.Radius=0.750000
App.ActiveDocument.C1690.Height=15.00
App.ActiveDocument.C1690.Angle=360.00 
App.ActiveDocument.C1690.Placement=Base.Placement(Base.Vector(-80.524965,-138.562826,506.368672),Base.Rotation(-0.036458,-0.622030,0.000000,0.782144))
App.ActiveDocument.addObject("Part::Cylinder","C1691")
App.ActiveDocument.C1691.Radius=0.750000
App.ActiveDocument.C1691.Height=15.00
App.ActiveDocument.C1691.Angle=360.00 
App.ActiveDocument.C1691.Placement=Base.Placement(Base.Vector(-81.004865,-138.318262,503.812534),Base.Rotation(-0.042185,-0.650182,0.000000,0.758607))
App.ActiveDocument.addObject("Part::Cylinder","C1692")
App.ActiveDocument.C1692.Radius=0.750000
App.ActiveDocument.C1692.Height=15.00
App.ActiveDocument.C1692.Angle=360.00 
App.ActiveDocument.C1692.Placement=Base.Placement(Base.Vector(-81.313278,-138.384684,501.022163),Base.Rotation(-0.043453,-0.682333,0.000000,0.729749))
App.ActiveDocument.addObject("Part::Cylinder","C1693")
App.ActiveDocument.C1693.Radius=0.750000
App.ActiveDocument.C1693.Height=15.00
App.ActiveDocument.C1693.Angle=360.00 
App.ActiveDocument.C1693.Placement=Base.Placement(Base.Vector(-81.401232,-138.674287,498.603576),Base.Rotation(-0.038724,-0.710068,0.000000,0.703067))
App.ActiveDocument.addObject("Part::Cylinder","C1694")
App.ActiveDocument.C1694.Radius=0.750000
App.ActiveDocument.C1694.Height=15.00
App.ActiveDocument.C1694.Angle=360.00 
App.ActiveDocument.C1694.Placement=Base.Placement(Base.Vector(-81.232348,-138.658850,495.732971),Base.Rotation(-0.041959,-0.741914,0.000000,0.669181))
App.ActiveDocument.addObject("Part::Cylinder","C1695")
App.ActiveDocument.C1695.Radius=0.750000
App.ActiveDocument.C1695.Height=15.00
App.ActiveDocument.C1695.Angle=360.00 
App.ActiveDocument.C1695.Placement=Base.Placement(Base.Vector(-34.967920,-144.328096,548.214251),Base.Rotation(0.026135,-0.078480,0.000000,0.996573))
App.ActiveDocument.addObject("Part::Cylinder","C1696")
App.ActiveDocument.C1696.Radius=0.750000
App.ActiveDocument.C1696.Height=15.00
App.ActiveDocument.C1696.Angle=360.00 
App.ActiveDocument.C1696.Placement=Base.Placement(Base.Vector(-35.084490,-147.778862,547.911719),Base.Rotation(0.055614,-0.078714,0.000000,0.995345))
App.ActiveDocument.addObject("Part::Cylinder","C1697")
App.ActiveDocument.C1697.Radius=0.750000
App.ActiveDocument.C1697.Height=15.00
App.ActiveDocument.C1697.Angle=360.00 
App.ActiveDocument.C1697.Placement=Base.Placement(Base.Vector(-35.010220,-151.096576,547.436964),Base.Rotation(0.088494,-0.075236,0.000000,0.993231))
App.ActiveDocument.addObject("Part::Cylinder","C1698")
App.ActiveDocument.C1698.Radius=0.750000
App.ActiveDocument.C1698.Height=15.00
App.ActiveDocument.C1698.Angle=360.00 
App.ActiveDocument.C1698.Placement=Base.Placement(Base.Vector(-35.160936,-154.300327,546.717309),Base.Rotation(0.124858,-0.074289,0.000000,0.989390))
App.ActiveDocument.addObject("Part::Cylinder","C1699")
App.ActiveDocument.C1699.Radius=0.750000
App.ActiveDocument.C1699.Height=15.00
App.ActiveDocument.C1699.Angle=360.00 
App.ActiveDocument.C1699.Placement=Base.Placement(Base.Vector(-35.218066,-157.408645,545.779499),Base.Rotation(0.163762,-0.070072,0.000000,0.984008))
App.ActiveDocument.addObject("Part::Cylinder","C1700")
App.ActiveDocument.C1700.Radius=0.750000
App.ActiveDocument.C1700.Height=15.00
App.ActiveDocument.C1700.Angle=360.00 
App.ActiveDocument.C1700.Placement=Base.Placement(Base.Vector(-35.237570,-160.285872,544.652691),Base.Rotation(0.202247,-0.071354,0.000000,0.976732))
App.ActiveDocument.addObject("Part::Cylinder","C1701")
App.ActiveDocument.C1701.Radius=0.750000
App.ActiveDocument.C1701.Height=15.00
App.ActiveDocument.C1701.Angle=360.00 
App.ActiveDocument.C1701.Placement=Base.Placement(Base.Vector(-35.332486,-163.029104,543.282167),Base.Rotation(0.247147,-0.065081,0.000000,0.966790))
App.ActiveDocument.addObject("Part::Cylinder","C1702")
App.ActiveDocument.C1702.Radius=0.750000
App.ActiveDocument.C1702.Height=15.00
App.ActiveDocument.C1702.Angle=360.00 
App.ActiveDocument.C1702.Placement=Base.Placement(Base.Vector(-35.353827,-165.590535,541.704096),Base.Rotation(0.292729,-0.063187,0.000000,0.954105))
App.ActiveDocument.addObject("Part::Cylinder","C1703")
App.ActiveDocument.C1703.Radius=0.750000
App.ActiveDocument.C1703.Height=15.00
App.ActiveDocument.C1703.Angle=360.00 
App.ActiveDocument.C1703.Placement=Base.Placement(Base.Vector(-35.566152,-167.999956,539.854038),Base.Rotation(0.338830,-0.061275,0.000000,0.938850))
App.ActiveDocument.addObject("Part::Cylinder","C1704")
App.ActiveDocument.C1704.Radius=0.750000
App.ActiveDocument.C1704.Height=15.00
App.ActiveDocument.C1704.Angle=360.00 
App.ActiveDocument.C1704.Placement=Base.Placement(Base.Vector(-35.613425,-170.234747,537.786564),Base.Rotation(0.387280,-0.054247,0.000000,0.920365))
App.ActiveDocument.addObject("Part::Cylinder","C1705")
App.ActiveDocument.C1705.Radius=0.750000
App.ActiveDocument.C1705.Height=15.00
App.ActiveDocument.C1705.Angle=360.00 
App.ActiveDocument.C1705.Placement=Base.Placement(Base.Vector(-35.653155,-172.310074,535.446753),Base.Rotation(0.430686,-0.052121,0.000000,0.900996))
App.ActiveDocument.addObject("Part::Cylinder","C1706")
App.ActiveDocument.C1706.Radius=0.750000
App.ActiveDocument.C1706.Height=15.00
App.ActiveDocument.C1706.Angle=360.00 
App.ActiveDocument.C1706.Placement=Base.Placement(Base.Vector(-35.784303,-174.151663,532.902842),Base.Rotation(0.473354,-0.046443,0.000000,0.879647))
App.ActiveDocument.addObject("Part::Cylinder","C1707")
App.ActiveDocument.C1707.Radius=0.750000
App.ActiveDocument.C1707.Height=15.00
App.ActiveDocument.C1707.Angle=360.00 
App.ActiveDocument.C1707.Placement=Base.Placement(Base.Vector(-35.906309,-175.721378,530.266536),Base.Rotation(0.510421,-0.045190,0.000000,0.858737))
App.ActiveDocument.addObject("Part::Cylinder","C1708")
App.ActiveDocument.C1708.Radius=0.750000
App.ActiveDocument.C1708.Height=15.00
App.ActiveDocument.C1708.Angle=360.00 
App.ActiveDocument.C1708.Placement=Base.Placement(Base.Vector(-35.886812,-177.112580,527.426167),Base.Rotation(0.546916,-0.040924,0.000000,0.836187))
App.ActiveDocument.addObject("Part::Cylinder","C1709")
App.ActiveDocument.C1709.Radius=0.750000
App.ActiveDocument.C1709.Height=15.00
App.ActiveDocument.C1709.Angle=360.00 
App.ActiveDocument.C1709.Placement=Base.Placement(Base.Vector(-35.989320,-178.285808,524.424727),Base.Rotation(0.577856,-0.040652,0.000000,0.815126))
App.ActiveDocument.addObject("Part::Cylinder","C1710")
App.ActiveDocument.C1710.Radius=0.750000
App.ActiveDocument.C1710.Height=15.00
App.ActiveDocument.C1710.Angle=360.00 
App.ActiveDocument.C1710.Placement=Base.Placement(Base.Vector(-36.077082,-179.259833,521.242532),Base.Rotation(0.606835,-0.037178,0.000000,0.793958))
App.ActiveDocument.addObject("Part::Cylinder","C1711")
App.ActiveDocument.C1711.Radius=0.750000
App.ActiveDocument.C1711.Height=15.00
App.ActiveDocument.C1711.Angle=360.00 
App.ActiveDocument.C1711.Placement=Base.Placement(Base.Vector(-36.068449,-179.996150,518.049485),Base.Rotation(0.634679,-0.033397,0.000000,0.772054))
App.ActiveDocument.addObject("Part::Cylinder","C1712")
App.ActiveDocument.C1712.Radius=0.750000
App.ActiveDocument.C1712.Height=15.00
App.ActiveDocument.C1712.Angle=360.00 
App.ActiveDocument.C1712.Placement=Base.Placement(Base.Vector(-36.111999,-180.524637,514.760139),Base.Rotation(0.659999,-0.029340,0.000000,0.750693))
App.ActiveDocument.addObject("Part::Cylinder","C1713")
App.ActiveDocument.C1713.Radius=0.750000
App.ActiveDocument.C1713.Height=15.00
App.ActiveDocument.C1713.Angle=360.00 
App.ActiveDocument.C1713.Placement=Base.Placement(Base.Vector(-36.301470,-180.839572,511.377902),Base.Rotation(0.683973,-0.025724,0.000000,0.729054))
App.ActiveDocument.addObject("Part::Cylinder","C1714")
App.ActiveDocument.C1714.Radius=0.750000
App.ActiveDocument.C1714.Height=15.00
App.ActiveDocument.C1714.Angle=360.00 
App.ActiveDocument.C1714.Placement=Base.Placement(Base.Vector(-36.435272,-180.947151,508.021929),Base.Rotation(0.705371,-0.017447,0.000000,0.708624))
App.ActiveDocument.addObject("Part::Cylinder","C1715")
App.ActiveDocument.C1715.Radius=0.750000
App.ActiveDocument.C1715.Height=15.00
App.ActiveDocument.C1715.Angle=360.00 
App.ActiveDocument.C1715.Placement=Base.Placement(Base.Vector(-36.521110,-180.855545,504.645079),Base.Rotation(0.726362,-0.009335,0.000000,0.687248))
App.ActiveDocument.addObject("Part::Cylinder","C1716")
App.ActiveDocument.C1716.Radius=0.750000
App.ActiveDocument.C1716.Height=15.00
App.ActiveDocument.C1716.Angle=360.00 
App.ActiveDocument.C1716.Placement=Base.Placement(Base.Vector(-36.661335,-180.559372,501.177991),Base.Rotation(0.746059,-0.001015,0.000000,0.665880))
App.ActiveDocument.addObject("Part::Cylinder","C1717")
App.ActiveDocument.C1717.Radius=0.750000
App.ActiveDocument.C1717.Height=15.00
App.ActiveDocument.C1717.Angle=360.00 
App.ActiveDocument.C1717.Placement=Base.Placement(Base.Vector(-36.805869,-180.077166,497.791278),Base.Rotation(0.764052,0.007130,0.000000,0.645116))
App.ActiveDocument.addObject("Part::Cylinder","C1718")
App.ActiveDocument.C1718.Radius=0.750000
App.ActiveDocument.C1718.Height=15.00
App.ActiveDocument.C1718.Angle=360.00 
App.ActiveDocument.C1718.Placement=Base.Placement(Base.Vector(-36.836120,-179.416119,494.444110),Base.Rotation(0.780737,0.016658,0.000000,0.624638))
App.ActiveDocument.addObject("Part::Cylinder","C1719")
App.ActiveDocument.C1719.Radius=0.750000
App.ActiveDocument.C1719.Height=15.00
App.ActiveDocument.C1719.Angle=360.00 
App.ActiveDocument.C1719.Placement=Base.Placement(Base.Vector(-37.016972,-178.587517,491.137297),Base.Rotation(0.796028,0.021930,0.000000,0.604862))
App.ActiveDocument.addObject("Part::Cylinder","C1720")
App.ActiveDocument.C1720.Radius=0.750000
App.ActiveDocument.C1720.Height=15.00
App.ActiveDocument.C1720.Angle=360.00 
App.ActiveDocument.C1720.Placement=Base.Placement(Base.Vector(-37.025081,-177.571775,487.837580),Base.Rotation(0.812277,0.030635,0.000000,0.582467))
App.ActiveDocument.addObject("Part::Cylinder","C1721")
App.ActiveDocument.C1721.Radius=0.750000
App.ActiveDocument.C1721.Height=15.00
App.ActiveDocument.C1721.Angle=360.00 
App.ActiveDocument.C1721.Placement=Base.Placement(Base.Vector(-37.097714,-176.362548,484.534383),Base.Rotation(0.826832,0.037795,0.000000,0.561178))
App.ActiveDocument.addObject("Part::Cylinder","C1722")
App.ActiveDocument.C1722.Radius=0.750000
App.ActiveDocument.C1722.Height=15.00
App.ActiveDocument.C1722.Angle=360.00 
App.ActiveDocument.C1722.Placement=Base.Placement(Base.Vector(-37.167228,-175.002960,481.366591),Base.Rotation(0.841702,0.049409,0.000000,0.537677))
App.ActiveDocument.addObject("Part::Cylinder","C1723")
App.ActiveDocument.C1723.Radius=0.750000
App.ActiveDocument.C1723.Height=15.00
App.ActiveDocument.C1723.Angle=360.00 
App.ActiveDocument.C1723.Placement=Base.Placement(Base.Vector(-37.259749,-173.463911,478.263797),Base.Rotation(0.855183,0.061018,0.000000,0.514722))
App.ActiveDocument.addObject("Part::Cylinder","C1724")
App.ActiveDocument.C1724.Radius=0.750000
App.ActiveDocument.C1724.Height=15.00
App.ActiveDocument.C1724.Angle=360.00 
App.ActiveDocument.C1724.Placement=Base.Placement(Base.Vector(-37.299504,-171.745529,475.257180),Base.Rotation(0.869296,0.071158,0.000000,0.489143))
App.ActiveDocument.addObject("Part::Cylinder","C1725")
App.ActiveDocument.C1725.Radius=0.750000
App.ActiveDocument.C1725.Height=15.00
App.ActiveDocument.C1725.Angle=360.00 
App.ActiveDocument.C1725.Placement=Base.Placement(Base.Vector(-37.456441,-169.926144,472.460408),Base.Rotation(0.882415,0.083265,0.000000,0.463044))
App.ActiveDocument.addObject("Part::Cylinder","C1726")
App.ActiveDocument.C1726.Radius=0.750000
App.ActiveDocument.C1726.Height=15.00
App.ActiveDocument.C1726.Angle=360.00 
App.ActiveDocument.C1726.Placement=Base.Placement(Base.Vector(-37.497087,-167.983028,469.859451),Base.Rotation(0.895352,0.100014,0.000000,0.433983))
App.ActiveDocument.addObject("Part::Cylinder","C1727")
App.ActiveDocument.C1727.Radius=0.750000
App.ActiveDocument.C1727.Height=15.00
App.ActiveDocument.C1727.Angle=360.00 
App.ActiveDocument.C1727.Placement=Base.Placement(Base.Vector(-37.576907,-166.300725,467.859640),Base.Rotation(0.905314,0.113369,0.000000,0.409334))
App.ActiveDocument.addObject("Part::Cylinder","C1728")
App.ActiveDocument.C1728.Radius=0.750000
App.ActiveDocument.C1728.Height=15.00
App.ActiveDocument.C1728.Angle=360.00 
App.ActiveDocument.C1728.Placement=Base.Placement(Base.Vector(-38.189918,-144.445611,547.569242),Base.Rotation(0.026022,-0.116338,0.000000,0.992869))
App.ActiveDocument.addObject("Part::Cylinder","C1729")
App.ActiveDocument.C1729.Radius=0.750000
App.ActiveDocument.C1729.Height=15.00
App.ActiveDocument.C1729.Angle=360.00 
App.ActiveDocument.C1729.Placement=Base.Placement(Base.Vector(-38.223453,-147.824190,547.281289),Base.Rotation(0.055255,-0.116003,0.000000,0.991711))
App.ActiveDocument.addObject("Part::Cylinder","C1730")
App.ActiveDocument.C1730.Radius=0.750000
App.ActiveDocument.C1730.Height=15.00
App.ActiveDocument.C1730.Angle=360.00 
App.ActiveDocument.C1730.Placement=Base.Placement(Base.Vector(-38.134231,-151.194548,546.807687),Base.Rotation(0.088098,-0.114510,0.000000,0.989508))
App.ActiveDocument.addObject("Part::Cylinder","C1731")
App.ActiveDocument.C1731.Radius=0.750000
App.ActiveDocument.C1731.Height=15.00
App.ActiveDocument.C1731.Angle=360.00 
App.ActiveDocument.C1731.Placement=Base.Placement(Base.Vector(-38.368943,-154.448623,546.035836),Base.Rotation(0.124262,-0.116924,0.000000,0.985336))
App.ActiveDocument.addObject("Part::Cylinder","C1732")
App.ActiveDocument.C1732.Radius=0.750000
App.ActiveDocument.C1732.Height=15.00
App.ActiveDocument.C1732.Angle=360.00 
App.ActiveDocument.C1732.Placement=Base.Placement(Base.Vector(-38.276257,-157.598250,545.102423),Base.Rotation(0.164477,-0.113968,0.000000,0.979775))
App.ActiveDocument.addObject("Part::Cylinder","C1733")
App.ActiveDocument.C1733.Radius=0.750000
App.ActiveDocument.C1733.Height=15.00
App.ActiveDocument.C1733.Angle=360.00 
App.ActiveDocument.C1733.Placement=Base.Placement(Base.Vector(-38.359995,-160.490046,543.932518),Base.Rotation(0.203979,-0.114671,0.000000,0.972236))
App.ActiveDocument.addObject("Part::Cylinder","C1734")
App.ActiveDocument.C1734.Radius=0.750000
App.ActiveDocument.C1734.Height=15.00
App.ActiveDocument.C1734.Angle=360.00 
App.ActiveDocument.C1734.Placement=Base.Placement(Base.Vector(-38.333905,-163.228350,542.562288),Base.Rotation(0.248119,-0.112390,0.000000,0.962188))
App.ActiveDocument.addObject("Part::Cylinder","C1735")
App.ActiveDocument.C1735.Radius=0.750000
App.ActiveDocument.C1735.Height=15.00
App.ActiveDocument.C1735.Angle=360.00 
App.ActiveDocument.C1735.Placement=Base.Placement(Base.Vector(-38.389378,-165.795059,540.940657),Base.Rotation(0.293110,-0.110576,0.000000,0.949663))
App.ActiveDocument.addObject("Part::Cylinder","C1736")
App.ActiveDocument.C1736.Radius=0.750000
App.ActiveDocument.C1736.Height=15.00
App.ActiveDocument.C1736.Angle=360.00 
App.ActiveDocument.C1736.Placement=Base.Placement(Base.Vector(-38.629550,-168.174707,539.046739),Base.Rotation(0.339561,-0.113199,0.000000,0.933747))
App.ActiveDocument.addObject("Part::Cylinder","C1737")
App.ActiveDocument.C1737.Radius=0.750000
App.ActiveDocument.C1737.Height=15.00
App.ActiveDocument.C1737.Angle=360.00 
App.ActiveDocument.C1737.Placement=Base.Placement(Base.Vector(-38.635748,-170.373636,536.980852),Base.Rotation(0.386140,-0.109255,0.000000,0.915947))
App.ActiveDocument.addObject("Part::Cylinder","C1738")
App.ActiveDocument.C1738.Radius=0.750000
App.ActiveDocument.C1738.Height=15.00
App.ActiveDocument.C1738.Angle=360.00 
App.ActiveDocument.C1738.Placement=Base.Placement(Base.Vector(-38.684410,-172.363244,534.698220),Base.Rotation(0.427640,-0.102064,0.000000,0.898169))
App.ActiveDocument.addObject("Part::Cylinder","C1739")
App.ActiveDocument.C1739.Radius=0.750000
App.ActiveDocument.C1739.Height=15.00
App.ActiveDocument.C1739.Angle=360.00 
App.ActiveDocument.C1739.Placement=Base.Placement(Base.Vector(-38.877136,-174.119125,532.213710),Base.Rotation(0.468474,-0.102085,0.000000,0.877560))
App.ActiveDocument.addObject("Part::Cylinder","C1740")
App.ActiveDocument.C1740.Radius=0.750000
App.ActiveDocument.C1740.Height=15.00
App.ActiveDocument.C1740.Angle=360.00 
App.ActiveDocument.C1740.Placement=Base.Placement(Base.Vector(-38.975914,-175.703302,529.510146),Base.Rotation(0.507874,-0.096537,0.000000,0.856005))
App.ActiveDocument.addObject("Part::Cylinder","C1741")
App.ActiveDocument.C1741.Radius=0.750000
App.ActiveDocument.C1741.Height=15.00
App.ActiveDocument.C1741.Angle=360.00 
App.ActiveDocument.C1741.Placement=Base.Placement(Base.Vector(-39.000525,-177.066890,526.679628),Base.Rotation(0.543276,-0.091235,0.000000,0.834582))
App.ActiveDocument.addObject("Part::Cylinder","C1742")
App.ActiveDocument.C1742.Radius=0.750000
App.ActiveDocument.C1742.Height=15.00
App.ActiveDocument.C1742.Angle=360.00 
App.ActiveDocument.C1742.Placement=Base.Placement(Base.Vector(-39.276518,-178.163746,523.740859),Base.Rotation(0.574943,-0.089242,0.000000,0.813312))
App.ActiveDocument.addObject("Part::Cylinder","C1743")
App.ActiveDocument.C1743.Radius=0.750000
App.ActiveDocument.C1743.Height=15.00
App.ActiveDocument.C1743.Angle=360.00 
App.ActiveDocument.C1743.Placement=Base.Placement(Base.Vector(-39.289970,-179.112809,520.623596),Base.Rotation(0.605870,-0.081079,0.000000,0.791421))
App.ActiveDocument.addObject("Part::Cylinder","C1744")
App.ActiveDocument.C1744.Radius=0.750000
App.ActiveDocument.C1744.Height=15.00
App.ActiveDocument.C1744.Angle=360.00 
App.ActiveDocument.C1744.Placement=Base.Placement(Base.Vector(-39.390036,-179.843343,517.375313),Base.Rotation(0.632294,-0.079808,0.000000,0.770607))
App.ActiveDocument.addObject("Part::Cylinder","C1745")
App.ActiveDocument.C1745.Radius=0.750000
App.ActiveDocument.C1745.Height=15.00
App.ActiveDocument.C1745.Angle=360.00 
App.ActiveDocument.C1745.Placement=Base.Placement(Base.Vector(-39.446253,-180.365167,514.054256),Base.Rotation(0.657367,-0.072492,0.000000,0.750076))
App.ActiveDocument.addObject("Part::Cylinder","C1746")
App.ActiveDocument.C1746.Radius=0.750000
App.ActiveDocument.C1746.Height=15.00
App.ActiveDocument.C1746.Angle=360.00 
App.ActiveDocument.C1746.Placement=Base.Placement(Base.Vector(-39.649304,-180.660396,510.704501),Base.Rotation(0.680939,-0.069653,0.000000,0.729020))
App.ActiveDocument.addObject("Part::Cylinder","C1747")
App.ActiveDocument.C1747.Radius=0.750000
App.ActiveDocument.C1747.Height=15.00
App.ActiveDocument.C1747.Angle=360.00 
App.ActiveDocument.C1747.Placement=Base.Placement(Base.Vector(-39.808338,-180.761225,507.336716),Base.Rotation(0.702115,-0.064677,0.000000,0.709120))
App.ActiveDocument.addObject("Part::Cylinder","C1748")
App.ActiveDocument.C1748.Radius=0.750000
App.ActiveDocument.C1748.Height=15.00
App.ActiveDocument.C1748.Angle=360.00 
App.ActiveDocument.C1748.Placement=Base.Placement(Base.Vector(-39.890177,-180.673085,503.962979),Base.Rotation(0.722975,-0.056167,0.000000,0.688587))
App.ActiveDocument.addObject("Part::Cylinder","C1749")
App.ActiveDocument.C1749.Radius=0.750000
App.ActiveDocument.C1749.Height=15.00
App.ActiveDocument.C1749.Angle=360.00 
App.ActiveDocument.C1749.Placement=Base.Placement(Base.Vector(-40.018655,-180.387664,500.542019),Base.Rotation(0.743690,-0.044696,0.000000,0.667029))
App.ActiveDocument.addObject("Part::Cylinder","C1750")
App.ActiveDocument.C1750.Radius=0.750000
App.ActiveDocument.C1750.Height=15.00
App.ActiveDocument.C1750.Angle=360.00 
App.ActiveDocument.C1750.Placement=Base.Placement(Base.Vector(-40.196693,-179.921258,497.220108),Base.Rotation(0.761433,-0.036762,0.000000,0.647200))
App.ActiveDocument.addObject("Part::Cylinder","C1751")
App.ActiveDocument.C1751.Radius=0.750000
App.ActiveDocument.C1751.Height=15.00
App.ActiveDocument.C1751.Angle=360.00 
App.ActiveDocument.C1751.Placement=Base.Placement(Base.Vector(-40.263383,-179.289239,493.950640),Base.Rotation(0.778854,-0.026214,0.000000,0.626657))
App.ActiveDocument.addObject("Part::Cylinder","C1752")
App.ActiveDocument.C1752.Radius=0.750000
App.ActiveDocument.C1752.Height=15.00
App.ActiveDocument.C1752.Angle=360.00 
App.ActiveDocument.C1752.Placement=Base.Placement(Base.Vector(-40.466305,-178.449685,490.602535),Base.Rotation(0.796377,-0.018122,0.000000,0.604529))
App.ActiveDocument.addObject("Part::Cylinder","C1753")
App.ActiveDocument.C1753.Radius=0.750000
App.ActiveDocument.C1753.Height=15.00
App.ActiveDocument.C1753.Angle=360.00 
App.ActiveDocument.C1753.Placement=Base.Placement(Base.Vector(-40.539257,-177.428519,487.282681),Base.Rotation(0.811659,-0.012627,0.000000,0.583995))
App.ActiveDocument.addObject("Part::Cylinder","C1754")
App.ActiveDocument.C1754.Radius=0.750000
App.ActiveDocument.C1754.Height=15.00
App.ActiveDocument.C1754.Angle=360.00 
App.ActiveDocument.C1754.Placement=Base.Placement(Base.Vector(-40.618090,-176.239140,484.037748),Base.Rotation(0.827097,-0.004056,0.000000,0.562045))
App.ActiveDocument.addObject("Part::Cylinder","C1755")
App.ActiveDocument.C1755.Radius=0.750000
App.ActiveDocument.C1755.Height=15.00
App.ActiveDocument.C1755.Angle=360.00 
App.ActiveDocument.C1755.Placement=Base.Placement(Base.Vector(-40.706758,-174.894508,480.898983),Base.Rotation(0.841554,-0.000016,0.000000,0.540174))
App.ActiveDocument.addObject("Part::Cylinder","C1756")
App.ActiveDocument.C1756.Radius=0.750000
App.ActiveDocument.C1756.Height=15.00
App.ActiveDocument.C1756.Angle=360.00 
App.ActiveDocument.C1756.Placement=Base.Placement(Base.Vector(-40.772670,-173.394660,477.866144),Base.Rotation(0.856064,0.008706,0.000000,0.516796))
App.ActiveDocument.addObject("Part::Cylinder","C1757")
App.ActiveDocument.C1757.Radius=0.750000
App.ActiveDocument.C1757.Height=15.00
App.ActiveDocument.C1757.Angle=360.00 
App.ActiveDocument.C1757.Placement=Base.Placement(Base.Vector(-40.805955,-171.732388,474.936704),Base.Rotation(0.871472,0.019039,0.000000,0.490076))
App.ActiveDocument.addObject("Part::Cylinder","C1758")
App.ActiveDocument.C1758.Radius=0.750000
App.ActiveDocument.C1758.Height=15.00
App.ActiveDocument.C1758.Angle=360.00 
App.ActiveDocument.C1758.Placement=Base.Placement(Base.Vector(-40.961092,-169.881684,472.085280),Base.Rotation(0.886258,0.027495,0.000000,0.462376))
App.ActiveDocument.addObject("Part::Cylinder","C1759")
App.ActiveDocument.C1759.Radius=0.750000
App.ActiveDocument.C1759.Height=15.00
App.ActiveDocument.C1759.Angle=360.00 
App.ActiveDocument.C1759.Placement=Base.Placement(Base.Vector(-40.979365,-167.925102,469.455613),Base.Rotation(0.900193,0.037965,0.000000,0.433834))
App.ActiveDocument.addObject("Part::Cylinder","C1760")
App.ActiveDocument.C1760.Radius=0.750000
App.ActiveDocument.C1760.Height=15.00
App.ActiveDocument.C1760.Angle=360.00 
App.ActiveDocument.C1760.Placement=Base.Placement(Base.Vector(-41.195066,-166.333984,467.546821),Base.Rotation(0.909951,0.042348,0.000000,0.412548))
App.ActiveDocument.addObject("Part::Cylinder","C1761")
App.ActiveDocument.C1761.Radius=0.750000
App.ActiveDocument.C1761.Height=15.00
App.ActiveDocument.C1761.Angle=360.00 
App.ActiveDocument.C1761.Placement=Base.Placement(Base.Vector(-41.364072,-144.377239,546.699248),Base.Rotation(0.025129,-0.150924,0.000000,0.988226))
App.ActiveDocument.addObject("Part::Cylinder","C1762")
App.ActiveDocument.C1762.Radius=0.750000
App.ActiveDocument.C1762.Height=15.00
App.ActiveDocument.C1762.Angle=360.00 
App.ActiveDocument.C1762.Placement=Base.Placement(Base.Vector(-41.398852,-147.763238,546.408310),Base.Rotation(0.054391,-0.150724,0.000000,0.987078))
App.ActiveDocument.addObject("Part::Cylinder","C1763")
App.ActiveDocument.C1763.Radius=0.750000
App.ActiveDocument.C1763.Height=15.00
App.ActiveDocument.C1763.Angle=360.00 
App.ActiveDocument.C1763.Placement=Base.Placement(Base.Vector(-41.316583,-151.105579,545.943413),Base.Rotation(0.087120,-0.150717,0.000000,0.984731))
App.ActiveDocument.addObject("Part::Cylinder","C1764")
App.ActiveDocument.C1764.Radius=0.750000
App.ActiveDocument.C1764.Height=15.00
App.ActiveDocument.C1764.Angle=360.00 
App.ActiveDocument.C1764.Placement=Base.Placement(Base.Vector(-41.559288,-154.252744,545.174506),Base.Rotation(0.121605,-0.153226,0.000000,0.980680))
App.ActiveDocument.addObject("Part::Cylinder","C1765")
App.ActiveDocument.C1765.Radius=0.750000
App.ActiveDocument.C1765.Height=15.00
App.ActiveDocument.C1765.Angle=360.00 
App.ActiveDocument.C1765.Placement=Base.Placement(Base.Vector(-41.376941,-157.355929,544.294383),Base.Rotation(0.161762,-0.151764,0.000000,0.975090))
App.ActiveDocument.addObject("Part::Cylinder","C1766")
App.ActiveDocument.C1766.Radius=0.750000
App.ActiveDocument.C1766.Height=15.00
App.ActiveDocument.C1766.Angle=360.00 
App.ActiveDocument.C1766.Placement=Base.Placement(Base.Vector(-41.525488,-160.328499,543.065214),Base.Rotation(0.203615,-0.152839,0.000000,0.967048))
App.ActiveDocument.addObject("Part::Cylinder","C1767")
App.ActiveDocument.C1767.Radius=0.750000
App.ActiveDocument.C1767.Height=15.00
App.ActiveDocument.C1767.Angle=360.00 
App.ActiveDocument.C1767.Placement=Base.Placement(Base.Vector(-41.466911,-163.128451,541.663827),Base.Rotation(0.247527,-0.153073,0.000000,0.956713))
App.ActiveDocument.addObject("Part::Cylinder","C1768")
App.ActiveDocument.C1768.Radius=0.750000
App.ActiveDocument.C1768.Height=15.00
App.ActiveDocument.C1768.Angle=360.00 
App.ActiveDocument.C1768.Placement=Base.Placement(Base.Vector(-41.546064,-165.675406,540.024300),Base.Rotation(0.291484,-0.152534,0.000000,0.944336))
App.ActiveDocument.addObject("Part::Cylinder","C1769")
App.ActiveDocument.C1769.Radius=0.750000
App.ActiveDocument.C1769.Height=15.00
App.ActiveDocument.C1769.Angle=360.00 
App.ActiveDocument.C1769.Placement=Base.Placement(Base.Vector(-41.745713,-168.028771,538.115690),Base.Rotation(0.335013,-0.152984,0.000000,0.929711))
App.ActiveDocument.addObject("Part::Cylinder","C1770")
App.ActiveDocument.C1770.Radius=0.750000
App.ActiveDocument.C1770.Height=15.00
App.ActiveDocument.C1770.Angle=360.00 
App.ActiveDocument.C1770.Placement=Base.Placement(Base.Vector(-41.797250,-170.227809,536.003061),Base.Rotation(0.379937,-0.154056,0.000000,0.912094))
App.ActiveDocument.addObject("Part::Cylinder","C1771")
App.ActiveDocument.C1771.Radius=0.750000
App.ActiveDocument.C1771.Height=15.00
App.ActiveDocument.C1771.Angle=360.00 
App.ActiveDocument.C1771.Placement=Base.Placement(Base.Vector(-41.811879,-172.173102,533.752545),Base.Rotation(0.423177,-0.149475,0.000000,0.893632))
App.ActiveDocument.addObject("Part::Cylinder","C1772")
App.ActiveDocument.C1772.Radius=0.750000
App.ActiveDocument.C1772.Height=15.00
App.ActiveDocument.C1772.Angle=360.00 
App.ActiveDocument.C1772.Placement=Base.Placement(Base.Vector(-41.994420,-173.917507,531.224144),Base.Rotation(0.464073,-0.149358,0.000000,0.873114))
App.ActiveDocument.addObject("Part::Cylinder","C1773")
App.ActiveDocument.C1773.Radius=0.750000
App.ActiveDocument.C1773.Height=15.00
App.ActiveDocument.C1773.Angle=360.00 
App.ActiveDocument.C1773.Placement=Base.Placement(Base.Vector(-42.056022,-175.449520,528.584704),Base.Rotation(0.501928,-0.146047,0.000000,0.852490))
App.ActiveDocument.addObject("Part::Cylinder","C1774")
App.ActiveDocument.C1774.Radius=0.750000
App.ActiveDocument.C1774.Height=15.00
App.ActiveDocument.C1774.Angle=360.00 
App.ActiveDocument.C1774.Placement=Base.Placement(Base.Vector(-42.178696,-176.780994,525.735857),Base.Rotation(0.534935,-0.145267,0.000000,0.832311))
App.ActiveDocument.addObject("Part::Cylinder","C1775")
App.ActiveDocument.C1775.Radius=0.750000
App.ActiveDocument.C1775.Height=15.00
App.ActiveDocument.C1775.Angle=360.00 
App.ActiveDocument.C1775.Placement=Base.Placement(Base.Vector(-42.383344,-177.874823,522.753451),Base.Rotation(0.567919,-0.141928,0.000000,0.810756))
App.ActiveDocument.addObject("Part::Cylinder","C1776")
App.ActiveDocument.C1776.Radius=0.750000
App.ActiveDocument.C1776.Height=15.00
App.ActiveDocument.C1776.Angle=360.00 
App.ActiveDocument.C1776.Placement=Base.Placement(Base.Vector(-42.402073,-178.820697,519.588732),Base.Rotation(0.597902,-0.136809,0.000000,0.789808))
App.ActiveDocument.addObject("Part::Cylinder","C1777")
App.ActiveDocument.C1777.Radius=0.750000
App.ActiveDocument.C1777.Height=15.00
App.ActiveDocument.C1777.Angle=360.00 
App.ActiveDocument.C1777.Placement=Base.Placement(Base.Vector(-42.539356,-179.501935,516.417611),Base.Rotation(0.624871,-0.130519,0.000000,0.769741))
App.ActiveDocument.addObject("Part::Cylinder","C1778")
App.ActiveDocument.C1778.Radius=0.750000
App.ActiveDocument.C1778.Height=15.00
App.ActiveDocument.C1778.Angle=360.00 
App.ActiveDocument.C1778.Placement=Base.Placement(Base.Vector(-42.660924,-179.987748,513.159296),Base.Rotation(0.650009,-0.128120,0.000000,0.749049))
App.ActiveDocument.addObject("Part::Cylinder","C1779")
App.ActiveDocument.C1779.Radius=0.750000
App.ActiveDocument.C1779.Height=15.00
App.ActiveDocument.C1779.Angle=360.00 
App.ActiveDocument.C1779.Placement=Base.Placement(Base.Vector(-42.891065,-180.257713,509.805833),Base.Rotation(0.672333,-0.125799,0.000000,0.729481))
App.ActiveDocument.addObject("Part::Cylinder","C1780")
App.ActiveDocument.C1780.Radius=0.750000
App.ActiveDocument.C1780.Height=15.00
App.ActiveDocument.C1780.Angle=360.00 
App.ActiveDocument.C1780.Placement=Base.Placement(Base.Vector(-42.991636,-180.354712,506.451260),Base.Rotation(0.694084,-0.117190,0.000000,0.710291))
App.ActiveDocument.addObject("Part::Cylinder","C1781")
App.ActiveDocument.C1781.Radius=0.750000
App.ActiveDocument.C1781.Height=15.00
App.ActiveDocument.C1781.Angle=360.00 
App.ActiveDocument.C1781.Placement=Base.Placement(Base.Vector(-43.095517,-180.259384,503.072188),Base.Rotation(0.716376,-0.112870,0.000000,0.688524))
App.ActiveDocument.addObject("Part::Cylinder","C1782")
App.ActiveDocument.C1782.Radius=0.750000
App.ActiveDocument.C1782.Height=15.00
App.ActiveDocument.C1782.Angle=360.00 
App.ActiveDocument.C1782.Placement=Base.Placement(Base.Vector(-43.206001,-179.979031,499.718221),Base.Rotation(0.735712,-0.105056,0.000000,0.669097))
App.ActiveDocument.addObject("Part::Cylinder","C1783")
App.ActiveDocument.C1783.Radius=0.750000
App.ActiveDocument.C1783.Height=15.00
App.ActiveDocument.C1783.Angle=360.00 
App.ActiveDocument.C1783.Placement=Base.Placement(Base.Vector(-43.470604,-179.490921,496.339446),Base.Rotation(0.754377,-0.100109,0.000000,0.648763))
App.ActiveDocument.addObject("Part::Cylinder","C1784")
App.ActiveDocument.C1784.Radius=0.750000
App.ActiveDocument.C1784.Height=15.00
App.ActiveDocument.C1784.Angle=360.00 
App.ActiveDocument.C1784.Placement=Base.Placement(Base.Vector(-43.492413,-178.872453,493.081801),Base.Rotation(0.773654,-0.084269,0.000000,0.627979))
App.ActiveDocument.addObject("Part::Cylinder","C1785")
App.ActiveDocument.C1785.Radius=0.750000
App.ActiveDocument.C1785.Height=15.00
App.ActiveDocument.C1785.Angle=360.00 
App.ActiveDocument.C1785.Placement=Base.Placement(Base.Vector(-43.752320,-178.037374,489.797640),Base.Rotation(0.791036,-0.075625,0.000000,0.607077))
App.ActiveDocument.addObject("Part::Cylinder","C1786")
App.ActiveDocument.C1786.Radius=0.750000
App.ActiveDocument.C1786.Height=15.00
App.ActiveDocument.C1786.Angle=360.00 
App.ActiveDocument.C1786.Placement=Base.Placement(Base.Vector(-43.927290,-177.028104,486.538730),Base.Rotation(0.809161,-0.064773,0.000000,0.584006))
App.ActiveDocument.addObject("Part::Cylinder","C1787")
App.ActiveDocument.C1787.Radius=0.750000
App.ActiveDocument.C1787.Height=15.00
App.ActiveDocument.C1787.Angle=360.00 
App.ActiveDocument.C1787.Placement=Base.Placement(Base.Vector(-43.988790,-175.863078,483.368297),Base.Rotation(0.825154,-0.052971,0.000000,0.562419))
App.ActiveDocument.addObject("Part::Cylinder","C1788")
App.ActiveDocument.C1788.Radius=0.750000
App.ActiveDocument.C1788.Height=15.00
App.ActiveDocument.C1788.Angle=360.00 
App.ActiveDocument.C1788.Placement=Base.Placement(Base.Vector(-44.238947,-174.523855,480.290286),Base.Rotation(0.840237,-0.049365,0.000000,0.539967))
App.ActiveDocument.addObject("Part::Cylinder","C1789")
App.ActiveDocument.C1789.Radius=0.750000
App.ActiveDocument.C1789.Height=15.00
App.ActiveDocument.C1789.Angle=360.00 
App.ActiveDocument.C1789.Placement=Base.Placement(Base.Vector(-44.301525,-173.015894,477.267637),Base.Rotation(0.855924,-0.041344,0.000000,0.515447))
App.ActiveDocument.addObject("Part::Cylinder","C1790")
App.ActiveDocument.C1790.Radius=0.750000
App.ActiveDocument.C1790.Height=15.00
App.ActiveDocument.C1790.Angle=360.00 
App.ActiveDocument.C1790.Placement=Base.Placement(Base.Vector(-44.349414,-171.348876,474.356711),Base.Rotation(0.871619,-0.036017,0.000000,0.488860))
App.ActiveDocument.addObject("Part::Cylinder","C1791")
App.ActiveDocument.C1791.Radius=0.750000
App.ActiveDocument.C1791.Height=15.00
App.ActiveDocument.C1791.Angle=360.00 
App.ActiveDocument.C1791.Placement=Base.Placement(Base.Vector(-44.410537,-169.526345,471.577778),Base.Rotation(0.886526,-0.029972,0.000000,0.461707))
App.ActiveDocument.addObject("Part::Cylinder","C1792")
App.ActiveDocument.C1792.Radius=0.750000
App.ActiveDocument.C1792.Height=15.00
App.ActiveDocument.C1792.Angle=360.00 
App.ActiveDocument.C1792.Placement=Base.Placement(Base.Vector(-44.669834,-167.567192,468.976090),Base.Rotation(0.901418,-0.026512,0.000000,0.432138))
App.ActiveDocument.addObject("Part::Cylinder","C1793")
App.ActiveDocument.C1793.Radius=0.750000
App.ActiveDocument.C1793.Height=15.00
App.ActiveDocument.C1793.Angle=360.00 
App.ActiveDocument.C1793.Placement=Base.Placement(Base.Vector(-44.522594,-144.400078,545.591967),Base.Rotation(0.025647,-0.184030,0.000000,0.982586))
App.ActiveDocument.addObject("Part::Cylinder","C1794")
App.ActiveDocument.C1794.Radius=0.750000
App.ActiveDocument.C1794.Height=15.00
App.ActiveDocument.C1794.Angle=360.00 
App.ActiveDocument.C1794.Placement=Base.Placement(Base.Vector(-44.490563,-147.835147,545.312605),Base.Rotation(0.054917,-0.183996,0.000000,0.981392))
App.ActiveDocument.addObject("Part::Cylinder","C1795")
App.ActiveDocument.C1795.Radius=0.750000
App.ActiveDocument.C1795.Height=15.00
App.ActiveDocument.C1795.Angle=360.00 
App.ActiveDocument.C1795.Placement=Base.Placement(Base.Vector(-44.501183,-151.151851,544.806059),Base.Rotation(0.087937,-0.184106,0.000000,0.978965))
App.ActiveDocument.addObject("Part::Cylinder","C1796")
App.ActiveDocument.C1796.Radius=0.750000
App.ActiveDocument.C1796.Height=15.00
App.ActiveDocument.C1796.Angle=360.00 
App.ActiveDocument.C1796.Placement=Base.Placement(Base.Vector(-44.699825,-154.320559,544.008053),Base.Rotation(0.122721,-0.187186,0.000000,0.974629))
App.ActiveDocument.addObject("Part::Cylinder","C1797")
App.ActiveDocument.C1797.Radius=0.750000
App.ActiveDocument.C1797.Height=15.00
App.ActiveDocument.C1797.Angle=360.00 
App.ActiveDocument.C1797.Placement=Base.Placement(Base.Vector(-44.480528,-157.418498,543.131258),Base.Rotation(0.162948,-0.184107,0.000000,0.969305))
App.ActiveDocument.addObject("Part::Cylinder","C1798")
App.ActiveDocument.C1798.Radius=0.750000
App.ActiveDocument.C1798.Height=15.00
App.ActiveDocument.C1798.Angle=360.00 
App.ActiveDocument.C1798.Placement=Base.Placement(Base.Vector(-44.657454,-160.336588,541.860386),Base.Rotation(0.202879,-0.187704,0.000000,0.961045))
App.ActiveDocument.addObject("Part::Cylinder","C1799")
App.ActiveDocument.C1799.Radius=0.750000
App.ActiveDocument.C1799.Height=15.00
App.ActiveDocument.C1799.Angle=360.00 
App.ActiveDocument.C1799.Placement=Base.Placement(Base.Vector(-44.613687,-163.122365,540.422287),Base.Rotation(0.251374,-0.186937,0.000000,0.949666))
App.ActiveDocument.addObject("Part::Cylinder","C1800")
App.ActiveDocument.C1800.Radius=0.750000
App.ActiveDocument.C1800.Height=15.00
App.ActiveDocument.C1800.Angle=360.00 
App.ActiveDocument.C1800.Placement=Base.Placement(Base.Vector(-44.786482,-165.633218,538.696175),Base.Rotation(0.291856,-0.192249,0.000000,0.936942))
App.ActiveDocument.addObject("Part::Cylinder","C1801")
App.ActiveDocument.C1801.Radius=0.750000
App.ActiveDocument.C1801.Height=15.00
App.ActiveDocument.C1801.Angle=360.00 
App.ActiveDocument.C1801.Placement=Base.Placement(Base.Vector(-44.854260,-167.957177,536.788097),Base.Rotation(0.338009,-0.189168,0.000000,0.921936))
App.ActiveDocument.addObject("Part::Cylinder","C1802")
App.ActiveDocument.C1802.Radius=0.750000
App.ActiveDocument.C1802.Height=15.00
App.ActiveDocument.C1802.Angle=360.00 
App.ActiveDocument.C1802.Placement=Base.Placement(Base.Vector(-44.974856,-170.026555,534.688973),Base.Rotation(0.381077,-0.192106,0.000000,0.904365))
App.ActiveDocument.addObject("Part::Cylinder","C1803")
App.ActiveDocument.C1803.Radius=0.750000
App.ActiveDocument.C1803.Height=15.00
App.ActiveDocument.C1803.Angle=360.00 
App.ActiveDocument.C1803.Placement=Base.Placement(Base.Vector(-44.933164,-171.969782,532.394403),Base.Rotation(0.422072,-0.189580,0.000000,0.886518))
App.ActiveDocument.addObject("Part::Cylinder","C1804")
App.ActiveDocument.C1804.Radius=0.750000
App.ActiveDocument.C1804.Height=15.00
App.ActiveDocument.C1804.Angle=360.00 
App.ActiveDocument.C1804.Placement=Base.Placement(Base.Vector(-45.183119,-173.590951,529.892674),Base.Rotation(0.460553,-0.191085,0.000000,0.866820))
App.ActiveDocument.addObject("Part::Cylinder","C1805")
App.ActiveDocument.C1805.Radius=0.750000
App.ActiveDocument.C1805.Height=15.00
App.ActiveDocument.C1805.Angle=360.00 
App.ActiveDocument.C1805.Placement=Base.Placement(Base.Vector(-45.186088,-175.102039,527.237601),Base.Rotation(0.497644,-0.188431,0.000000,0.846666))
App.ActiveDocument.addObject("Part::Cylinder","C1806")
App.ActiveDocument.C1806.Radius=0.750000
App.ActiveDocument.C1806.Height=15.00
App.ActiveDocument.C1806.Angle=360.00 
App.ActiveDocument.C1806.Placement=Base.Placement(Base.Vector(-45.399050,-176.333309,524.415005),Base.Rotation(0.530091,-0.190721,0.000000,0.826213))
App.ActiveDocument.addObject("Part::Cylinder","C1807")
App.ActiveDocument.C1807.Radius=0.750000
App.ActiveDocument.C1807.Height=15.00
App.ActiveDocument.C1807.Angle=360.00 
App.ActiveDocument.C1807.Placement=Base.Placement(Base.Vector(-45.482259,-177.432270,521.380597),Base.Rotation(0.562745,-0.187216,0.000000,0.805151))
App.ActiveDocument.addObject("Part::Cylinder","C1808")
App.ActiveDocument.C1808.Radius=0.750000
App.ActiveDocument.C1808.Height=15.00
App.ActiveDocument.C1808.Angle=360.00 
App.ActiveDocument.C1808.Placement=Base.Placement(Base.Vector(-45.548301,-178.319039,518.235644),Base.Rotation(0.591598,-0.184974,0.000000,0.784727))
App.ActiveDocument.addObject("Part::Cylinder","C1809")
App.ActiveDocument.C1809.Radius=0.750000
App.ActiveDocument.C1809.Height=15.00
App.ActiveDocument.C1809.Angle=360.00 
App.ActiveDocument.C1809.Placement=Base.Placement(Base.Vector(-45.704837,-178.944492,515.103443),Base.Rotation(0.616519,-0.182911,0.000000,0.765799))
App.ActiveDocument.addObject("Part::Cylinder","C1810")
App.ActiveDocument.C1810.Radius=0.750000
App.ActiveDocument.C1810.Height=15.00
App.ActiveDocument.C1810.Angle=360.00 
App.ActiveDocument.C1810.Placement=Base.Placement(Base.Vector(-45.874976,-179.374115,511.909535),Base.Rotation(0.640833,-0.180501,0.000000,0.746158))
App.ActiveDocument.addObject("Part::Cylinder","C1811")
App.ActiveDocument.C1811.Radius=0.750000
App.ActiveDocument.C1811.Height=15.00
App.ActiveDocument.C1811.Angle=360.00 
App.ActiveDocument.C1811.Placement=Base.Placement(Base.Vector(-46.056200,-179.617753,508.563937),Base.Rotation(0.662773,-0.180415,0.000000,0.726762))
App.ActiveDocument.addObject("Part::Cylinder","C1812")
App.ActiveDocument.C1812.Radius=0.750000
App.ActiveDocument.C1812.Height=15.00
App.ActiveDocument.C1812.Angle=360.00 
App.ActiveDocument.C1812.Placement=Base.Placement(Base.Vector(-46.108267,-179.699651,505.222850),Base.Rotation(0.685692,-0.172571,0.000000,0.707139))
App.ActiveDocument.addObject("Part::Cylinder","C1813")
App.ActiveDocument.C1813.Radius=0.750000
App.ActiveDocument.C1813.Height=15.00
App.ActiveDocument.C1813.Angle=360.00 
App.ActiveDocument.C1813.Placement=Base.Placement(Base.Vector(-46.252506,-179.571523,501.872125),Base.Rotation(0.706014,-0.168353,0.000000,0.687897))
App.ActiveDocument.addObject("Part::Cylinder","C1814")
App.ActiveDocument.C1814.Radius=0.750000
App.ActiveDocument.C1814.Height=15.00
App.ActiveDocument.C1814.Angle=360.00 
App.ActiveDocument.C1814.Placement=Base.Placement(Base.Vector(-46.409239,-179.261553,498.553089),Base.Rotation(0.725048,-0.164606,0.000000,0.668737))
App.ActiveDocument.addObject("Part::Cylinder","C1815")
App.ActiveDocument.C1815.Radius=0.750000
App.ActiveDocument.C1815.Height=15.00
App.ActiveDocument.C1815.Angle=360.00 
App.ActiveDocument.C1815.Placement=Base.Placement(Base.Vector(-46.588339,-178.768399,495.226803),Base.Rotation(0.743275,-0.161273,0.000000,0.649256))
App.ActiveDocument.addObject("Part::Cylinder","C1816")
App.ActiveDocument.C1816.Radius=0.750000
App.ActiveDocument.C1816.Height=15.00
App.ActiveDocument.C1816.Angle=360.00 
App.ActiveDocument.C1816.Placement=Base.Placement(Base.Vector(-46.618614,-178.137709,491.940136),Base.Rotation(0.762029,-0.154121,0.000000,0.628934))
App.ActiveDocument.addObject("Part::Cylinder","C1817")
App.ActiveDocument.C1817.Radius=0.750000
App.ActiveDocument.C1817.Height=15.00
App.ActiveDocument.C1817.Angle=360.00 
App.ActiveDocument.C1817.Placement=Base.Placement(Base.Vector(-46.931941,-177.285466,488.721664),Base.Rotation(0.779532,-0.149279,0.000000,0.608314))
App.ActiveDocument.addObject("Part::Cylinder","C1818")
App.ActiveDocument.C1818.Radius=0.750000
App.ActiveDocument.C1818.Height=15.00
App.ActiveDocument.C1818.Angle=360.00 
App.ActiveDocument.C1818.Placement=Base.Placement(Base.Vector(-47.033455,-176.276398,485.461837),Base.Rotation(0.799667,-0.135816,0.000000,0.584882))
App.ActiveDocument.addObject("Part::Cylinder","C1819")
App.ActiveDocument.C1819.Radius=0.750000
App.ActiveDocument.C1819.Height=15.00
App.ActiveDocument.C1819.Angle=360.00 
App.ActiveDocument.C1819.Placement=Base.Placement(Base.Vector(-47.202700,-175.124787,482.384046),Base.Rotation(0.816368,-0.128529,0.000000,0.563048))
App.ActiveDocument.addObject("Part::Cylinder","C1820")
App.ActiveDocument.C1820.Radius=0.750000
App.ActiveDocument.C1820.Height=15.00
App.ActiveDocument.C1820.Angle=360.00 
App.ActiveDocument.C1820.Placement=Base.Placement(Base.Vector(-47.541121,-173.772080,479.362915),Base.Rotation(0.832466,-0.124682,0.000000,0.539865))
App.ActiveDocument.addObject("Part::Cylinder","C1821")
App.ActiveDocument.C1821.Radius=0.750000
App.ActiveDocument.C1821.Height=15.00
App.ActiveDocument.C1821.Angle=360.00 
App.ActiveDocument.C1821.Placement=Base.Placement(Base.Vector(-47.652075,-172.325852,476.506139),Base.Rotation(0.849629,-0.108759,0.000000,0.516045))
App.ActiveDocument.addObject("Part::Cylinder","C1822")
App.ActiveDocument.C1822.Radius=0.750000
App.ActiveDocument.C1822.Height=15.00
App.ActiveDocument.C1822.Angle=360.00 
App.ActiveDocument.C1822.Placement=Base.Placement(Base.Vector(-47.823053,-170.667351,473.674499),Base.Rotation(0.867244,-0.100183,0.000000,0.487700))
App.ActiveDocument.addObject("Part::Cylinder","C1823")
App.ActiveDocument.C1823.Radius=0.750000
App.ActiveDocument.C1823.Height=15.00
App.ActiveDocument.C1823.Angle=360.00 
App.ActiveDocument.C1823.Placement=Base.Placement(Base.Vector(-47.809657,-168.860907,470.956404),Base.Rotation(0.883878,-0.090288,0.000000,0.458920))
App.ActiveDocument.addObject("Part::Cylinder","C1824")
App.ActiveDocument.C1824.Radius=0.750000
App.ActiveDocument.C1824.Height=15.00
App.ActiveDocument.C1824.Angle=360.00 
App.ActiveDocument.C1824.Placement=Base.Placement(Base.Vector(-48.008163,-166.872503,468.386294),Base.Rotation(0.899342,-0.089445,0.000000,0.428000))
App.ActiveDocument.addObject("Part::Cylinder","C1825")
App.ActiveDocument.C1825.Radius=0.750000
App.ActiveDocument.C1825.Height=15.00
App.ActiveDocument.C1825.Angle=360.00 
App.ActiveDocument.C1825.Placement=Base.Placement(Base.Vector(-47.641012,-144.398743,544.259560),Base.Rotation(0.025576,-0.216117,0.000000,0.976033))
App.ActiveDocument.addObject("Part::Cylinder","C1826")
App.ActiveDocument.C1826.Radius=0.750000
App.ActiveDocument.C1826.Height=15.00
App.ActiveDocument.C1826.Angle=360.00 
App.ActiveDocument.C1826.Placement=Base.Placement(Base.Vector(-47.529415,-147.855079,544.009625),Base.Rotation(0.055882,-0.215224,0.000000,0.974965))
App.ActiveDocument.addObject("Part::Cylinder","C1827")
App.ActiveDocument.C1827.Radius=0.750000
App.ActiveDocument.C1827.Height=15.00
App.ActiveDocument.C1827.Angle=360.00 
App.ActiveDocument.C1827.Placement=Base.Placement(Base.Vector(-47.559619,-151.182070,543.475500),Base.Rotation(0.088666,-0.216097,0.000000,0.972338))
App.ActiveDocument.addObject("Part::Cylinder","C1828")
App.ActiveDocument.C1828.Radius=0.750000
App.ActiveDocument.C1828.Height=15.00
App.ActiveDocument.C1828.Angle=360.00 
App.ActiveDocument.C1828.Placement=Base.Placement(Base.Vector(-47.839179,-154.320224,542.605345),Base.Rotation(0.124185,-0.219825,0.000000,0.967603))
App.ActiveDocument.addObject("Part::Cylinder","C1829")
App.ActiveDocument.C1829.Radius=0.750000
App.ActiveDocument.C1829.Height=15.00
App.ActiveDocument.C1829.Angle=360.00 
App.ActiveDocument.C1829.Placement=Base.Placement(Base.Vector(-47.532141,-157.327092,541.789632),Base.Rotation(0.160975,-0.218653,0.000000,0.962433))
App.ActiveDocument.addObject("Part::Cylinder","C1830")
App.ActiveDocument.C1830.Radius=0.750000
App.ActiveDocument.C1830.Height=15.00
App.ActiveDocument.C1830.Angle=360.00 
App.ActiveDocument.C1830.Placement=Base.Placement(Base.Vector(-47.759434,-160.181261,540.471525),Base.Rotation(0.204857,-0.220913,0.000000,0.953536))
App.ActiveDocument.addObject("Part::Cylinder","C1831")
App.ActiveDocument.C1831.Radius=0.750000
App.ActiveDocument.C1831.Height=15.00
App.ActiveDocument.C1831.Angle=360.00 
App.ActiveDocument.C1831.Placement=Base.Placement(Base.Vector(-47.681487,-162.895912,539.051256),Base.Rotation(0.250521,-0.220511,0.000000,0.942663))
App.ActiveDocument.addObject("Part::Cylinder","C1832")
App.ActiveDocument.C1832.Radius=0.750000
App.ActiveDocument.C1832.Height=15.00
App.ActiveDocument.C1832.Angle=360.00 
App.ActiveDocument.C1832.Placement=Base.Placement(Base.Vector(-47.941046,-165.341166,537.258751),Base.Rotation(0.293022,-0.226392,0.000000,0.928916))
App.ActiveDocument.addObject("Part::Cylinder","C1833")
App.ActiveDocument.C1833.Radius=0.750000
App.ActiveDocument.C1833.Height=15.00
App.ActiveDocument.C1833.Angle=360.00 
App.ActiveDocument.C1833.Placement=Base.Placement(Base.Vector(-47.932860,-167.618476,535.373026),Base.Rotation(0.336614,-0.225736,0.000000,0.914185))
App.ActiveDocument.addObject("Part::Cylinder","C1834")
App.ActiveDocument.C1834.Radius=0.750000
App.ActiveDocument.C1834.Height=15.00
App.ActiveDocument.C1834.Angle=360.00 
App.ActiveDocument.C1834.Placement=Base.Placement(Base.Vector(-48.114190,-169.681589,533.157296),Base.Rotation(0.379878,-0.228900,0.000000,0.896268))
App.ActiveDocument.addObject("Part::Cylinder","C1835")
App.ActiveDocument.C1835.Radius=0.750000
App.ActiveDocument.C1835.Height=15.00
App.ActiveDocument.C1835.Angle=360.00 
App.ActiveDocument.C1835.Placement=Base.Placement(Base.Vector(-48.044311,-171.557237,530.887718),Base.Rotation(0.420928,-0.228272,0.000000,0.877902))
App.ActiveDocument.addObject("Part::Cylinder","C1836")
App.ActiveDocument.C1836.Radius=0.750000
App.ActiveDocument.C1836.Height=15.00
App.ActiveDocument.C1836.Angle=360.00 
App.ActiveDocument.C1836.Placement=Base.Placement(Base.Vector(-48.281084,-173.152292,528.298824),Base.Rotation(0.459348,-0.231274,0.000000,0.857620))
App.ActiveDocument.addObject("Part::Cylinder","C1837")
App.ActiveDocument.C1837.Radius=0.750000
App.ActiveDocument.C1837.Height=15.00
App.ActiveDocument.C1837.Angle=360.00 
App.ActiveDocument.C1837.Placement=Base.Placement(Base.Vector(-48.316757,-174.551919,525.698977),Base.Rotation(0.493584,-0.231168,0.000000,0.838413))
App.ActiveDocument.addObject("Part::Cylinder","C1838")
App.ActiveDocument.C1838.Radius=0.750000
App.ActiveDocument.C1838.Height=15.00
App.ActiveDocument.C1838.Angle=360.00 
App.ActiveDocument.C1838.Placement=Base.Placement(Base.Vector(-48.472721,-175.742644,522.852741),Base.Rotation(0.525309,-0.229668,0.000000,0.819331))
App.ActiveDocument.addObject("Part::Cylinder","C1839")
App.ActiveDocument.C1839.Radius=0.750000
App.ActiveDocument.C1839.Height=15.00
App.ActiveDocument.C1839.Angle=360.00 
App.ActiveDocument.C1839.Placement=Base.Placement(Base.Vector(-48.593899,-176.755680,519.843097),Base.Rotation(0.554681,-0.233104,0.000000,0.798744))
App.ActiveDocument.addObject("Part::Cylinder","C1840")
App.ActiveDocument.C1840.Radius=0.750000
App.ActiveDocument.C1840.Height=15.00
App.ActiveDocument.C1840.Angle=360.00 
App.ActiveDocument.C1840.Placement=Base.Placement(Base.Vector(-48.662100,-177.576761,516.743746),Base.Rotation(0.581931,-0.230699,0.000000,0.779830))
App.ActiveDocument.addObject("Part::Cylinder","C1841")
App.ActiveDocument.C1841.Radius=0.750000
App.ActiveDocument.C1841.Height=15.00
App.ActiveDocument.C1841.Angle=360.00 
App.ActiveDocument.C1841.Placement=Base.Placement(Base.Vector(-48.827324,-178.153427,513.565117),Base.Rotation(0.609640,-0.231666,0.000000,0.758069))
App.ActiveDocument.addObject("Part::Cylinder","C1842")
App.ActiveDocument.C1842.Radius=0.750000
App.ActiveDocument.C1842.Height=15.00
App.ActiveDocument.C1842.Angle=360.00 
App.ActiveDocument.C1842.Placement=Base.Placement(Base.Vector(-48.993963,-178.528702,510.380741),Base.Rotation(0.628441,-0.233926,0.000000,0.741850))
App.ActiveDocument.addObject("Part::Cylinder","C1843")
App.ActiveDocument.C1843.Radius=0.750000
App.ActiveDocument.C1843.Height=15.00
App.ActiveDocument.C1843.Angle=360.00 
App.ActiveDocument.C1843.Placement=Base.Placement(Base.Vector(-49.089758,-178.739817,507.209821),Base.Rotation(0.649688,-0.233740,0.000000,0.723375))
App.ActiveDocument.addObject("Part::Cylinder","C1844")
App.ActiveDocument.C1844.Radius=0.750000
App.ActiveDocument.C1844.Height=15.00
App.ActiveDocument.C1844.Angle=360.00 
App.ActiveDocument.C1844.Placement=Base.Placement(Base.Vector(-49.120898,-178.799748,503.927423),Base.Rotation(0.670785,-0.230726,0.000000,0.704849))
App.ActiveDocument.addObject("Part::Cylinder","C1845")
App.ActiveDocument.C1845.Radius=0.750000
App.ActiveDocument.C1845.Height=15.00
App.ActiveDocument.C1845.Angle=360.00 
App.ActiveDocument.C1845.Placement=Base.Placement(Base.Vector(-49.319862,-178.623573,500.656149),Base.Rotation(0.688508,-0.233972,0.000000,0.686451))
App.ActiveDocument.addObject("Part::Cylinder","C1846")
App.ActiveDocument.C1846.Radius=0.750000
App.ActiveDocument.C1846.Height=15.00
App.ActiveDocument.C1846.Angle=360.00 
App.ActiveDocument.C1846.Placement=Base.Placement(Base.Vector(-49.451383,-178.297178,497.374704),Base.Rotation(0.706823,-0.231023,0.000000,0.668603))
App.ActiveDocument.addObject("Part::Cylinder","C1847")
App.ActiveDocument.C1847.Radius=0.750000
App.ActiveDocument.C1847.Height=15.00
App.ActiveDocument.C1847.Angle=360.00 
App.ActiveDocument.C1847.Placement=Base.Placement(Base.Vector(-49.581410,-177.785999,494.024368),Base.Rotation(0.726931,-0.224150,0.000000,0.649098))
App.ActiveDocument.addObject("Part::Cylinder","C1848")
App.ActiveDocument.C1848.Radius=0.750000
App.ActiveDocument.C1848.Height=15.00
App.ActiveDocument.C1848.Angle=360.00 
App.ActiveDocument.C1848.Placement=Base.Placement(Base.Vector(-49.690639,-177.121234,490.767852),Base.Rotation(0.743508,-0.224671,0.000000,0.629857))
App.ActiveDocument.addObject("Part::Cylinder","C1849")
App.ActiveDocument.C1849.Radius=0.750000
App.ActiveDocument.C1849.Height=15.00
App.ActiveDocument.C1849.Angle=360.00 
App.ActiveDocument.C1849.Placement=Base.Placement(Base.Vector(-49.908315,-176.260518,487.576754),Base.Rotation(0.761104,-0.221581,0.000000,0.609608))
App.ActiveDocument.addObject("Part::Cylinder","C1850")
App.ActiveDocument.C1850.Radius=0.750000
App.ActiveDocument.C1850.Height=15.00
App.ActiveDocument.C1850.Angle=360.00 
App.ActiveDocument.C1850.Placement=Base.Placement(Base.Vector(-50.016544,-175.278846,484.465192),Base.Rotation(0.777946,-0.218833,0.000000,0.588993))
App.ActiveDocument.addObject("Part::Cylinder","C1851")
App.ActiveDocument.C1851.Radius=0.750000
App.ActiveDocument.C1851.Height=15.00
App.ActiveDocument.C1851.Angle=360.00 
App.ActiveDocument.C1851.Placement=Base.Placement(Base.Vector(-50.241013,-174.125454,481.470142),Base.Rotation(0.795118,-0.213808,0.000000,0.567516))
App.ActiveDocument.addObject("Part::Cylinder","C1852")
App.ActiveDocument.C1852.Radius=0.750000
App.ActiveDocument.C1852.Height=15.00
App.ActiveDocument.C1852.Angle=360.00 
App.ActiveDocument.C1852.Placement=Base.Placement(Base.Vector(-50.578004,-172.761941,478.493751),Base.Rotation(0.813744,-0.207163,0.000000,0.543051))
App.ActiveDocument.addObject("Part::Cylinder","C1853")
App.ActiveDocument.C1853.Radius=0.750000
App.ActiveDocument.C1853.Height=15.00
App.ActiveDocument.C1853.Angle=360.00 
App.ActiveDocument.C1853.Placement=Base.Placement(Base.Vector(-50.703558,-171.255334,475.542353),Base.Rotation(0.833659,-0.197296,0.000000,0.515836))
App.ActiveDocument.addObject("Part::Cylinder","C1854")
App.ActiveDocument.C1854.Radius=0.750000
App.ActiveDocument.C1854.Height=15.00
App.ActiveDocument.C1854.Angle=360.00 
App.ActiveDocument.C1854.Placement=Base.Placement(Base.Vector(-50.902738,-169.581946,472.744378),Base.Rotation(0.851498,-0.188033,0.000000,0.489484))
App.ActiveDocument.addObject("Part::Cylinder","C1855")
App.ActiveDocument.C1855.Radius=0.750000
App.ActiveDocument.C1855.Height=15.00
App.ActiveDocument.C1855.Angle=360.00 
App.ActiveDocument.C1855.Placement=Base.Placement(Base.Vector(-51.046870,-167.836571,470.193996),Base.Rotation(0.871013,-0.175654,0.000000,0.458783))
App.ActiveDocument.addObject("Part::Cylinder","C1856")
App.ActiveDocument.C1856.Radius=0.750000
App.ActiveDocument.C1856.Height=15.00
App.ActiveDocument.C1856.Angle=360.00 
App.ActiveDocument.C1856.Placement=Base.Placement(Base.Vector(-51.302687,-166.031705,467.924744),Base.Rotation(0.887103,-0.169971,0.000000,0.429137))
App.ActiveDocument.addObject("Part::Cylinder","C1857")
App.ActiveDocument.C1857.Radius=0.750000
App.ActiveDocument.C1857.Height=15.00
App.ActiveDocument.C1857.Angle=360.00 
App.ActiveDocument.C1857.Placement=Base.Placement(Base.Vector(-50.683523,-144.355877,542.726413),Base.Rotation(0.025457,-0.246256,0.000000,0.968871))
App.ActiveDocument.addObject("Part::Cylinder","C1858")
App.ActiveDocument.C1858.Radius=0.750000
App.ActiveDocument.C1858.Height=15.00
App.ActiveDocument.C1858.Angle=360.00 
App.ActiveDocument.C1858.Placement=Base.Placement(Base.Vector(-50.537241,-147.739081,542.503963),Base.Rotation(0.055149,-0.244978,0.000000,0.967959))
App.ActiveDocument.addObject("Part::Cylinder","C1859")
App.ActiveDocument.C1859.Radius=0.750000
App.ActiveDocument.C1859.Height=15.00
App.ActiveDocument.C1859.Angle=360.00 
App.ActiveDocument.C1859.Placement=Base.Placement(Base.Vector(-50.601892,-150.996864,541.952583),Base.Rotation(0.088674,-0.247032,0.000000,0.964942))
App.ActiveDocument.addObject("Part::Cylinder","C1860")
App.ActiveDocument.C1860.Radius=0.750000
App.ActiveDocument.C1860.Height=15.00
App.ActiveDocument.C1860.Angle=360.00 
App.ActiveDocument.C1860.Placement=Base.Placement(Base.Vector(-50.888026,-154.118516,541.044971),Base.Rotation(0.125209,-0.251658,0.000000,0.959683))
App.ActiveDocument.addObject("Part::Cylinder","C1861")
App.ActiveDocument.C1861.Radius=0.750000
App.ActiveDocument.C1861.Height=15.00
App.ActiveDocument.C1861.Angle=360.00 
App.ActiveDocument.C1861.Placement=Base.Placement(Base.Vector(-50.490842,-157.087840,540.295122),Base.Rotation(0.161326,-0.248010,0.000000,0.955230))
App.ActiveDocument.addObject("Part::Cylinder","C1862")
App.ActiveDocument.C1862.Radius=0.750000
App.ActiveDocument.C1862.Height=15.00
App.ActiveDocument.C1862.Angle=360.00 
App.ActiveDocument.C1862.Placement=Base.Placement(Base.Vector(-50.701949,-159.868978,538.972186),Base.Rotation(0.202002,-0.250834,0.000000,0.946719))
App.ActiveDocument.addObject("Part::Cylinder","C1863")
App.ActiveDocument.C1863.Radius=0.750000
App.ActiveDocument.C1863.Height=15.00
App.ActiveDocument.C1863.Angle=360.00 
App.ActiveDocument.C1863.Placement=Base.Placement(Base.Vector(-50.755068,-162.522684,537.474269),Base.Rotation(0.248127,-0.255826,0.000000,0.934337))
App.ActiveDocument.addObject("Part::Cylinder","C1864")
App.ActiveDocument.C1864.Radius=0.750000
App.ActiveDocument.C1864.Height=15.00
App.ActiveDocument.C1864.Angle=360.00 
App.ActiveDocument.C1864.Placement=Base.Placement(Base.Vector(-50.952845,-164.944456,535.662746),Base.Rotation(0.291452,-0.259389,0.000000,0.920746))
App.ActiveDocument.addObject("Part::Cylinder","C1865")
App.ActiveDocument.C1865.Radius=0.750000
App.ActiveDocument.C1865.Height=15.00
App.ActiveDocument.C1865.Angle=360.00 
App.ActiveDocument.C1865.Placement=Base.Placement(Base.Vector(-50.993388,-167.212386,533.679392),Base.Rotation(0.337515,-0.260985,0.000000,0.904417))
App.ActiveDocument.addObject("Part::Cylinder","C1866")
App.ActiveDocument.C1866.Radius=0.750000
App.ActiveDocument.C1866.Height=15.00
App.ActiveDocument.C1866.Angle=360.00 
App.ActiveDocument.C1866.Placement=Base.Placement(Base.Vector(-51.130399,-169.217636,531.442997),Base.Rotation(0.378659,-0.263451,0.000000,0.887249))
App.ActiveDocument.addObject("Part::Cylinder","C1867")
App.ActiveDocument.C1867.Radius=0.750000
App.ActiveDocument.C1867.Height=15.00
App.ActiveDocument.C1867.Angle=360.00 
App.ActiveDocument.C1867.Placement=Base.Placement(Base.Vector(-51.177429,-171.009697,529.077109),Base.Rotation(0.419746,-0.266421,0.000000,0.867659))
App.ActiveDocument.addObject("Part::Cylinder","C1868")
App.ActiveDocument.C1868.Radius=0.750000
App.ActiveDocument.C1868.Height=15.00
App.ActiveDocument.C1868.Angle=360.00 
App.ActiveDocument.C1868.Placement=Base.Placement(Base.Vector(-51.417375,-172.468713,526.532922),Base.Rotation(0.453269,-0.270271,0.000000,0.849412))
App.ActiveDocument.addObject("Part::Cylinder","C1869")
App.ActiveDocument.C1869.Radius=0.750000
App.ActiveDocument.C1869.Height=15.00
App.ActiveDocument.C1869.Angle=360.00 
App.ActiveDocument.C1869.Placement=Base.Placement(Base.Vector(-51.371762,-173.842368,523.923022),Base.Rotation(0.487140,-0.270845,0.000000,0.830263))
App.ActiveDocument.addObject("Part::Cylinder","C1870")
App.ActiveDocument.C1870.Radius=0.750000
App.ActiveDocument.C1870.Height=15.00
App.ActiveDocument.C1870.Angle=360.00 
App.ActiveDocument.C1870.Placement=Base.Placement(Base.Vector(-51.541183,-174.925121,521.115909),Base.Rotation(0.517512,-0.274153,0.000000,0.810569))
App.ActiveDocument.addObject("Part::Cylinder","C1871")
App.ActiveDocument.C1871.Radius=0.750000
App.ActiveDocument.C1871.Height=15.00
App.ActiveDocument.C1871.Angle=360.00 
App.ActiveDocument.C1871.Placement=Base.Placement(Base.Vector(-51.646788,-175.862655,518.120177),Base.Rotation(0.545036,-0.277604,0.000000,0.791120))
App.ActiveDocument.addObject("Part::Cylinder","C1872")
App.ActiveDocument.C1872.Radius=0.750000
App.ActiveDocument.C1872.Height=15.00
App.ActiveDocument.C1872.Angle=360.00 
App.ActiveDocument.C1872.Placement=Base.Placement(Base.Vector(-51.656047,-176.613263,515.155185),Base.Rotation(0.571409,-0.277705,0.000000,0.772251))
App.ActiveDocument.addObject("Part::Cylinder","C1873")
App.ActiveDocument.C1873.Radius=0.750000
App.ActiveDocument.C1873.Height=15.00
App.ActiveDocument.C1873.Angle=360.00 
App.ActiveDocument.C1873.Placement=Base.Placement(Base.Vector(-51.866991,-177.095093,512.023525),Base.Rotation(0.591305,-0.284774,0.000000,0.754495))
App.ActiveDocument.addObject("Part::Cylinder","C1874")
App.ActiveDocument.C1874.Radius=0.750000
App.ActiveDocument.C1874.Height=15.00
App.ActiveDocument.C1874.Angle=360.00 
App.ActiveDocument.C1874.Placement=Base.Placement(Base.Vector(-51.966635,-177.437734,508.841759),Base.Rotation(0.613056,-0.286436,0.000000,0.736286))
App.ActiveDocument.addObject("Part::Cylinder","C1875")
App.ActiveDocument.C1875.Radius=0.750000
App.ActiveDocument.C1875.Height=15.00
App.ActiveDocument.C1875.Angle=360.00 
App.ActiveDocument.C1875.Placement=Base.Placement(Base.Vector(-52.002465,-177.624644,505.609779),Base.Rotation(0.633041,-0.288496,0.000000,0.718352))
App.ActiveDocument.addObject("Part::Cylinder","C1876")
App.ActiveDocument.C1876.Radius=0.750000
App.ActiveDocument.C1876.Height=15.00
App.ActiveDocument.C1876.Angle=360.00 
App.ActiveDocument.C1876.Placement=Base.Placement(Base.Vector(-52.104852,-177.602949,502.481173),Base.Rotation(0.650103,-0.293060,0.000000,0.701058))
App.ActiveDocument.addObject("Part::Cylinder","C1877")
App.ActiveDocument.C1877.Radius=0.750000
App.ActiveDocument.C1877.Height=15.00
App.ActiveDocument.C1877.Angle=360.00 
App.ActiveDocument.C1877.Placement=Base.Placement(Base.Vector(-52.239763,-177.396781,499.216414),Base.Rotation(0.666812,-0.297012,0.000000,0.683481))
App.ActiveDocument.addObject("Part::Cylinder","C1878")
App.ActiveDocument.C1878.Radius=0.750000
App.ActiveDocument.C1878.Height=15.00
App.ActiveDocument.C1878.Angle=360.00 
App.ActiveDocument.C1878.Placement=Base.Placement(Base.Vector(-52.294747,-177.049901,495.925595),Base.Rotation(0.685998,-0.295102,0.000000,0.665073))
App.ActiveDocument.addObject("Part::Cylinder","C1879")
App.ActiveDocument.C1879.Radius=0.750000
App.ActiveDocument.C1879.Height=15.00
App.ActiveDocument.C1879.Angle=360.00 
App.ActiveDocument.C1879.Placement=Base.Placement(Base.Vector(-52.438420,-176.492064,492.642827),Base.Rotation(0.700458,-0.299404,0.000000,0.647855))
App.ActiveDocument.addObject("Part::Cylinder","C1880")
App.ActiveDocument.C1880.Radius=0.750000
App.ActiveDocument.C1880.Height=15.00
App.ActiveDocument.C1880.Angle=360.00 
App.ActiveDocument.C1880.Placement=Base.Placement(Base.Vector(-52.518325,-175.805862,489.446504),Base.Rotation(0.716736,-0.301967,0.000000,0.628575))
App.ActiveDocument.addObject("Part::Cylinder","C1881")
App.ActiveDocument.C1881.Radius=0.750000
App.ActiveDocument.C1881.Height=15.00
App.ActiveDocument.C1881.Angle=360.00 
App.ActiveDocument.C1881.Placement=Base.Placement(Base.Vector(-52.680925,-174.923416,486.296280),Base.Rotation(0.728459,-0.310926,0.000000,0.610470))
App.ActiveDocument.addObject("Part::Cylinder","C1882")
App.ActiveDocument.C1882.Radius=0.750000
App.ActiveDocument.C1882.Height=15.00
App.ActiveDocument.C1882.Angle=360.00 
App.ActiveDocument.C1882.Placement=Base.Placement(Base.Vector(-52.813549,-173.913982,483.252895),Base.Rotation(0.744532,-0.310841,0.000000,0.590805))
App.ActiveDocument.addObject("Part::Cylinder","C1883")
App.ActiveDocument.C1883.Radius=0.750000
App.ActiveDocument.C1883.Height=15.00
App.ActiveDocument.C1883.Angle=360.00 
App.ActiveDocument.C1883.Placement=Base.Placement(Base.Vector(-52.990391,-172.713078,480.224890),Base.Rotation(0.757730,-0.317314,0.000000,0.570226))
App.ActiveDocument.addObject("Part::Cylinder","C1884")
App.ActiveDocument.C1884.Radius=0.750000
App.ActiveDocument.C1884.Height=15.00
App.ActiveDocument.C1884.Angle=360.00 
App.ActiveDocument.C1884.Placement=Base.Placement(Base.Vector(-53.178125,-171.372085,477.339894),Base.Rotation(0.772824,-0.318636,0.000000,0.548830))
App.ActiveDocument.addObject("Part::Cylinder","C1885")
App.ActiveDocument.C1885.Radius=0.750000
App.ActiveDocument.C1885.Height=15.00
App.ActiveDocument.C1885.Angle=360.00 
App.ActiveDocument.C1885.Placement=Base.Placement(Base.Vector(-53.295633,-169.868173,474.465527),Base.Rotation(0.790144,-0.318473,0.000000,0.523686))
App.ActiveDocument.addObject("Part::Cylinder","C1886")
App.ActiveDocument.C1886.Radius=0.750000
App.ActiveDocument.C1886.Height=15.00
App.ActiveDocument.C1886.Angle=360.00 
App.ActiveDocument.C1886.Placement=Base.Placement(Base.Vector(-53.536216,-168.175003,471.748930),Base.Rotation(0.809899,-0.313082,0.000000,0.496027))
App.ActiveDocument.addObject("Part::Cylinder","C1887")
App.ActiveDocument.C1887.Radius=0.750000
App.ActiveDocument.C1887.Height=15.00
App.ActiveDocument.C1887.Angle=360.00 
App.ActiveDocument.C1887.Placement=Base.Placement(Base.Vector(-53.726187,-166.441205,469.299458),Base.Rotation(0.824894,-0.317675,0.000000,0.467582))
App.ActiveDocument.addObject("Part::Cylinder","C1888")
App.ActiveDocument.C1888.Radius=0.750000
App.ActiveDocument.C1888.Height=15.00
App.ActiveDocument.C1888.Angle=360.00 
App.ActiveDocument.C1888.Placement=Base.Placement(Base.Vector(-53.851646,-164.789788,467.234098),Base.Rotation(0.841185,-0.312441,0.000000,0.441348))
App.ActiveDocument.addObject("Part::Cylinder","C1889")
App.ActiveDocument.C1889.Radius=0.750000
App.ActiveDocument.C1889.Height=15.00
App.ActiveDocument.C1889.Angle=360.00 
App.ActiveDocument.C1889.Placement=Base.Placement(Base.Vector(-53.672024,-144.344057,540.980875),Base.Rotation(0.025053,-0.275508,0.000000,0.960972))
App.ActiveDocument.addObject("Part::Cylinder","C1890")
App.ActiveDocument.C1890.Radius=0.750000
App.ActiveDocument.C1890.Height=15.00
App.ActiveDocument.C1890.Angle=360.00 
App.ActiveDocument.C1890.Placement=Base.Placement(Base.Vector(-53.435979,-147.712911,540.816298),Base.Rotation(0.056032,-0.274129,0.000000,0.960059))
App.ActiveDocument.addObject("Part::Cylinder","C1891")
App.ActiveDocument.C1891.Radius=0.750000
App.ActiveDocument.C1891.Height=15.00
App.ActiveDocument.C1891.Angle=360.00 
App.ActiveDocument.C1891.Placement=Base.Placement(Base.Vector(-53.558393,-150.935393,540.208958),Base.Rotation(0.089229,-0.276285,0.000000,0.956925))
App.ActiveDocument.addObject("Part::Cylinder","C1892")
App.ActiveDocument.C1892.Radius=0.750000
App.ActiveDocument.C1892.Height=15.00
App.ActiveDocument.C1892.Angle=360.00 
App.ActiveDocument.C1892.Placement=Base.Placement(Base.Vector(-53.788250,-154.117123,539.263345),Base.Rotation(0.129019,-0.279850,0.000000,0.951335))
App.ActiveDocument.addObject("Part::Cylinder","C1893")
App.ActiveDocument.C1893.Radius=0.750000
App.ActiveDocument.C1893.Height=15.00
App.ActiveDocument.C1893.Angle=360.00 
App.ActiveDocument.C1893.Placement=Base.Placement(Base.Vector(-53.491038,-157.082077,538.431013),Base.Rotation(0.167858,-0.280564,0.000000,0.945044))
App.ActiveDocument.addObject("Part::Cylinder","C1894")
App.ActiveDocument.C1894.Radius=0.750000
App.ActiveDocument.C1894.Height=15.00
App.ActiveDocument.C1894.Angle=360.00 
App.ActiveDocument.C1894.Placement=Base.Placement(Base.Vector(-53.641819,-159.853043,537.058534),Base.Rotation(0.207927,-0.283155,0.000000,0.936264))
App.ActiveDocument.addObject("Part::Cylinder","C1895")
App.ActiveDocument.C1895.Radius=0.750000
App.ActiveDocument.C1895.Height=15.00
App.ActiveDocument.C1895.Angle=360.00 
App.ActiveDocument.C1895.Placement=Base.Placement(Base.Vector(-53.808828,-162.330959,535.483518),Base.Rotation(0.250635,-0.286407,0.000000,0.924745))
App.ActiveDocument.addObject("Part::Cylinder","C1896")
App.ActiveDocument.C1896.Radius=0.750000
App.ActiveDocument.C1896.Height=15.00
App.ActiveDocument.C1896.Angle=360.00 
App.ActiveDocument.C1896.Placement=Base.Placement(Base.Vector(-53.928886,-164.641249,533.688322),Base.Rotation(0.293678,-0.290948,0.000000,0.910551))
App.ActiveDocument.addObject("Part::Cylinder","C1897")
App.ActiveDocument.C1897.Radius=0.750000
App.ActiveDocument.C1897.Height=15.00
App.ActiveDocument.C1897.Angle=360.00 
App.ActiveDocument.C1897.Placement=Base.Placement(Base.Vector(-54.030349,-166.746963,531.681297),Base.Rotation(0.338752,-0.294308,0.000000,0.893661))
App.ActiveDocument.addObject("Part::Cylinder","C1898")
App.ActiveDocument.C1898.Radius=0.750000
App.ActiveDocument.C1898.Height=15.00
App.ActiveDocument.C1898.Angle=360.00 
App.ActiveDocument.C1898.Placement=Base.Placement(Base.Vector(-54.108141,-168.684996,529.425139),Base.Rotation(0.382124,-0.297659,0.000000,0.874860))
App.ActiveDocument.addObject("Part::Cylinder","C1899")
App.ActiveDocument.C1899.Radius=0.750000
App.ActiveDocument.C1899.Height=15.00
App.ActiveDocument.C1899.Angle=360.00 
App.ActiveDocument.C1899.Placement=Base.Placement(Base.Vector(-54.258486,-170.282802,527.061562),Base.Rotation(0.419415,-0.300814,0.000000,0.856506))
App.ActiveDocument.addObject("Part::Cylinder","C1900")
App.ActiveDocument.C1900.Radius=0.750000
App.ActiveDocument.C1900.Height=15.00
App.ActiveDocument.C1900.Angle=360.00 
App.ActiveDocument.C1900.Placement=Base.Placement(Base.Vector(-54.367966,-171.726725,524.481792),Base.Rotation(0.452741,-0.304456,0.000000,0.838053))
App.ActiveDocument.addObject("Part::Cylinder","C1901")
App.ActiveDocument.C1901.Radius=0.750000
App.ActiveDocument.C1901.Height=15.00
App.ActiveDocument.C1901.Angle=360.00 
App.ActiveDocument.C1901.Placement=Base.Placement(Base.Vector(-54.381740,-172.989439,521.821693),Base.Rotation(0.484062,-0.309695,0.000000,0.818397))
App.ActiveDocument.addObject("Part::Cylinder","C1902")
App.ActiveDocument.C1902.Radius=0.750000
App.ActiveDocument.C1902.Height=15.00
App.ActiveDocument.C1902.Angle=360.00 
App.ActiveDocument.C1902.Placement=Base.Placement(Base.Vector(-54.568912,-173.920444,519.082060),Base.Rotation(0.511474,-0.314596,0.000000,0.799640))
App.ActiveDocument.addObject("Part::Cylinder","C1903")
App.ActiveDocument.C1903.Radius=0.750000
App.ActiveDocument.C1903.Height=15.00
App.ActiveDocument.C1903.Angle=360.00 
App.ActiveDocument.C1903.Placement=Base.Placement(Base.Vector(-54.613274,-174.786000,516.103281),Base.Rotation(0.537508,-0.319356,0.000000,0.780446))
App.ActiveDocument.addObject("Part::Cylinder","C1904")
App.ActiveDocument.C1904.Radius=0.750000
App.ActiveDocument.C1904.Height=15.00
App.ActiveDocument.C1904.Angle=360.00 
App.ActiveDocument.C1904.Placement=Base.Placement(Base.Vector(-54.724371,-175.375876,513.218889),Base.Rotation(0.557319,-0.326886,0.000000,0.763244))
App.ActiveDocument.addObject("Part::Cylinder","C1905")
App.ActiveDocument.C1905.Radius=0.750000
App.ActiveDocument.C1905.Height=15.00
App.ActiveDocument.C1905.Angle=360.00 
App.ActiveDocument.C1905.Placement=Base.Placement(Base.Vector(-54.743655,-175.845688,510.199324),Base.Rotation(0.579198,-0.329820,0.000000,0.745485))
App.ActiveDocument.addObject("Part::Cylinder","C1906")
App.ActiveDocument.C1906.Radius=0.750000
App.ActiveDocument.C1906.Height=15.00
App.ActiveDocument.C1906.Angle=360.00 
App.ActiveDocument.C1906.Placement=Base.Placement(Base.Vector(-54.874371,-176.083460,507.019631),Base.Rotation(0.595111,-0.338142,0.000000,0.729042))
App.ActiveDocument.addObject("Part::Cylinder","C1907")
App.ActiveDocument.C1907.Radius=0.750000
App.ActiveDocument.C1907.Height=15.00
App.ActiveDocument.C1907.Angle=360.00 
App.ActiveDocument.C1907.Placement=Base.Placement(Base.Vector(-54.959840,-176.163272,503.858511),Base.Rotation(0.614375,-0.343574,0.000000,0.710282))
App.ActiveDocument.addObject("Part::Cylinder","C1908")
App.ActiveDocument.C1908.Radius=0.750000
App.ActiveDocument.C1908.Height=15.00
App.ActiveDocument.C1908.Angle=360.00 
App.ActiveDocument.C1908.Placement=Base.Placement(Base.Vector(-54.923293,-176.139142,500.809478),Base.Rotation(0.628107,-0.351396,0.000000,0.694264))
App.ActiveDocument.addObject("Part::Cylinder","C1909")
App.ActiveDocument.C1909.Radius=0.750000
App.ActiveDocument.C1909.Height=15.00
App.ActiveDocument.C1909.Angle=360.00 
App.ActiveDocument.C1909.Placement=Base.Placement(Base.Vector(-54.980113,-175.887944,497.543758),Base.Rotation(0.641405,-0.359583,0.000000,0.677716))
App.ActiveDocument.addObject("Part::Cylinder","C1910")
App.ActiveDocument.C1910.Radius=0.750000
App.ActiveDocument.C1910.Height=15.00
App.ActiveDocument.C1910.Angle=360.00 
App.ActiveDocument.C1910.Placement=Base.Placement(Base.Vector(-55.042164,-175.478579,494.397714),Base.Rotation(0.653587,-0.367843,0.000000,0.661449))
App.ActiveDocument.addObject("Part::Cylinder","C1911")
App.ActiveDocument.C1911.Radius=0.750000
App.ActiveDocument.C1911.Height=15.00
App.ActiveDocument.C1911.Angle=360.00 
App.ActiveDocument.C1911.Placement=Base.Placement(Base.Vector(-55.104488,-174.909842,491.281699),Base.Rotation(0.665703,-0.376306,0.000000,0.644386))
App.ActiveDocument.addObject("Part::Cylinder","C1912")
App.ActiveDocument.C1912.Radius=0.750000
App.ActiveDocument.C1912.Height=15.00
App.ActiveDocument.C1912.Angle=360.00 
App.ActiveDocument.C1912.Placement=Base.Placement(Base.Vector(-55.219025,-174.159988,488.207617),Base.Rotation(0.677115,-0.384156,0.000000,0.627645))
App.ActiveDocument.addObject("Part::Cylinder","C1913")
App.ActiveDocument.C1913.Radius=0.750000
App.ActiveDocument.C1913.Height=15.00
App.ActiveDocument.C1913.Angle=360.00 
App.ActiveDocument.C1913.Placement=Base.Placement(Base.Vector(-55.263841,-173.267614,485.072231),Base.Rotation(0.683074,-0.401504,0.000000,0.610085))
App.ActiveDocument.addObject("Part::Cylinder","C1914")
App.ActiveDocument.C1914.Radius=0.750000
App.ActiveDocument.C1914.Height=15.00
App.ActiveDocument.C1914.Angle=360.00 
App.ActiveDocument.C1914.Placement=Base.Placement(Base.Vector(-55.285120,-172.276686,482.129536),Base.Rotation(0.694276,-0.408811,0.000000,0.592330))
App.ActiveDocument.addObject("Part::Cylinder","C1915")
App.ActiveDocument.C1915.Radius=0.750000
App.ActiveDocument.C1915.Height=15.00
App.ActiveDocument.C1915.Angle=360.00 
App.ActiveDocument.C1915.Placement=Base.Placement(Base.Vector(-55.394212,-171.047440,479.161088),Base.Rotation(0.698861,-0.427224,0.000000,0.573648))
App.ActiveDocument.addObject("Part::Cylinder","C1916")
App.ActiveDocument.C1916.Radius=0.750000
App.ActiveDocument.C1916.Height=15.00
App.ActiveDocument.C1916.Angle=360.00 
App.ActiveDocument.C1916.Placement=Base.Placement(Base.Vector(-55.357608,-169.712400,476.199557),Base.Rotation(0.704800,-0.443523,0.000000,0.553665))
App.ActiveDocument.addObject("Part::Cylinder","C1917")
App.ActiveDocument.C1917.Radius=0.750000
App.ActiveDocument.C1917.Height=15.00
App.ActiveDocument.C1917.Angle=360.00 
App.ActiveDocument.C1917.Placement=Base.Placement(Base.Vector(-55.342709,-168.256322,473.438775),Base.Rotation(0.707229,-0.463215,0.000000,0.534097))
App.ActiveDocument.addObject("Part::Cylinder","C1918")
App.ActiveDocument.C1918.Radius=0.750000
App.ActiveDocument.C1918.Height=15.00
App.ActiveDocument.C1918.Angle=360.00 
App.ActiveDocument.C1918.Placement=Base.Placement(Base.Vector(-55.365487,-166.593272,470.740492),Base.Rotation(0.698782,-0.497308,0.000000,0.514187))
App.ActiveDocument.addObject("Part::Cylinder","C1919")
App.ActiveDocument.C1919.Radius=0.750000
App.ActiveDocument.C1919.Height=15.00
App.ActiveDocument.C1919.Angle=360.00 
App.ActiveDocument.C1919.Placement=Base.Placement(Base.Vector(-55.546185,-164.775800,468.348031),Base.Rotation(0.707438,-0.511720,0.000000,0.487518))
App.ActiveDocument.addObject("Part::Cylinder","C1920")
App.ActiveDocument.C1920.Radius=0.750000
App.ActiveDocument.C1920.Height=15.00
App.ActiveDocument.C1920.Angle=360.00 
App.ActiveDocument.C1920.Placement=Base.Placement(Base.Vector(-55.577909,-163.246477,466.450617),Base.Rotation(0.679944,-0.557905,0.000000,0.475834))
App.ActiveDocument.addObject("Part::Cylinder","C1921")
App.ActiveDocument.C1921.Radius=0.750000
App.ActiveDocument.C1921.Height=15.00
App.ActiveDocument.C1921.Angle=360.00 
App.ActiveDocument.C1921.Placement=Base.Placement(Base.Vector(-56.539301,-144.298360,539.076005),Base.Rotation(0.026001,-0.302550,0.000000,0.952779))
App.ActiveDocument.addObject("Part::Cylinder","C1922")
App.ActiveDocument.C1922.Radius=0.750000
App.ActiveDocument.C1922.Height=15.00
App.ActiveDocument.C1922.Angle=360.00 
App.ActiveDocument.C1922.Placement=Base.Placement(Base.Vector(-56.245462,-147.577469,538.969996),Base.Rotation(0.055766,-0.300871,0.000000,0.952033))
App.ActiveDocument.addObject("Part::Cylinder","C1923")
App.ActiveDocument.C1923.Radius=0.750000
App.ActiveDocument.C1923.Height=15.00
App.ActiveDocument.C1923.Angle=360.00 
App.ActiveDocument.C1923.Placement=Base.Placement(Base.Vector(-56.414305,-150.836088,538.294901),Base.Rotation(0.089946,-0.303557,0.000000,0.948558))
App.ActiveDocument.addObject("Part::Cylinder","C1924")
App.ActiveDocument.C1924.Radius=0.750000
App.ActiveDocument.C1924.Height=15.00
App.ActiveDocument.C1924.Angle=360.00 
App.ActiveDocument.C1924.Placement=Base.Placement(Base.Vector(-56.701408,-153.958459,537.266248),Base.Rotation(0.130380,-0.308685,0.000000,0.942186))
App.ActiveDocument.addObject("Part::Cylinder","C1925")
App.ActiveDocument.C1925.Radius=0.750000
App.ActiveDocument.C1925.Height=15.00
App.ActiveDocument.C1925.Angle=360.00 
App.ActiveDocument.C1925.Placement=Base.Placement(Base.Vector(-56.409796,-156.980598,536.378666),Base.Rotation(0.168282,-0.308744,0.000000,0.936140))
App.ActiveDocument.addObject("Part::Cylinder","C1926")
App.ActiveDocument.C1926.Radius=0.750000
App.ActiveDocument.C1926.Height=15.00
App.ActiveDocument.C1926.Angle=360.00 
App.ActiveDocument.C1926.Placement=Base.Placement(Base.Vector(-56.584417,-159.639889,534.945519),Base.Rotation(0.212390,-0.312767,0.000000,0.925779))
App.ActiveDocument.addObject("Part::Cylinder","C1927")
App.ActiveDocument.C1927.Radius=0.750000
App.ActiveDocument.C1927.Height=15.00
App.ActiveDocument.C1927.Angle=360.00 
App.ActiveDocument.C1927.Placement=Base.Placement(Base.Vector(-56.695645,-161.999278,533.380941),Base.Rotation(0.255158,-0.316979,0.000000,0.913465))
App.ActiveDocument.addObject("Part::Cylinder","C1928")
App.ActiveDocument.C1928.Radius=0.750000
App.ActiveDocument.C1928.Height=15.00
App.ActiveDocument.C1928.Angle=360.00 
App.ActiveDocument.C1928.Placement=Base.Placement(Base.Vector(-56.795646,-164.189987,531.577956),Base.Rotation(0.300133,-0.321066,0.000000,0.898241))
App.ActiveDocument.addObject("Part::Cylinder","C1929")
App.ActiveDocument.C1929.Radius=0.750000
App.ActiveDocument.C1929.Height=15.00
App.ActiveDocument.C1929.Angle=360.00 
App.ActiveDocument.C1929.Placement=Base.Placement(Base.Vector(-56.925312,-166.181087,529.511470),Base.Rotation(0.341427,-0.325988,0.000000,0.881566))
App.ActiveDocument.addObject("Part::Cylinder","C1930")
App.ActiveDocument.C1930.Radius=0.750000
App.ActiveDocument.C1930.Height=15.00
App.ActiveDocument.C1930.Angle=360.00 
App.ActiveDocument.C1930.Placement=Base.Placement(Base.Vector(-57.096999,-167.923857,527.218880),Base.Rotation(0.381145,-0.330272,0.000000,0.863510))
App.ActiveDocument.addObject("Part::Cylinder","C1931")
App.ActiveDocument.C1931.Radius=0.750000
App.ActiveDocument.C1931.Height=15.00
App.ActiveDocument.C1931.Angle=360.00 
App.ActiveDocument.C1931.Placement=Base.Placement(Base.Vector(-57.217338,-169.442497,524.805341),Base.Rotation(0.418958,-0.335240,0.000000,0.843853))
App.ActiveDocument.addObject("Part::Cylinder","C1932")
App.ActiveDocument.C1932.Radius=0.750000
App.ActiveDocument.C1932.Height=15.00
App.ActiveDocument.C1932.Angle=360.00 
App.ActiveDocument.C1932.Placement=Base.Placement(Base.Vector(-57.258455,-170.796097,522.246709),Base.Rotation(0.451211,-0.339516,0.000000,0.825310))
App.ActiveDocument.addObject("Part::Cylinder","C1933")
App.ActiveDocument.C1933.Radius=0.750000
App.ActiveDocument.C1933.Height=15.00
App.ActiveDocument.C1933.Angle=360.00 
App.ActiveDocument.C1933.Placement=Base.Placement(Base.Vector(-57.511075,-171.774478,519.567702),Base.Rotation(0.479767,-0.347839,0.000000,0.805501))
App.ActiveDocument.addObject("Part::Cylinder","C1934")
App.ActiveDocument.C1934.Radius=0.750000
App.ActiveDocument.C1934.Height=15.00
App.ActiveDocument.C1934.Angle=360.00 
App.ActiveDocument.C1934.Placement=Base.Placement(Base.Vector(-57.485321,-172.734983,516.811047),Base.Rotation(0.506729,-0.353327,0.000000,0.786375))
App.ActiveDocument.addObject("Part::Cylinder","C1935")
App.ActiveDocument.C1935.Radius=0.750000
App.ActiveDocument.C1935.Height=15.00
App.ActiveDocument.C1935.Angle=360.00 
App.ActiveDocument.C1935.Placement=Base.Placement(Base.Vector(-57.682115,-173.345373,513.964332),Base.Rotation(0.526423,-0.359893,0.000000,0.770296))
App.ActiveDocument.addObject("Part::Cylinder","C1936")
App.ActiveDocument.C1936.Radius=0.750000
App.ActiveDocument.C1936.Height=15.00
App.ActiveDocument.C1936.Angle=360.00 
App.ActiveDocument.C1936.Placement=Base.Placement(Base.Vector(-57.628669,-173.913489,511.169199),Base.Rotation(0.547869,-0.368180,0.000000,0.751188))
App.ActiveDocument.addObject("Part::Cylinder","C1937")
App.ActiveDocument.C1937.Radius=0.750000
App.ActiveDocument.C1937.Height=15.00
App.ActiveDocument.C1937.Angle=360.00 
App.ActiveDocument.C1937.Placement=Base.Placement(Base.Vector(-57.704150,-174.238323,508.236635),Base.Rotation(0.563851,-0.375518,0.000000,0.735567))
App.ActiveDocument.addObject("Part::Cylinder","C1938")
App.ActiveDocument.C1938.Radius=0.750000
App.ActiveDocument.C1938.Height=15.00
App.ActiveDocument.C1938.Angle=360.00 
App.ActiveDocument.C1938.Placement=Base.Placement(Base.Vector(-57.731097,-174.421430,505.219376),Base.Rotation(0.578508,-0.385915,0.000000,0.718608))
App.ActiveDocument.addObject("Part::Cylinder","C1939")
App.ActiveDocument.C1939.Radius=0.750000
App.ActiveDocument.C1939.Height=15.00
App.ActiveDocument.C1939.Angle=360.00 
App.ActiveDocument.C1939.Placement=Base.Placement(Base.Vector(-57.764398,-174.426727,502.056718),Base.Rotation(0.593034,-0.395949,0.000000,0.701096))
App.ActiveDocument.addObject("Part::Cylinder","C1940")
App.ActiveDocument.C1940.Radius=0.750000
App.ActiveDocument.C1940.Height=15.00
App.ActiveDocument.C1940.Angle=360.00 
App.ActiveDocument.C1940.Placement=Base.Placement(Base.Vector(-57.737580,-174.312842,499.129716),Base.Rotation(0.604051,-0.405440,0.000000,0.686106))
App.ActiveDocument.addObject("Part::Cylinder","C1941")
App.ActiveDocument.C1941.Radius=0.750000
App.ActiveDocument.C1941.Height=15.00
App.ActiveDocument.C1941.Angle=360.00 
App.ActiveDocument.C1941.Placement=Base.Placement(Base.Vector(-57.733924,-173.997702,495.927850),Base.Rotation(0.611760,-0.421451,0.000000,0.669425))
App.ActiveDocument.addObject("Part::Cylinder","C1942")
App.ActiveDocument.C1942.Radius=0.750000
App.ActiveDocument.C1942.Height=15.00
App.ActiveDocument.C1942.Angle=360.00 
App.ActiveDocument.C1942.Placement=Base.Placement(Base.Vector(-57.734170,-173.523919,492.826900),Base.Rotation(0.618333,-0.436881,0.000000,0.653299))
App.ActiveDocument.addObject("Part::Cylinder","C1943")
App.ActiveDocument.C1943.Radius=0.750000
App.ActiveDocument.C1943.Height=15.00
App.ActiveDocument.C1943.Angle=360.00 
App.ActiveDocument.C1943.Placement=Base.Placement(Base.Vector(-57.699602,-172.897278,489.675496),Base.Rotation(0.625672,-0.449947,0.000000,0.637246))
App.ActiveDocument.addObject("Part::Cylinder","C1944")
App.ActiveDocument.C1944.Radius=0.750000
App.ActiveDocument.C1944.Height=15.00
App.ActiveDocument.C1944.Angle=360.00 
App.ActiveDocument.C1944.Placement=Base.Placement(Base.Vector(-57.781969,-172.056190,486.696410),Base.Rotation(0.625567,-0.472572,0.000000,0.620759))
App.ActiveDocument.addObject("Part::Cylinder","C1945")
App.ActiveDocument.C1945.Radius=0.750000
App.ActiveDocument.C1945.Height=15.00
App.ActiveDocument.C1945.Angle=360.00 
App.ActiveDocument.C1945.Placement=Base.Placement(Base.Vector(-57.606023,-171.207311,483.631531),Base.Rotation(0.630543,-0.485565,0.000000,0.605510))
App.ActiveDocument.addObject("Part::Cylinder","C1946")
App.ActiveDocument.C1946.Radius=0.750000
App.ActiveDocument.C1946.Height=15.00
App.ActiveDocument.C1946.Angle=360.00 
App.ActiveDocument.C1946.Placement=Base.Placement(Base.Vector(-57.643779,-170.113296,480.816476),Base.Rotation(0.625256,-0.511015,0.000000,0.589847))
App.ActiveDocument.addObject("Part::Cylinder","C1947")
App.ActiveDocument.C1947.Radius=0.750000
App.ActiveDocument.C1947.Height=15.00
App.ActiveDocument.C1947.Angle=360.00 
App.ActiveDocument.C1947.Placement=Base.Placement(Base.Vector(-57.492747,-168.974111,477.979190),Base.Rotation(0.622041,-0.531980,0.000000,0.574511))
App.ActiveDocument.addObject("Part::Cylinder","C1948")
App.ActiveDocument.C1948.Radius=0.750000
App.ActiveDocument.C1948.Height=15.00
App.ActiveDocument.C1948.Angle=360.00 
App.ActiveDocument.C1948.Placement=Base.Placement(Base.Vector(-57.431907,-167.608777,475.225463),Base.Rotation(0.611434,-0.561704,0.000000,0.557349))
App.ActiveDocument.addObject("Part::Cylinder","C1949")
App.ActiveDocument.C1949.Radius=0.750000
App.ActiveDocument.C1949.Height=15.00
App.ActiveDocument.C1949.Angle=360.00 
App.ActiveDocument.C1949.Placement=Base.Placement(Base.Vector(-57.345168,-166.147555,472.640660),Base.Rotation(0.594969,-0.594258,0.000000,0.541174))
App.ActiveDocument.addObject("Part::Cylinder","C1950")
App.ActiveDocument.C1950.Radius=0.750000
App.ActiveDocument.C1950.Height=15.00
App.ActiveDocument.C1950.Angle=360.00 
App.ActiveDocument.C1950.Placement=Base.Placement(Base.Vector(-57.221526,-164.569221,470.192111),Base.Rotation(0.564389,-0.635599,0.000000,0.526762))
App.ActiveDocument.addObject("Part::Cylinder","C1951")
App.ActiveDocument.C1951.Radius=0.750000
App.ActiveDocument.C1951.Height=15.00
App.ActiveDocument.C1951.Angle=360.00 
App.ActiveDocument.C1951.Placement=Base.Placement(Base.Vector(-57.082053,-162.878387,467.907500),Base.Rotation(0.523956,-0.681773,0.000000,0.510544))
App.ActiveDocument.addObject("Part::Cylinder","C1952")
App.ActiveDocument.C1952.Radius=0.750000
App.ActiveDocument.C1952.Height=15.00
App.ActiveDocument.C1952.Angle=360.00 
App.ActiveDocument.C1952.Placement=Base.Placement(Base.Vector(-56.853410,-161.344516,465.986495),Base.Rotation(0.472973,-0.724561,0.000000,0.501306))
App.ActiveDocument.addObject("Part::Cylinder","C1953")
App.ActiveDocument.C1953.Radius=0.750000
App.ActiveDocument.C1953.Height=15.00
App.ActiveDocument.C1953.Angle=360.00 
App.ActiveDocument.C1953.Placement=Base.Placement(Base.Vector(-59.326628,-144.288689,536.989811),Base.Rotation(0.026944,-0.328268,0.000000,0.944200))
App.ActiveDocument.addObject("Part::Cylinder","C1954")
App.ActiveDocument.C1954.Radius=0.750000
App.ActiveDocument.C1954.Height=15.00
App.ActiveDocument.C1954.Angle=360.00 
App.ActiveDocument.C1954.Placement=Base.Placement(Base.Vector(-59.032640,-147.599197,536.889817),Base.Rotation(0.058229,-0.326016,0.000000,0.943569))
App.ActiveDocument.addObject("Part::Cylinder","C1955")
App.ActiveDocument.C1955.Radius=0.750000
App.ActiveDocument.C1955.Height=15.00
App.ActiveDocument.C1955.Angle=360.00 
App.ActiveDocument.C1955.Placement=Base.Placement(Base.Vector(-59.242233,-150.800162,536.139058),Base.Rotation(0.091665,-0.330100,0.000000,0.939485))
App.ActiveDocument.addObject("Part::Cylinder","C1956")
App.ActiveDocument.C1956.Radius=0.750000
App.ActiveDocument.C1956.Height=15.00
App.ActiveDocument.C1956.Angle=360.00 
App.ActiveDocument.C1956.Placement=Base.Placement(Base.Vector(-59.457686,-153.822089,535.120571),Base.Rotation(0.133161,-0.334905,0.000000,0.932795))
App.ActiveDocument.addObject("Part::Cylinder","C1957")
App.ActiveDocument.C1957.Radius=0.750000
App.ActiveDocument.C1957.Height=15.00
App.ActiveDocument.C1957.Angle=360.00 
App.ActiveDocument.C1957.Placement=Base.Placement(Base.Vector(-59.231152,-156.755787,534.172354),Base.Rotation(0.175093,-0.334932,0.000000,0.925831))
App.ActiveDocument.addObject("Part::Cylinder","C1958")
App.ActiveDocument.C1958.Radius=0.750000
App.ActiveDocument.C1958.Height=15.00
App.ActiveDocument.C1958.Angle=360.00 
App.ActiveDocument.C1958.Placement=Base.Placement(Base.Vector(-59.447209,-159.311851,532.651207),Base.Rotation(0.218039,-0.341177,0.000000,0.914362))
App.ActiveDocument.addObject("Part::Cylinder","C1959")
App.ActiveDocument.C1959.Radius=0.750000
App.ActiveDocument.C1959.Height=15.00
App.ActiveDocument.C1959.Angle=360.00 
App.ActiveDocument.C1959.Placement=Base.Placement(Base.Vector(-59.592316,-161.660696,530.932991),Base.Rotation(0.262257,-0.345299,0.000000,0.901105))
App.ActiveDocument.addObject("Part::Cylinder","C1960")
App.ActiveDocument.C1960.Radius=0.750000
App.ActiveDocument.C1960.Height=15.00
App.ActiveDocument.C1960.Angle=360.00 
App.ActiveDocument.C1960.Placement=Base.Placement(Base.Vector(-59.617427,-163.805507,529.075847),Base.Rotation(0.306797,-0.348784,0.000000,0.885565))
App.ActiveDocument.addObject("Part::Cylinder","C1961")
App.ActiveDocument.C1961.Radius=0.750000
App.ActiveDocument.C1961.Height=15.00
App.ActiveDocument.C1961.Angle=360.00 
App.ActiveDocument.C1961.Placement=Base.Placement(Base.Vector(-59.913248,-165.512853,526.910715),Base.Rotation(0.347204,-0.356673,0.000000,0.867314))
App.ActiveDocument.addObject("Part::Cylinder","C1962")
App.ActiveDocument.C1962.Radius=0.750000
App.ActiveDocument.C1962.Height=15.00
App.ActiveDocument.C1962.Angle=360.00 
App.ActiveDocument.C1962.Placement=Base.Placement(Base.Vector(-59.935558,-167.148815,524.707034),Base.Rotation(0.386532,-0.362545,0.000000,0.848030))
App.ActiveDocument.addObject("Part::Cylinder","C1963")
App.ActiveDocument.C1963.Radius=0.750000
App.ActiveDocument.C1963.Height=15.00
App.ActiveDocument.C1963.Angle=360.00 
App.ActiveDocument.C1963.Placement=Base.Placement(Base.Vector(-60.074431,-168.532745,522.204934),Base.Rotation(0.421507,-0.367363,0.000000,0.829082))
App.ActiveDocument.addObject("Part::Cylinder","C1964")
App.ActiveDocument.C1964.Radius=0.750000
App.ActiveDocument.C1964.Height=15.00
App.ActiveDocument.C1964.Angle=360.00 
App.ActiveDocument.C1964.Placement=Base.Placement(Base.Vector(-60.330773,-169.546963,519.652806),Base.Rotation(0.450426,-0.375872,0.000000,0.809837))
App.ActiveDocument.addObject("Part::Cylinder","C1965")
App.ActiveDocument.C1965.Radius=0.750000
App.ActiveDocument.C1965.Height=15.00
App.ActiveDocument.C1965.Angle=360.00 
App.ActiveDocument.C1965.Placement=Base.Placement(Base.Vector(-60.392152,-170.515324,516.953957),Base.Rotation(0.477508,-0.381868,0.000000,0.791305))
App.ActiveDocument.addObject("Part::Cylinder","C1966")
App.ActiveDocument.C1966.Radius=0.750000
App.ActiveDocument.C1966.Height=15.00
App.ActiveDocument.C1966.Angle=360.00 
App.ActiveDocument.C1966.Placement=Base.Placement(Base.Vector(-60.503456,-171.212479,514.245013),Base.Rotation(0.501003,-0.389883,0.000000,0.772649))
App.ActiveDocument.addObject("Part::Cylinder","C1967")
App.ActiveDocument.C1967.Radius=0.750000
App.ActiveDocument.C1967.Height=15.00
App.ActiveDocument.C1967.Angle=360.00 
App.ActiveDocument.C1967.Placement=Base.Placement(Base.Vector(-60.579640,-171.749661,511.426944),Base.Rotation(0.520804,-0.400799,0.000000,0.753740))
App.ActiveDocument.addObject("Part::Cylinder","C1968")
App.ActiveDocument.C1968.Radius=0.750000
App.ActiveDocument.C1968.Height=15.00
App.ActiveDocument.C1968.Angle=360.00 
App.ActiveDocument.C1968.Placement=Base.Placement(Base.Vector(-60.529308,-172.190643,508.569691),Base.Rotation(0.539046,-0.407892,0.000000,0.736921))
App.ActiveDocument.addObject("Part::Cylinder","C1969")
App.ActiveDocument.C1969.Radius=0.750000
App.ActiveDocument.C1969.Height=15.00
App.ActiveDocument.C1969.Angle=360.00 
App.ActiveDocument.C1969.Placement=Base.Placement(Base.Vector(-60.504738,-172.426087,505.748538),Base.Rotation(0.552694,-0.419095,0.000000,0.720339))
App.ActiveDocument.addObject("Part::Cylinder","C1970")
App.ActiveDocument.C1970.Radius=0.750000
App.ActiveDocument.C1970.Height=15.00
App.ActiveDocument.C1970.Angle=360.00 
App.ActiveDocument.C1970.Placement=Base.Placement(Base.Vector(-60.559583,-172.434973,502.916721),Base.Rotation(0.564018,-0.430539,0.000000,0.704641))
App.ActiveDocument.addObject("Part::Cylinder","C1971")
App.ActiveDocument.C1971.Radius=0.750000
App.ActiveDocument.C1971.Height=15.00
App.ActiveDocument.C1971.Angle=360.00 
App.ActiveDocument.C1971.Placement=Base.Placement(Base.Vector(-60.498878,-172.359362,499.855434),Base.Rotation(0.573754,-0.444935,0.000000,0.687633))
App.ActiveDocument.addObject("Part::Cylinder","C1972")
App.ActiveDocument.C1972.Radius=0.750000
App.ActiveDocument.C1972.Height=15.00
App.ActiveDocument.C1972.Angle=360.00 
App.ActiveDocument.C1972.Placement=Base.Placement(Base.Vector(-60.421076,-172.136353,496.904607),Base.Rotation(0.581577,-0.458185,0.000000,0.672186))
App.ActiveDocument.addObject("Part::Cylinder","C1973")
App.ActiveDocument.C1973.Radius=0.750000
App.ActiveDocument.C1973.Height=15.00
App.ActiveDocument.C1973.Angle=360.00 
App.ActiveDocument.C1973.Placement=Base.Placement(Base.Vector(-60.460479,-171.664464,493.991804),Base.Rotation(0.585233,-0.475395,0.000000,0.656888))
App.ActiveDocument.addObject("Part::Cylinder","C1974")
App.ActiveDocument.C1974.Radius=0.750000
App.ActiveDocument.C1974.Height=15.00
App.ActiveDocument.C1974.Angle=360.00 
App.ActiveDocument.C1974.Placement=Base.Placement(Base.Vector(-60.352227,-171.119723,490.951092),Base.Rotation(0.587636,-0.494240,0.000000,0.640633))
App.ActiveDocument.addObject("Part::Cylinder","C1975")
App.ActiveDocument.C1975.Radius=0.750000
App.ActiveDocument.C1975.Height=15.00
App.ActiveDocument.C1975.Angle=360.00 
App.ActiveDocument.C1975.Placement=Base.Placement(Base.Vector(-60.364269,-170.394588,488.244981),Base.Rotation(0.587180,-0.513084,0.000000,0.626070))
App.ActiveDocument.addObject("Part::Cylinder","C1976")
App.ActiveDocument.C1976.Radius=0.750000
App.ActiveDocument.C1976.Height=15.00
App.ActiveDocument.C1976.Angle=360.00 
App.ActiveDocument.C1976.Placement=Base.Placement(Base.Vector(-60.241102,-169.520236,485.220794),Base.Rotation(0.583173,-0.535898,0.000000,0.610510))
App.ActiveDocument.addObject("Part::Cylinder","C1977")
App.ActiveDocument.C1977.Radius=0.750000
App.ActiveDocument.C1977.Height=15.00
App.ActiveDocument.C1977.Angle=360.00 
App.ActiveDocument.C1977.Placement=Base.Placement(Base.Vector(-60.191350,-168.523306,482.535235),Base.Rotation(0.576674,-0.558943,0.000000,0.595844))
App.ActiveDocument.addObject("Part::Cylinder","C1978")
App.ActiveDocument.C1978.Radius=0.750000
App.ActiveDocument.C1978.Height=15.00
App.ActiveDocument.C1978.Angle=360.00 
App.ActiveDocument.C1978.Placement=Base.Placement(Base.Vector(-59.938655,-167.422773,479.603306),Base.Rotation(0.566172,-0.585875,0.000000,0.579827))
App.ActiveDocument.addObject("Part::Cylinder","C1979")
App.ActiveDocument.C1979.Radius=0.750000
App.ActiveDocument.C1979.Height=15.00
App.ActiveDocument.C1979.Angle=360.00 
App.ActiveDocument.C1979.Placement=Base.Placement(Base.Vector(-59.758074,-166.170938,476.937159),Base.Rotation(0.548395,-0.616742,0.000000,0.564705))
App.ActiveDocument.addObject("Part::Cylinder","C1980")
App.ActiveDocument.C1980.Radius=0.750000
App.ActiveDocument.C1980.Height=15.00
App.ActiveDocument.C1980.Angle=360.00 
App.ActiveDocument.C1980.Placement=Base.Placement(Base.Vector(-59.633737,-164.776244,474.516280),Base.Rotation(0.523838,-0.651195,0.000000,0.549126))
App.ActiveDocument.addObject("Part::Cylinder","C1981")
App.ActiveDocument.C1981.Radius=0.750000
App.ActiveDocument.C1981.Height=15.00
App.ActiveDocument.C1981.Angle=360.00 
App.ActiveDocument.C1981.Placement=Base.Placement(Base.Vector(-59.417529,-163.324209,472.197598),Base.Rotation(0.489071,-0.689547,0.000000,0.534168))
App.ActiveDocument.addObject("Part::Cylinder","C1982")
App.ActiveDocument.C1982.Radius=0.750000
App.ActiveDocument.C1982.Height=15.00
App.ActiveDocument.C1982.Angle=360.00 
App.ActiveDocument.C1982.Placement=Base.Placement(Base.Vector(-59.182453,-161.694305,469.987739),Base.Rotation(0.448566,-0.727651,0.000000,0.518954))
App.ActiveDocument.addObject("Part::Cylinder","C1983")
App.ActiveDocument.C1983.Radius=0.750000
App.ActiveDocument.C1983.Height=15.00
App.ActiveDocument.C1983.Angle=360.00 
App.ActiveDocument.C1983.Placement=Base.Placement(Base.Vector(-58.996415,-159.994106,468.138999),Base.Rotation(0.392944,-0.769316,0.000000,0.503734))
App.ActiveDocument.addObject("Part::Cylinder","C1984")
App.ActiveDocument.C1984.Radius=0.750000
App.ActiveDocument.C1984.Height=15.00
App.ActiveDocument.C1984.Angle=360.00 
App.ActiveDocument.C1984.Placement=Base.Placement(Base.Vector(-58.422201,-158.560992,466.211498),Base.Rotation(0.339868,-0.801583,0.000000,0.491888))
App.ActiveDocument.addObject("Part::Cylinder","C1985")
App.ActiveDocument.C1985.Radius=0.750000
App.ActiveDocument.C1985.Height=15.00
App.ActiveDocument.C1985.Angle=360.00 
App.ActiveDocument.C1985.Placement=Base.Placement(Base.Vector(-62.003520,-144.246941,534.759040),Base.Rotation(0.026819,-0.352141,0.000000,0.935563))
App.ActiveDocument.addObject("Part::Cylinder","C1986")
App.ActiveDocument.C1986.Radius=0.750000
App.ActiveDocument.C1986.Height=15.00
App.ActiveDocument.C1986.Angle=360.00 
App.ActiveDocument.C1986.Placement=Base.Placement(Base.Vector(-61.711670,-147.557613,534.661701),Base.Rotation(0.060035,-0.351251,0.000000,0.934355))
App.ActiveDocument.addObject("Part::Cylinder","C1987")
App.ActiveDocument.C1987.Radius=0.750000
App.ActiveDocument.C1987.Height=15.00
App.ActiveDocument.C1987.Angle=360.00 
App.ActiveDocument.C1987.Placement=Base.Placement(Base.Vector(-61.975205,-150.642725,533.833082),Base.Rotation(0.095011,-0.355569,0.000000,0.929808))
App.ActiveDocument.addObject("Part::Cylinder","C1988")
App.ActiveDocument.C1988.Radius=0.750000
App.ActiveDocument.C1988.Height=15.00
App.ActiveDocument.C1988.Angle=360.00 
App.ActiveDocument.C1988.Placement=Base.Placement(Base.Vector(-62.173553,-153.661003,532.753886),Base.Rotation(0.136085,-0.360466,0.000000,0.922792))
App.ActiveDocument.addObject("Part::Cylinder","C1989")
App.ActiveDocument.C1989.Radius=0.750000
App.ActiveDocument.C1989.Height=15.00
App.ActiveDocument.C1989.Angle=360.00 
App.ActiveDocument.C1989.Placement=Base.Placement(Base.Vector(-61.920088,-156.453053,531.835042),Base.Rotation(0.178654,-0.360239,0.000000,0.915593))
App.ActiveDocument.addObject("Part::Cylinder","C1990")
App.ActiveDocument.C1990.Radius=0.750000
App.ActiveDocument.C1990.Height=15.00
App.ActiveDocument.C1990.Angle=360.00 
App.ActiveDocument.C1990.Placement=Base.Placement(Base.Vector(-62.238131,-158.832002,530.191319),Base.Rotation(0.221883,-0.367561,0.000000,0.903143))
App.ActiveDocument.addObject("Part::Cylinder","C1991")
App.ActiveDocument.C1991.Radius=0.750000
App.ActiveDocument.C1991.Height=15.00
App.ActiveDocument.C1991.Angle=360.00 
App.ActiveDocument.C1991.Placement=Base.Placement(Base.Vector(-62.350141,-161.123278,528.406865),Base.Rotation(0.268315,-0.372878,0.000000,0.888239))
App.ActiveDocument.addObject("Part::Cylinder","C1992")
App.ActiveDocument.C1992.Radius=0.750000
App.ActiveDocument.C1992.Height=15.00
App.ActiveDocument.C1992.Angle=360.00 
App.ActiveDocument.C1992.Placement=Base.Placement(Base.Vector(-62.432402,-162.995291,526.580992),Base.Rotation(0.309269,-0.377650,0.000000,0.872773))
App.ActiveDocument.addObject("Part::Cylinder","C1993")
App.ActiveDocument.C1993.Radius=0.750000
App.ActiveDocument.C1993.Height=15.00
App.ActiveDocument.C1993.Angle=360.00 
App.ActiveDocument.C1993.Placement=Base.Placement(Base.Vector(-62.715249,-164.622039,524.307134),Base.Rotation(0.353143,-0.384172,0.000000,0.853054))
App.ActiveDocument.addObject("Part::Cylinder","C1994")
App.ActiveDocument.C1994.Radius=0.750000
App.ActiveDocument.C1994.Height=15.00
App.ActiveDocument.C1994.Angle=360.00 
App.ActiveDocument.C1994.Placement=Base.Placement(Base.Vector(-62.763387,-166.126751,522.020538),Base.Rotation(0.390437,-0.390165,0.000000,0.833865))
App.ActiveDocument.addObject("Part::Cylinder","C1995")
App.ActiveDocument.C1995.Radius=0.750000
App.ActiveDocument.C1995.Height=15.00
App.ActiveDocument.C1995.Angle=360.00 
App.ActiveDocument.C1995.Placement=Base.Placement(Base.Vector(-63.079125,-167.171967,519.507457),Base.Rotation(0.421561,-0.398315,0.000000,0.814636))
App.ActiveDocument.addObject("Part::Cylinder","C1996")
App.ActiveDocument.C1996.Radius=0.750000
App.ActiveDocument.C1996.Height=15.00
App.ActiveDocument.C1996.Angle=360.00 
App.ActiveDocument.C1996.Placement=Base.Placement(Base.Vector(-63.210432,-168.140887,516.902815),Base.Rotation(0.450641,-0.404928,0.000000,0.795585))
App.ActiveDocument.addObject("Part::Cylinder","C1997")
App.ActiveDocument.C1997.Radius=0.750000
App.ActiveDocument.C1997.Height=15.00
App.ActiveDocument.C1997.Angle=360.00 
App.ActiveDocument.C1997.Placement=Base.Placement(Base.Vector(-63.332463,-168.867490,514.287628),Base.Rotation(0.475939,-0.414982,0.000000,0.775417))
App.ActiveDocument.addObject("Part::Cylinder","C1998")
App.ActiveDocument.C1998.Radius=0.750000
App.ActiveDocument.C1998.Height=15.00
App.ActiveDocument.C1998.Angle=360.00 
App.ActiveDocument.C1998.Placement=Base.Placement(Base.Vector(-63.389229,-169.461500,511.500151),Base.Rotation(0.498275,-0.424393,0.000000,0.756051))
App.ActiveDocument.addObject("Part::Cylinder","C1999")
App.ActiveDocument.C1999.Radius=0.750000
App.ActiveDocument.C1999.Height=15.00
App.ActiveDocument.C1999.Angle=360.00 
App.ActiveDocument.C1999.Placement=Base.Placement(Base.Vector(-63.394251,-169.874377,508.769047),Base.Rotation(0.516589,-0.434567,0.000000,0.737759))
App.ActiveDocument.addObject("Part::Cylinder","C2000")
App.ActiveDocument.C2000.Radius=0.750000
App.ActiveDocument.C2000.Height=15.00
App.ActiveDocument.C2000.Angle=360.00 
App.ActiveDocument.C2000.Placement=Base.Placement(Base.Vector(-63.269247,-170.217414,505.836729),Base.Rotation(0.533417,-0.445254,0.000000,0.719176))
App.ActiveDocument.addObject("Part::Cylinder","C2001")
App.ActiveDocument.C2001.Radius=0.750000
App.ActiveDocument.C2001.Height=15.00
App.ActiveDocument.C2001.Angle=360.00 
App.ActiveDocument.C2001.Placement=Base.Placement(Base.Vector(-63.344975,-170.197084,503.071823),Base.Rotation(0.543327,-0.458613,0.000000,0.703186))
App.ActiveDocument.addObject("Part::Cylinder","C2002")
App.ActiveDocument.C2002.Radius=0.750000
App.ActiveDocument.C2002.Height=15.00
App.ActiveDocument.C2002.Angle=360.00 
App.ActiveDocument.C2002.Placement=Base.Placement(Base.Vector(-63.334394,-170.092773,500.471891),Base.Rotation(0.553078,-0.470363,0.000000,0.687651))
App.ActiveDocument.addObject("Part::Cylinder","C2003")
App.ActiveDocument.C2003.Radius=0.750000
App.ActiveDocument.C2003.Height=15.00
App.ActiveDocument.C2003.Angle=360.00 
App.ActiveDocument.C2003.Placement=Base.Placement(Base.Vector(-63.230479,-169.898600,497.656120),Base.Rotation(0.559368,-0.485779,0.000000,0.671659))
App.ActiveDocument.addObject("Part::Cylinder","C2004")
App.ActiveDocument.C2004.Radius=0.750000
App.ActiveDocument.C2004.Height=15.00
App.ActiveDocument.C2004.Angle=360.00 
App.ActiveDocument.C2004.Placement=Base.Placement(Base.Vector(-63.152816,-169.514866,494.818252),Base.Rotation(0.562146,-0.502498,0.000000,0.656878))
App.ActiveDocument.addObject("Part::Cylinder","C2005")
App.ActiveDocument.C2005.Radius=0.750000
App.ActiveDocument.C2005.Height=15.00
App.ActiveDocument.C2005.Angle=360.00 
App.ActiveDocument.C2005.Placement=Base.Placement(Base.Vector(-63.140963,-168.909805,492.013367),Base.Rotation(0.563807,-0.522474,0.000000,0.639643))
App.ActiveDocument.addObject("Part::Cylinder","C2006")
App.ActiveDocument.C2006.Radius=0.750000
App.ActiveDocument.C2006.Height=15.00
App.ActiveDocument.C2006.Angle=360.00 
App.ActiveDocument.C2006.Placement=Base.Placement(Base.Vector(-63.043740,-168.270599,489.398858),Base.Rotation(0.562417,-0.541989,0.000000,0.624448))
App.ActiveDocument.addObject("Part::Cylinder","C2007")
App.ActiveDocument.C2007.Radius=0.750000
App.ActiveDocument.C2007.Height=15.00
App.ActiveDocument.C2007.Angle=360.00 
App.ActiveDocument.C2007.Placement=Base.Placement(Base.Vector(-62.983863,-167.418715,486.741193),Base.Rotation(0.557100,-0.563551,0.000000,0.609959))
App.ActiveDocument.addObject("Part::Cylinder","C2008")
App.ActiveDocument.C2008.Radius=0.750000
App.ActiveDocument.C2008.Height=15.00
App.ActiveDocument.C2008.Angle=360.00 
App.ActiveDocument.C2008.Placement=Base.Placement(Base.Vector(-62.809889,-166.468442,484.003283),Base.Rotation(0.549694,-0.587202,0.000000,0.594163))
App.ActiveDocument.addObject("Part::Cylinder","C2009")
App.ActiveDocument.C2009.Radius=0.750000
App.ActiveDocument.C2009.Height=15.00
App.ActiveDocument.C2009.Angle=360.00 
App.ActiveDocument.C2009.Placement=Base.Placement(Base.Vector(-62.602930,-165.435299,481.429119),Base.Rotation(0.537542,-0.613344,0.000000,0.578669))
App.ActiveDocument.addObject("Part::Cylinder","C2010")
App.ActiveDocument.C2010.Radius=0.750000
App.ActiveDocument.C2010.Height=15.00
App.ActiveDocument.C2010.Angle=360.00 
App.ActiveDocument.C2010.Placement=Base.Placement(Base.Vector(-62.331326,-164.251000,478.826580),Base.Rotation(0.520997,-0.641944,0.000000,0.562557))
App.ActiveDocument.addObject("Part::Cylinder","C2011")
App.ActiveDocument.C2011.Radius=0.750000
App.ActiveDocument.C2011.Height=15.00
App.ActiveDocument.C2011.Angle=360.00 
App.ActiveDocument.C2011.Placement=Base.Placement(Base.Vector(-62.124079,-162.874252,476.423772),Base.Rotation(0.495904,-0.676467,0.000000,0.544492))
App.ActiveDocument.addObject("Part::Cylinder","C2012")
App.ActiveDocument.C2012.Radius=0.750000
App.ActiveDocument.C2012.Height=15.00
App.ActiveDocument.C2012.Angle=360.00 
App.ActiveDocument.C2012.Placement=Base.Placement(Base.Vector(-62.012267,-161.196971,474.184172),Base.Rotation(0.470613,-0.705924,0.000000,0.529334))
App.ActiveDocument.addObject("Part::Cylinder","C2013")
App.ActiveDocument.C2013.Radius=0.750000
App.ActiveDocument.C2013.Height=15.00
App.ActiveDocument.C2013.Angle=360.00 
App.ActiveDocument.C2013.Placement=Base.Placement(Base.Vector(-61.651236,-159.744694,472.130131),Base.Rotation(0.429030,-0.745736,0.000000,0.509716))
App.ActiveDocument.addObject("Part::Cylinder","C2014")
App.ActiveDocument.C2014.Radius=0.750000
App.ActiveDocument.C2014.Height=15.00
App.ActiveDocument.C2014.Angle=360.00 
App.ActiveDocument.C2014.Placement=Base.Placement(Base.Vector(-61.612378,-158.042590,470.661862),Base.Rotation(0.389788,-0.778616,0.000000,0.491754))
App.ActiveDocument.addObject("Part::Cylinder","C2015")
App.ActiveDocument.C2015.Radius=0.750000
App.ActiveDocument.C2015.Height=15.00
App.ActiveDocument.C2015.Angle=360.00 
App.ActiveDocument.C2015.Placement=Base.Placement(Base.Vector(-61.128507,-156.360796,468.868578),Base.Rotation(0.334400,-0.815355,0.000000,0.472623))
App.ActiveDocument.addObject("Part::Cylinder","C2016")
App.ActiveDocument.C2016.Radius=0.750000
App.ActiveDocument.C2016.Height=15.00
App.ActiveDocument.C2016.Angle=360.00 
App.ActiveDocument.C2016.Placement=Base.Placement(Base.Vector(-60.049868,-155.260877,466.859763),Base.Rotation(0.269398,-0.847066,0.000000,0.458153))
App.ActiveDocument.addObject("Part::Cylinder","C2017")
App.ActiveDocument.C2017.Radius=0.750000
App.ActiveDocument.C2017.Height=15.00
App.ActiveDocument.C2017.Angle=360.00 
App.ActiveDocument.C2017.Placement=Base.Placement(Base.Vector(-64.610073,-144.190073,532.353671),Base.Rotation(0.027451,-0.375670,0.000000,0.926347))
App.ActiveDocument.addObject("Part::Cylinder","C2018")
App.ActiveDocument.C2018.Radius=0.750000
App.ActiveDocument.C2018.Height=15.00
App.ActiveDocument.C2018.Angle=360.00 
App.ActiveDocument.C2018.Placement=Base.Placement(Base.Vector(-64.258680,-147.457894,532.324239),Base.Rotation(0.060472,-0.374114,0.000000,0.925409))
App.ActiveDocument.addObject("Part::Cylinder","C2019")
App.ActiveDocument.C2019.Radius=0.750000
App.ActiveDocument.C2019.Height=15.00
App.ActiveDocument.C2019.Angle=360.00 
App.ActiveDocument.C2019.Placement=Base.Placement(Base.Vector(-64.607306,-150.497114,531.355214),Base.Rotation(0.098295,-0.379151,0.000000,0.920099))
App.ActiveDocument.addObject("Part::Cylinder","C2020")
App.ActiveDocument.C2020.Radius=0.750000
App.ActiveDocument.C2020.Height=15.00
App.ActiveDocument.C2020.Angle=360.00 
App.ActiveDocument.C2020.Placement=Base.Placement(Base.Vector(-64.725773,-153.469009,530.286072),Base.Rotation(0.136274,-0.382550,0.000000,0.913830))
App.ActiveDocument.addObject("Part::Cylinder","C2021")
App.ActiveDocument.C2021.Radius=0.750000
App.ActiveDocument.C2021.Height=15.00
App.ActiveDocument.C2021.Angle=360.00 
App.ActiveDocument.C2021.Placement=Base.Placement(Base.Vector(-64.641434,-156.050059,529.218718),Base.Rotation(0.178798,-0.386628,0.000000,0.904738))
App.ActiveDocument.addObject("Part::Cylinder","C2022")
App.ActiveDocument.C2022.Radius=0.750000
App.ActiveDocument.C2022.Height=15.00
App.ActiveDocument.C2022.Angle=360.00 
App.ActiveDocument.C2022.Placement=Base.Placement(Base.Vector(-64.940086,-158.304406,527.521724),Base.Rotation(0.226294,-0.392933,0.000000,0.891288))
App.ActiveDocument.addObject("Part::Cylinder","C2023")
App.ActiveDocument.C2023.Radius=0.750000
App.ActiveDocument.C2023.Height=15.00
App.ActiveDocument.C2023.Angle=360.00 
App.ActiveDocument.C2023.Placement=Base.Placement(Base.Vector(-65.070156,-160.371687,525.729618),Base.Rotation(0.273141,-0.399005,0.000000,0.875322))
App.ActiveDocument.addObject("Part::Cylinder","C2024")
App.ActiveDocument.C2024.Radius=0.750000
App.ActiveDocument.C2024.Height=15.00
App.ActiveDocument.C2024.Angle=360.00 
App.ActiveDocument.C2024.Placement=Base.Placement(Base.Vector(-65.175611,-162.125620,523.811045),Base.Rotation(0.315814,-0.402765,0.000000,0.859094))
App.ActiveDocument.addObject("Part::Cylinder","C2025")
App.ActiveDocument.C2025.Radius=0.750000
App.ActiveDocument.C2025.Height=15.00
App.ActiveDocument.C2025.Angle=360.00 
App.ActiveDocument.C2025.Placement=Base.Placement(Base.Vector(-65.497181,-163.499976,521.534372),Base.Rotation(0.355946,-0.411575,0.000000,0.838993))
App.ActiveDocument.addObject("Part::Cylinder","C2026")
App.ActiveDocument.C2026.Radius=0.750000
App.ActiveDocument.C2026.Height=15.00
App.ActiveDocument.C2026.Angle=360.00 
App.ActiveDocument.C2026.Placement=Base.Placement(Base.Vector(-65.745787,-164.614293,519.261905),Base.Rotation(0.390836,-0.417734,0.000000,0.820211))
App.ActiveDocument.addObject("Part::Cylinder","C2027")
App.ActiveDocument.C2027.Radius=0.750000
App.ActiveDocument.C2027.Height=15.00
App.ActiveDocument.C2027.Angle=360.00 
App.ActiveDocument.C2027.Placement=Base.Placement(Base.Vector(-65.962814,-165.588307,516.724315),Base.Rotation(0.423617,-0.426477,0.000000,0.799166))
App.ActiveDocument.addObject("Part::Cylinder","C2028")
App.ActiveDocument.C2028.Radius=0.750000
App.ActiveDocument.C2028.Height=15.00
App.ActiveDocument.C2028.Angle=360.00 
App.ActiveDocument.C2028.Placement=Base.Placement(Base.Vector(-66.030683,-166.450939,514.100163),Base.Rotation(0.452860,-0.435280,0.000000,0.778106))
App.ActiveDocument.addObject("Part::Cylinder","C2029")
App.ActiveDocument.C2029.Radius=0.750000
App.ActiveDocument.C2029.Height=15.00
App.ActiveDocument.C2029.Angle=360.00 
App.ActiveDocument.C2029.Placement=Base.Placement(Base.Vector(-66.167186,-167.004853,511.405393),Base.Rotation(0.476385,-0.444495,0.000000,0.758605))
App.ActiveDocument.addObject("Part::Cylinder","C2030")
App.ActiveDocument.C2030.Radius=0.750000
App.ActiveDocument.C2030.Height=15.00
App.ActiveDocument.C2030.Angle=360.00 
App.ActiveDocument.C2030.Placement=Base.Placement(Base.Vector(-66.150561,-167.472826,508.655039),Base.Rotation(0.499248,-0.454990,0.000000,0.737384))
App.ActiveDocument.addObject("Part::Cylinder","C2031")
App.ActiveDocument.C2031.Radius=0.750000
App.ActiveDocument.C2031.Height=15.00
App.ActiveDocument.C2031.Angle=360.00 
App.ActiveDocument.C2031.Placement=Base.Placement(Base.Vector(-65.997246,-167.844989,505.918780),Base.Rotation(0.515767,-0.465109,0.000000,0.719485))
App.ActiveDocument.addObject("Part::Cylinder","C2032")
App.ActiveDocument.C2032.Radius=0.750000
App.ActiveDocument.C2032.Height=15.00
App.ActiveDocument.C2032.Angle=360.00 
App.ActiveDocument.C2032.Placement=Base.Placement(Base.Vector(-66.039377,-167.846578,503.224058),Base.Rotation(0.528644,-0.478403,0.000000,0.701190))
App.ActiveDocument.addObject("Part::Cylinder","C2033")
App.ActiveDocument.C2033.Radius=0.750000
App.ActiveDocument.C2033.Height=15.00
App.ActiveDocument.C2033.Angle=360.00 
App.ActiveDocument.C2033.Placement=Base.Placement(Base.Vector(-66.088528,-167.660021,500.512565),Base.Rotation(0.537408,-0.492139,0.000000,0.684830))
App.ActiveDocument.addObject("Part::Cylinder","C2034")
App.ActiveDocument.C2034.Radius=0.750000
App.ActiveDocument.C2034.Height=15.00
App.ActiveDocument.C2034.Angle=360.00 
App.ActiveDocument.C2034.Placement=Base.Placement(Base.Vector(-65.972299,-167.484106,498.017817),Base.Rotation(0.544531,-0.505616,0.000000,0.669207))
App.ActiveDocument.addObject("Part::Cylinder","C2035")
App.ActiveDocument.C2035.Radius=0.750000
App.ActiveDocument.C2035.Height=15.00
App.ActiveDocument.C2035.Angle=360.00 
App.ActiveDocument.C2035.Placement=Base.Placement(Base.Vector(-65.921287,-167.073302,495.382789),Base.Rotation(0.549005,-0.521523,0.000000,0.653152))
App.ActiveDocument.addObject("Part::Cylinder","C2036")
App.ActiveDocument.C2036.Radius=0.750000
App.ActiveDocument.C2036.Height=15.00
App.ActiveDocument.C2036.Angle=360.00 
App.ActiveDocument.C2036.Placement=Base.Placement(Base.Vector(-65.883829,-166.516011,492.867203),Base.Rotation(0.550755,-0.538673,0.000000,0.637573))
App.ActiveDocument.addObject("Part::Cylinder","C2037")
App.ActiveDocument.C2037.Radius=0.750000
App.ActiveDocument.C2037.Height=15.00
App.ActiveDocument.C2037.Angle=360.00 
App.ActiveDocument.C2037.Placement=Base.Placement(Base.Vector(-65.727520,-165.850715,490.145390),Base.Rotation(0.549849,-0.559128,0.000000,0.620517))
App.ActiveDocument.addObject("Part::Cylinder","C2038")
App.ActiveDocument.C2038.Radius=0.750000
App.ActiveDocument.C2038.Height=15.00
App.ActiveDocument.C2038.Angle=360.00 
App.ActiveDocument.C2038.Placement=Base.Placement(Base.Vector(-65.720290,-164.934968,487.660662),Base.Rotation(0.545918,-0.579848,0.000000,0.604773))
App.ActiveDocument.addObject("Part::Cylinder","C2039")
App.ActiveDocument.C2039.Radius=0.750000
App.ActiveDocument.C2039.Height=15.00
App.ActiveDocument.C2039.Angle=360.00 
App.ActiveDocument.C2039.Placement=Base.Placement(Base.Vector(-65.526146,-164.046692,485.197346),Base.Rotation(0.539182,-0.602364,0.000000,0.588592))
App.ActiveDocument.addObject("Part::Cylinder","C2040")
App.ActiveDocument.C2040.Radius=0.750000
App.ActiveDocument.C2040.Height=15.00
App.ActiveDocument.C2040.Angle=360.00 
App.ActiveDocument.C2040.Placement=Base.Placement(Base.Vector(-65.284648,-162.990966,482.682287),Base.Rotation(0.528332,-0.628186,0.000000,0.571180))
App.ActiveDocument.addObject("Part::Cylinder","C2041")
App.ActiveDocument.C2041.Radius=0.750000
App.ActiveDocument.C2041.Height=15.00
App.ActiveDocument.C2041.Angle=360.00 
App.ActiveDocument.C2041.Placement=Base.Placement(Base.Vector(-64.921529,-161.897933,480.223719),Base.Rotation(0.512510,-0.656780,0.000000,0.553149))
App.ActiveDocument.addObject("Part::Cylinder","C2042")
App.ActiveDocument.C2042.Radius=0.750000
App.ActiveDocument.C2042.Height=15.00
App.ActiveDocument.C2042.Angle=360.00 
App.ActiveDocument.C2042.Placement=Base.Placement(Base.Vector(-64.795320,-160.454842,478.048531),Base.Rotation(0.494259,-0.684521,0.000000,0.535854))
App.ActiveDocument.addObject("Part::Cylinder","C2043")
App.ActiveDocument.C2043.Radius=0.750000
App.ActiveDocument.C2043.Height=15.00
App.ActiveDocument.C2043.Angle=360.00 
App.ActiveDocument.C2043.Placement=Base.Placement(Base.Vector(-64.831613,-158.368449,475.799715),Base.Rotation(0.466758,-0.721289,0.000000,0.511742))
App.ActiveDocument.addObject("Part::Cylinder","C2044")
App.ActiveDocument.C2044.Radius=0.750000
App.ActiveDocument.C2044.Height=15.00
App.ActiveDocument.C2044.Angle=360.00 
App.ActiveDocument.C2044.Placement=Base.Placement(Base.Vector(-64.648726,-156.350391,473.748827),Base.Rotation(0.428941,-0.762036,0.000000,0.485088))
App.ActiveDocument.addObject("Part::Cylinder","C2045")
App.ActiveDocument.C2045.Radius=0.750000
App.ActiveDocument.C2045.Height=15.00
App.ActiveDocument.C2045.Angle=360.00 
App.ActiveDocument.C2045.Placement=Base.Placement(Base.Vector(-64.377657,-154.344975,471.998013),Base.Rotation(0.383171,-0.802055,0.000000,0.458134))
App.ActiveDocument.addObject("Part::Cylinder","C2046")
App.ActiveDocument.C2046.Radius=0.750000
App.ActiveDocument.C2046.Height=15.00
App.ActiveDocument.C2046.Angle=360.00 
App.ActiveDocument.C2046.Placement=Base.Placement(Base.Vector(-63.325991,-152.778019,469.905303),Base.Rotation(0.311113,-0.846626,0.000000,0.431779))
App.ActiveDocument.addObject("Part::Cylinder","C2047")
App.ActiveDocument.C2047.Radius=0.750000
App.ActiveDocument.C2047.Height=15.00
App.ActiveDocument.C2047.Angle=360.00 
App.ActiveDocument.C2047.Placement=Base.Placement(Base.Vector(-61.888094,-151.712517,467.876412),Base.Rotation(0.231105,-0.880239,0.000000,0.414451))
App.ActiveDocument.addObject("Part::Cylinder","C2048")
App.ActiveDocument.C2048.Radius=0.750000
App.ActiveDocument.C2048.Height=15.00
App.ActiveDocument.C2048.Angle=360.00 
App.ActiveDocument.C2048.Placement=Base.Placement(Base.Vector(-67.073350,-144.171205,529.844300),Base.Rotation(0.029260,-0.398011,0.000000,0.916914))
App.ActiveDocument.addObject("Part::Cylinder","C2049")
App.ActiveDocument.C2049.Radius=0.750000
App.ActiveDocument.C2049.Height=15.00
App.ActiveDocument.C2049.Angle=360.00 
App.ActiveDocument.C2049.Placement=Base.Placement(Base.Vector(-66.770212,-147.372271,529.779843),Base.Rotation(0.062846,-0.396618,0.000000,0.915830))
App.ActiveDocument.addObject("Part::Cylinder","C2050")
App.ActiveDocument.C2050.Radius=0.750000
App.ActiveDocument.C2050.Height=15.00
App.ActiveDocument.C2050.Angle=360.00 
App.ActiveDocument.C2050.Placement=Base.Placement(Base.Vector(-67.105581,-150.344328,528.753232),Base.Rotation(0.101766,-0.402591,0.000000,0.909706))
App.ActiveDocument.addObject("Part::Cylinder","C2051")
App.ActiveDocument.C2051.Radius=0.750000
App.ActiveDocument.C2051.Height=15.00
App.ActiveDocument.C2051.Angle=360.00 
App.ActiveDocument.C2051.Placement=Base.Placement(Base.Vector(-67.208136,-153.182758,527.653764),Base.Rotation(0.144664,-0.406446,0.000000,0.902150))
App.ActiveDocument.addObject("Part::Cylinder","C2052")
App.ActiveDocument.C2052.Radius=0.750000
App.ActiveDocument.C2052.Height=15.00
App.ActiveDocument.C2052.Angle=360.00 
App.ActiveDocument.C2052.Placement=Base.Placement(Base.Vector(-67.289203,-155.610953,526.364619),Base.Rotation(0.193717,-0.410452,0.000000,0.891069))
App.ActiveDocument.addObject("Part::Cylinder","C2053")
App.ActiveDocument.C2053.Radius=0.750000
App.ActiveDocument.C2053.Height=15.00
App.ActiveDocument.C2053.Angle=360.00 
App.ActiveDocument.C2053.Placement=Base.Placement(Base.Vector(-67.519810,-157.789633,524.617495),Base.Rotation(0.239950,-0.416781,0.000000,0.876765))
App.ActiveDocument.addObject("Part::Cylinder","C2054")
App.ActiveDocument.C2054.Radius=0.750000
App.ActiveDocument.C2054.Height=15.00
App.ActiveDocument.C2054.Angle=360.00 
App.ActiveDocument.C2054.Placement=Base.Placement(Base.Vector(-67.682762,-159.734658,522.659500),Base.Rotation(0.281569,-0.423889,0.000000,0.860835))
App.ActiveDocument.addObject("Part::Cylinder","C2055")
App.ActiveDocument.C2055.Radius=0.750000
App.ActiveDocument.C2055.Height=15.00
App.ActiveDocument.C2055.Angle=360.00 
App.ActiveDocument.C2055.Placement=Base.Placement(Base.Vector(-68.002292,-161.070994,520.612202),Base.Rotation(0.323364,-0.431460,0.000000,0.842186))
App.ActiveDocument.addObject("Part::Cylinder","C2056")
App.ActiveDocument.C2056.Radius=0.750000
App.ActiveDocument.C2056.Height=15.00
App.ActiveDocument.C2056.Angle=360.00 
App.ActiveDocument.C2056.Placement=Base.Placement(Base.Vector(-68.246140,-162.258035,518.394860),Base.Rotation(0.359960,-0.438924,0.000000,0.823271))
App.ActiveDocument.addObject("Part::Cylinder","C2057")
App.ActiveDocument.C2057.Radius=0.750000
App.ActiveDocument.C2057.Height=15.00
App.ActiveDocument.C2057.Angle=360.00 
App.ActiveDocument.C2057.Placement=Base.Placement(Base.Vector(-68.446835,-163.236713,516.052260),Base.Rotation(0.396548,-0.446613,0.000000,0.802052))
App.ActiveDocument.addObject("Part::Cylinder","C2058")
App.ActiveDocument.C2058.Radius=0.750000
App.ActiveDocument.C2058.Height=15.00
App.ActiveDocument.C2058.Angle=360.00 
App.ActiveDocument.C2058.Placement=Base.Placement(Base.Vector(-68.644544,-163.970604,513.597413),Base.Rotation(0.428777,-0.455178,0.000000,0.780361))
App.ActiveDocument.addObject("Part::Cylinder","C2059")
App.ActiveDocument.C2059.Radius=0.750000
App.ActiveDocument.C2059.Height=15.00
App.ActiveDocument.C2059.Angle=360.00 
App.ActiveDocument.C2059.Placement=Base.Placement(Base.Vector(-68.772519,-164.546475,511.043700),Base.Rotation(0.453985,-0.462502,0.000000,0.761571))
App.ActiveDocument.addObject("Part::Cylinder","C2060")
App.ActiveDocument.C2060.Radius=0.750000
App.ActiveDocument.C2060.Height=15.00
App.ActiveDocument.C2060.Angle=360.00 
App.ActiveDocument.C2060.Placement=Base.Placement(Base.Vector(-68.835207,-164.949646,508.435100),Base.Rotation(0.477502,-0.473913,0.000000,0.739864))
App.ActiveDocument.addObject("Part::Cylinder","C2061")
App.ActiveDocument.C2061.Radius=0.750000
App.ActiveDocument.C2061.Height=15.00
App.ActiveDocument.C2061.Angle=360.00 
App.ActiveDocument.C2061.Placement=Base.Placement(Base.Vector(-68.785639,-165.245395,505.727062),Base.Rotation(0.498347,-0.483903,0.000000,0.719367))
App.ActiveDocument.addObject("Part::Cylinder","C2062")
App.ActiveDocument.C2062.Radius=0.750000
App.ActiveDocument.C2062.Height=15.00
App.ActiveDocument.C2062.Angle=360.00 
App.ActiveDocument.C2062.Placement=Base.Placement(Base.Vector(-68.805867,-165.259874,503.210483),Base.Rotation(0.512750,-0.496272,0.000000,0.700573))
App.ActiveDocument.addObject("Part::Cylinder","C2063")
App.ActiveDocument.C2063.Radius=0.750000
App.ActiveDocument.C2063.Height=15.00
App.ActiveDocument.C2063.Angle=360.00 
App.ActiveDocument.C2063.Placement=Base.Placement(Base.Vector(-68.674660,-165.230712,500.558854),Base.Rotation(0.524213,-0.508230,0.000000,0.683303))
App.ActiveDocument.addObject("Part::Cylinder","C2064")
App.ActiveDocument.C2064.Radius=0.750000
App.ActiveDocument.C2064.Height=15.00
App.ActiveDocument.C2064.Angle=360.00 
App.ActiveDocument.C2064.Placement=Base.Placement(Base.Vector(-68.606874,-164.952039,497.894574),Base.Rotation(0.534350,-0.523125,0.000000,0.663936))
App.ActiveDocument.addObject("Part::Cylinder","C2065")
App.ActiveDocument.C2065.Radius=0.750000
App.ActiveDocument.C2065.Height=15.00
App.ActiveDocument.C2065.Angle=360.00 
App.ActiveDocument.C2065.Placement=Base.Placement(Base.Vector(-68.596702,-164.502295,495.544418),Base.Rotation(0.538863,-0.537894,0.000000,0.648304))
App.ActiveDocument.addObject("Part::Cylinder","C2066")
App.ActiveDocument.C2066.Radius=0.750000
App.ActiveDocument.C2066.Height=15.00
App.ActiveDocument.C2066.Angle=360.00 
App.ActiveDocument.C2066.Placement=Base.Placement(Base.Vector(-68.469030,-163.963307,492.995681),Base.Rotation(0.542042,-0.554077,0.000000,0.631813))
App.ActiveDocument.addObject("Part::Cylinder","C2067")
App.ActiveDocument.C2067.Radius=0.750000
App.ActiveDocument.C2067.Height=15.00
App.ActiveDocument.C2067.Angle=360.00 
App.ActiveDocument.C2067.Placement=Base.Placement(Base.Vector(-68.625128,-162.784810,490.050133),Base.Rotation(0.541669,-0.578239,0.000000,0.610110))
App.ActiveDocument.addObject("Part::Cylinder","C2068")
App.ActiveDocument.C2068.Radius=0.750000
App.ActiveDocument.C2068.Height=15.00
App.ActiveDocument.C2068.Angle=360.00 
App.ActiveDocument.C2068.Placement=Base.Placement(Base.Vector(-68.483055,-161.616707,487.031878),Base.Rotation(0.537369,-0.605931,0.000000,0.586584))
App.ActiveDocument.addObject("Part::Cylinder","C2069")
App.ActiveDocument.C2069.Radius=0.750000
App.ActiveDocument.C2069.Height=15.00
App.ActiveDocument.C2069.Angle=360.00 
App.ActiveDocument.C2069.Placement=Base.Placement(Base.Vector(-68.193258,-160.482104,484.318423),Base.Rotation(0.529245,-0.631744,0.000000,0.566391))
App.ActiveDocument.addObject("Part::Cylinder","C2070")
App.ActiveDocument.C2070.Radius=0.750000
App.ActiveDocument.C2070.Height=15.00
App.ActiveDocument.C2070.Angle=360.00 
App.ActiveDocument.C2070.Placement=Base.Placement(Base.Vector(-67.895936,-159.245315,481.865761),Base.Rotation(0.517875,-0.658274,0.000000,0.546334))
App.ActiveDocument.addObject("Part::Cylinder","C2071")
App.ActiveDocument.C2071.Radius=0.750000
App.ActiveDocument.C2071.Height=15.00
App.ActiveDocument.C2071.Angle=360.00 
App.ActiveDocument.C2071.Placement=Base.Placement(Base.Vector(-67.437907,-157.949957,479.435613),Base.Rotation(0.498527,-0.690905,0.000000,0.523566))
App.ActiveDocument.addObject("Part::Cylinder","C2072")
App.ActiveDocument.C2072.Radius=0.750000
App.ActiveDocument.C2072.Height=15.00
App.ActiveDocument.C2072.Angle=360.00 
App.ActiveDocument.C2072.Placement=Base.Placement(Base.Vector(-67.826615,-155.538097,477.510256),Base.Rotation(0.476710,-0.725841,0.000000,0.495886))
App.ActiveDocument.addObject("Part::Cylinder","C2073")
App.ActiveDocument.C2073.Radius=0.750000
App.ActiveDocument.C2073.Height=15.00
App.ActiveDocument.C2073.Angle=360.00 
App.ActiveDocument.C2073.Placement=Base.Placement(Base.Vector(-67.546051,-153.396498,475.367783),Base.Rotation(0.439604,-0.767233,0.000000,0.467013))
App.ActiveDocument.addObject("Part::Cylinder","C2074")
App.ActiveDocument.C2074.Radius=0.750000
App.ActiveDocument.C2074.Height=15.00
App.ActiveDocument.C2074.Angle=360.00 
App.ActiveDocument.C2074.Placement=Base.Placement(Base.Vector(-67.059592,-151.255270,473.445186),Base.Rotation(0.383270,-0.815181,0.000000,0.434262))
App.ActiveDocument.addObject("Part::Cylinder","C2075")
App.ActiveDocument.C2075.Radius=0.750000
App.ActiveDocument.C2075.Height=15.00
App.ActiveDocument.C2075.Angle=360.00 
App.ActiveDocument.C2075.Placement=Base.Placement(Base.Vector(-65.812260,-149.583382,471.343508),Base.Rotation(0.309196,-0.860638,0.000000,0.404598))
App.ActiveDocument.addObject("Part::Cylinder","C2076")
App.ActiveDocument.C2076.Radius=0.750000
App.ActiveDocument.C2076.Height=15.00
App.ActiveDocument.C2076.Angle=360.00 
App.ActiveDocument.C2076.Placement=Base.Placement(Base.Vector(-63.930265,-148.271670,469.088170),Base.Rotation(0.217070,-0.899971,0.000000,0.378064))
App.ActiveDocument.addObject("Part::Cylinder","C2077")
App.ActiveDocument.C2077.Radius=0.750000
App.ActiveDocument.C2077.Height=15.00
App.ActiveDocument.C2077.Angle=360.00 
App.ActiveDocument.C2077.Placement=Base.Placement(Base.Vector(-69.407997,-144.143449,527.218038),Base.Rotation(0.029583,-0.420408,0.000000,0.906853))
App.ActiveDocument.addObject("Part::Cylinder","C2078")
App.ActiveDocument.C2078.Radius=0.750000
App.ActiveDocument.C2078.Height=15.00
App.ActiveDocument.C2078.Angle=360.00 
App.ActiveDocument.C2078.Placement=Base.Placement(Base.Vector(-69.167754,-147.310248,527.083266),Base.Rotation(0.065743,-0.420214,0.000000,0.905040))
App.ActiveDocument.addObject("Part::Cylinder","C2079")
App.ActiveDocument.C2079.Radius=0.750000
App.ActiveDocument.C2079.Height=15.00
App.ActiveDocument.C2079.Angle=360.00 
App.ActiveDocument.C2079.Placement=Base.Placement(Base.Vector(-69.495180,-150.185474,525.981829),Base.Rotation(0.106784,-0.426485,0.000000,0.898169))
App.ActiveDocument.addObject("Part::Cylinder","C2080")
App.ActiveDocument.C2080.Radius=0.750000
App.ActiveDocument.C2080.Height=15.00
App.ActiveDocument.C2080.Angle=360.00 
App.ActiveDocument.C2080.Placement=Base.Placement(Base.Vector(-69.562732,-152.896134,524.862070),Base.Rotation(0.151414,-0.430559,0.000000,0.889771))
App.ActiveDocument.addObject("Part::Cylinder","C2081")
App.ActiveDocument.C2081.Radius=0.750000
App.ActiveDocument.C2081.Height=15.00
App.ActiveDocument.C2081.Angle=360.00 
App.ActiveDocument.C2081.Placement=Base.Placement(Base.Vector(-69.719518,-155.183951,523.404695),Base.Rotation(0.197783,-0.436182,0.000000,0.877854))
App.ActiveDocument.addObject("Part::Cylinder","C2082")
App.ActiveDocument.C2082.Radius=0.750000
App.ActiveDocument.C2082.Height=15.00
App.ActiveDocument.C2082.Angle=360.00 
App.ActiveDocument.C2082.Placement=Base.Placement(Base.Vector(-70.003236,-157.144369,521.517517),Base.Rotation(0.245256,-0.443929,0.000000,0.861845))
App.ActiveDocument.addObject("Part::Cylinder","C2083")
App.ActiveDocument.C2083.Radius=0.750000
App.ActiveDocument.C2083.Height=15.00
App.ActiveDocument.C2083.Angle=360.00 
App.ActiveDocument.C2083.Placement=Base.Placement(Base.Vector(-70.310600,-158.674616,519.472005),Base.Rotation(0.289451,-0.450981,0.000000,0.844295))
App.ActiveDocument.addObject("Part::Cylinder","C2084")
App.ActiveDocument.C2084.Radius=0.750000
App.ActiveDocument.C2084.Height=15.00
App.ActiveDocument.C2084.Angle=360.00 
App.ActiveDocument.C2084.Placement=Base.Placement(Base.Vector(-70.661699,-159.743525,517.395992),Base.Rotation(0.328909,-0.460764,0.000000,0.824327))
App.ActiveDocument.addObject("Part::Cylinder","C2085")
App.ActiveDocument.C2085.Radius=0.750000
App.ActiveDocument.C2085.Height=15.00
App.ActiveDocument.C2085.Angle=360.00 
App.ActiveDocument.C2085.Placement=Base.Placement(Base.Vector(-70.859983,-160.848691,515.011889),Base.Rotation(0.369135,-0.466891,0.000000,0.803587))
App.ActiveDocument.addObject("Part::Cylinder","C2086")
App.ActiveDocument.C2086.Radius=0.750000
App.ActiveDocument.C2086.Height=15.00
App.ActiveDocument.C2086.Angle=360.00 
App.ActiveDocument.C2086.Placement=Base.Placement(Base.Vector(-70.999527,-161.633154,512.746162),Base.Rotation(0.403220,-0.474792,0.000000,0.782296))
App.ActiveDocument.addObject("Part::Cylinder","C2087")
App.ActiveDocument.C2087.Radius=0.750000
App.ActiveDocument.C2087.Height=15.00
App.ActiveDocument.C2087.Angle=360.00 
App.ActiveDocument.C2087.Placement=Base.Placement(Base.Vector(-71.237918,-162.068237,510.375885),Base.Rotation(0.431288,-0.484532,0.000000,0.761065))
App.ActiveDocument.addObject("Part::Cylinder","C2088")
App.ActiveDocument.C2088.Radius=0.750000
App.ActiveDocument.C2088.Height=15.00
App.ActiveDocument.C2088.Angle=360.00 
App.ActiveDocument.C2088.Placement=Base.Placement(Base.Vector(-71.442017,-162.317544,507.971780),Base.Rotation(0.452277,-0.493111,0.000000,0.743161))
App.ActiveDocument.addObject("Part::Cylinder","C2089")
App.ActiveDocument.C2089.Radius=0.750000
App.ActiveDocument.C2089.Height=15.00
App.ActiveDocument.C2089.Angle=360.00 
App.ActiveDocument.C2089.Placement=Base.Placement(Base.Vector(-71.435603,-162.578682,505.505020),Base.Rotation(0.476284,-0.502559,0.000000,0.721518))
App.ActiveDocument.addObject("Part::Cylinder","C2090")
App.ActiveDocument.C2090.Radius=0.750000
App.ActiveDocument.C2090.Height=15.00
App.ActiveDocument.C2090.Angle=360.00 
App.ActiveDocument.C2090.Placement=Base.Placement(Base.Vector(-71.333474,-162.725569,502.926986),Base.Rotation(0.495370,-0.513654,0.000000,0.700549))
App.ActiveDocument.addObject("Part::Cylinder","C2091")
App.ActiveDocument.C2091.Radius=0.750000
App.ActiveDocument.C2091.Height=15.00
App.ActiveDocument.C2091.Angle=360.00 
App.ActiveDocument.C2091.Placement=Base.Placement(Base.Vector(-71.178505,-162.707268,500.260168),Base.Rotation(0.509393,-0.525289,0.000000,0.681608))
App.ActiveDocument.addObject("Part::Cylinder","C2092")
App.ActiveDocument.C2092.Radius=0.750000
App.ActiveDocument.C2092.Height=15.00
App.ActiveDocument.C2092.Angle=360.00 
App.ActiveDocument.C2092.Placement=Base.Placement(Base.Vector(-71.385251,-162.178635,498.027725),Base.Rotation(0.519542,-0.538694,0.000000,0.663239))
App.ActiveDocument.addObject("Part::Cylinder","C2093")
App.ActiveDocument.C2093.Radius=0.750000
App.ActiveDocument.C2093.Height=15.00
App.ActiveDocument.C2093.Angle=360.00 
App.ActiveDocument.C2093.Placement=Base.Placement(Base.Vector(-71.129686,-161.901958,495.480318),Base.Rotation(0.528639,-0.553578,0.000000,0.643501))
App.ActiveDocument.addObject("Part::Cylinder","C2094")
App.ActiveDocument.C2094.Radius=0.750000
App.ActiveDocument.C2094.Height=15.00
App.ActiveDocument.C2094.Angle=360.00 
App.ActiveDocument.C2094.Placement=Base.Placement(Base.Vector(-71.324673,-160.832409,492.596645),Base.Rotation(0.533060,-0.573843,0.000000,0.621733))
App.ActiveDocument.addObject("Part::Cylinder","C2095")
App.ActiveDocument.C2095.Radius=0.750000
App.ActiveDocument.C2095.Height=15.00
App.ActiveDocument.C2095.Angle=360.00 
App.ActiveDocument.C2095.Placement=Base.Placement(Base.Vector(-71.364777,-159.656918,489.728973),Base.Rotation(0.533972,-0.598148,0.000000,0.597573))
App.ActiveDocument.addObject("Part::Cylinder","C2096")
App.ActiveDocument.C2096.Radius=0.750000
App.ActiveDocument.C2096.Height=15.00
App.ActiveDocument.C2096.Angle=360.00 
App.ActiveDocument.C2096.Placement=Base.Placement(Base.Vector(-71.191578,-158.404725,486.841061),Base.Rotation(0.531183,-0.623902,0.000000,0.573229))
App.ActiveDocument.addObject("Part::Cylinder","C2097")
App.ActiveDocument.C2097.Radius=0.750000
App.ActiveDocument.C2097.Height=15.00
App.ActiveDocument.C2097.Angle=360.00 
App.ActiveDocument.C2097.Placement=Base.Placement(Base.Vector(-70.856055,-157.112385,484.126824),Base.Rotation(0.522672,-0.653419,0.000000,0.547593))
App.ActiveDocument.addObject("Part::Cylinder","C2098")
App.ActiveDocument.C2098.Radius=0.750000
App.ActiveDocument.C2098.Height=15.00
App.ActiveDocument.C2098.Angle=360.00 
App.ActiveDocument.C2098.Placement=Base.Placement(Base.Vector(-70.499638,-155.653721,481.618043),Base.Rotation(0.509197,-0.682776,0.000000,0.523962))
App.ActiveDocument.addObject("Part::Cylinder","C2099")
App.ActiveDocument.C2099.Radius=0.750000
App.ActiveDocument.C2099.Height=15.00
App.ActiveDocument.C2099.Angle=360.00 
App.ActiveDocument.C2099.Placement=Base.Placement(Base.Vector(-70.524378,-154.076686,479.935682),Base.Rotation(0.490259,-0.713114,0.000000,0.501113))
App.ActiveDocument.addObject("Part::Cylinder","C2100")
App.ActiveDocument.C2100.Radius=0.750000
App.ActiveDocument.C2100.Height=15.00
App.ActiveDocument.C2100.Angle=360.00 
App.ActiveDocument.C2100.Placement=Base.Placement(Base.Vector(-70.626672,-151.978791,478.217617),Base.Rotation(0.457682,-0.751879,0.000000,0.474558))
App.ActiveDocument.addObject("Part::Cylinder","C2101")
App.ActiveDocument.C2101.Radius=0.750000
App.ActiveDocument.C2101.Height=15.00
App.ActiveDocument.C2101.Angle=360.00 
App.ActiveDocument.C2101.Placement=Base.Placement(Base.Vector(-70.165156,-150.136904,476.376011),Base.Rotation(0.403373,-0.799717,0.000000,0.444684))
App.ActiveDocument.addObject("Part::Cylinder","C2102")
App.ActiveDocument.C2102.Radius=0.750000
App.ActiveDocument.C2102.Height=15.00
App.ActiveDocument.C2102.Angle=360.00 
App.ActiveDocument.C2102.Placement=Base.Placement(Base.Vector(-69.303985,-148.210623,474.434346),Base.Rotation(0.330862,-0.849188,0.000000,0.411594))
App.ActiveDocument.addObject("Part::Cylinder","C2103")
App.ActiveDocument.C2103.Radius=0.750000
App.ActiveDocument.C2103.Height=15.00
App.ActiveDocument.C2103.Angle=360.00 
App.ActiveDocument.C2103.Placement=Base.Placement(Base.Vector(-67.817482,-146.455462,472.317708),Base.Rotation(0.256138,-0.887131,0.000000,0.383917))
App.ActiveDocument.addObject("Part::Cylinder","C2104")
App.ActiveDocument.C2104.Radius=0.750000
App.ActiveDocument.C2104.Height=15.00
App.ActiveDocument.C2104.Angle=360.00 
App.ActiveDocument.C2104.Placement=Base.Placement(Base.Vector(-65.772845,-145.017315,470.106941),Base.Rotation(0.184900,-0.915226,0.000000,0.358014))
App.ActiveDocument.addObject("Part::Cylinder","C2105")
App.ActiveDocument.C2105.Radius=0.750000
App.ActiveDocument.C2105.Height=15.00
App.ActiveDocument.C2105.Angle=360.00 
App.ActiveDocument.C2105.Placement=Base.Placement(Base.Vector(-71.561186,-144.116015,524.528216),Base.Rotation(0.031115,-0.444760,0.000000,0.895109))
App.ActiveDocument.addObject("Part::Cylinder","C2106")
App.ActiveDocument.C2106.Radius=0.750000
App.ActiveDocument.C2106.Height=15.00
App.ActiveDocument.C2106.Angle=360.00 
App.ActiveDocument.C2106.Placement=Base.Placement(Base.Vector(-71.416757,-147.233890,524.264427),Base.Rotation(0.068475,-0.444957,0.000000,0.892930))
App.ActiveDocument.addObject("Part::Cylinder","C2107")
App.ActiveDocument.C2107.Radius=0.750000
App.ActiveDocument.C2107.Height=15.00
App.ActiveDocument.C2107.Angle=360.00 
App.ActiveDocument.C2107.Placement=Base.Placement(Base.Vector(-71.746308,-149.997584,523.061610),Base.Rotation(0.110620,-0.451516,0.000000,0.885379))
App.ActiveDocument.addObject("Part::Cylinder","C2108")
App.ActiveDocument.C2108.Radius=0.750000
App.ActiveDocument.C2108.Height=15.00
App.ActiveDocument.C2108.Angle=360.00 
App.ActiveDocument.C2108.Placement=Base.Placement(Base.Vector(-71.858715,-152.549822,521.812271),Base.Rotation(0.157020,-0.455825,0.000000,0.876109))
App.ActiveDocument.addObject("Part::Cylinder","C2109")
App.ActiveDocument.C2109.Radius=0.750000
App.ActiveDocument.C2109.Height=15.00
App.ActiveDocument.C2109.Angle=360.00 
App.ActiveDocument.C2109.Placement=Base.Placement(Base.Vector(-72.049305,-154.552312,520.289934),Base.Rotation(0.204870,-0.464685,0.000000,0.861450))
App.ActiveDocument.addObject("Part::Cylinder","C2110")
App.ActiveDocument.C2110.Radius=0.750000
App.ActiveDocument.C2110.Height=15.00
App.ActiveDocument.C2110.Angle=360.00 
App.ActiveDocument.C2110.Placement=Base.Placement(Base.Vector(-72.463546,-156.124523,518.252311),Base.Rotation(0.246247,-0.473126,0.000000,0.845881))
App.ActiveDocument.addObject("Part::Cylinder","C2111")
App.ActiveDocument.C2111.Radius=0.750000
App.ActiveDocument.C2111.Height=15.00
App.ActiveDocument.C2111.Angle=360.00 
App.ActiveDocument.C2111.Placement=Base.Placement(Base.Vector(-72.769760,-157.434257,516.147994),Base.Rotation(0.292265,-0.481926,0.000000,0.826032))
App.ActiveDocument.addObject("Part::Cylinder","C2112")
App.ActiveDocument.C2112.Radius=0.750000
App.ActiveDocument.C2112.Height=15.00
App.ActiveDocument.C2112.Angle=360.00 
App.ActiveDocument.C2112.Placement=Base.Placement(Base.Vector(-73.051605,-158.444375,513.907413),Base.Rotation(0.335773,-0.490871,0.000000,0.803929))
App.ActiveDocument.addObject("Part::Cylinder","C2113")
App.ActiveDocument.C2113.Radius=0.750000
App.ActiveDocument.C2113.Height=15.00
App.ActiveDocument.C2113.Angle=360.00 
App.ActiveDocument.C2113.Placement=Base.Placement(Base.Vector(-73.186011,-159.329201,511.590374),Base.Rotation(0.371814,-0.497311,0.000000,0.783860))
App.ActiveDocument.addObject("Part::Cylinder","C2114")
App.ActiveDocument.C2114.Radius=0.750000
App.ActiveDocument.C2114.Height=15.00
App.ActiveDocument.C2114.Angle=360.00 
App.ActiveDocument.C2114.Placement=Base.Placement(Base.Vector(-73.521599,-159.606192,509.407885),Base.Rotation(0.402491,-0.507287,0.000000,0.762011))
App.ActiveDocument.addObject("Part::Cylinder","C2115")
App.ActiveDocument.C2115.Radius=0.750000
App.ActiveDocument.C2115.Height=15.00
App.ActiveDocument.C2115.Angle=360.00 
App.ActiveDocument.C2115.Placement=Base.Placement(Base.Vector(-73.654777,-159.919615,507.173987),Base.Rotation(0.425222,-0.515382,0.000000,0.744021))
App.ActiveDocument.addObject("Part::Cylinder","C2116")
App.ActiveDocument.C2116.Radius=0.750000
App.ActiveDocument.C2116.Height=15.00
App.ActiveDocument.C2116.Angle=360.00 
App.ActiveDocument.C2116.Placement=Base.Placement(Base.Vector(-73.743019,-160.084988,504.661596),Base.Rotation(0.453679,-0.524935,0.000000,0.720152))
App.ActiveDocument.addObject("Part::Cylinder","C2117")
App.ActiveDocument.C2117.Radius=0.750000
App.ActiveDocument.C2117.Height=15.00
App.ActiveDocument.C2117.Angle=360.00 
App.ActiveDocument.C2117.Placement=Base.Placement(Base.Vector(-73.651969,-160.219260,502.374472),Base.Rotation(0.475395,-0.533066,0.000000,0.699886))
App.ActiveDocument.addObject("Part::Cylinder","C2118")
App.ActiveDocument.C2118.Radius=0.750000
App.ActiveDocument.C2118.Height=15.00
App.ActiveDocument.C2118.Angle=360.00 
App.ActiveDocument.C2118.Placement=Base.Placement(Base.Vector(-73.576023,-160.143474,500.101722),Base.Rotation(0.492097,-0.544763,0.000000,0.679024))
App.ActiveDocument.addObject("Part::Cylinder","C2119")
App.ActiveDocument.C2119.Radius=0.750000
App.ActiveDocument.C2119.Height=15.00
App.ActiveDocument.C2119.Angle=360.00 
App.ActiveDocument.C2119.Placement=Base.Placement(Base.Vector(-73.933849,-159.250417,497.097352),Base.Rotation(0.503402,-0.563559,0.000000,0.654971))
App.ActiveDocument.addObject("Part::Cylinder","C2120")
App.ActiveDocument.C2120.Radius=0.750000
App.ActiveDocument.C2120.Height=15.00
App.ActiveDocument.C2120.Angle=360.00 
App.ActiveDocument.C2120.Placement=Base.Placement(Base.Vector(-73.869524,-158.638807,494.425888),Base.Rotation(0.512781,-0.579245,0.000000,0.633665))
App.ActiveDocument.addObject("Part::Cylinder","C2121")
App.ActiveDocument.C2121.Radius=0.750000
App.ActiveDocument.C2121.Height=15.00
App.ActiveDocument.C2121.Angle=360.00 
App.ActiveDocument.C2121.Placement=Base.Placement(Base.Vector(-74.010631,-157.541622,491.791622),Base.Rotation(0.516089,-0.601314,0.000000,0.609979))
App.ActiveDocument.addObject("Part::Cylinder","C2122")
App.ActiveDocument.C2122.Radius=0.750000
App.ActiveDocument.C2122.Height=15.00
App.ActiveDocument.C2122.Angle=360.00 
App.ActiveDocument.C2122.Placement=Base.Placement(Base.Vector(-73.935809,-156.357631,489.049342),Base.Rotation(0.517367,-0.625362,0.000000,0.584169))
App.ActiveDocument.addObject("Part::Cylinder","C2123")
App.ActiveDocument.C2123.Radius=0.750000
App.ActiveDocument.C2123.Height=15.00
App.ActiveDocument.C2123.Angle=360.00 
App.ActiveDocument.C2123.Placement=Base.Placement(Base.Vector(-73.686258,-155.121822,486.422935),Base.Rotation(0.513286,-0.651177,0.000000,0.559022))
App.ActiveDocument.addObject("Part::Cylinder","C2124")
App.ActiveDocument.C2124.Radius=0.750000
App.ActiveDocument.C2124.Height=15.00
App.ActiveDocument.C2124.Angle=360.00 
App.ActiveDocument.C2124.Placement=Base.Placement(Base.Vector(-73.356494,-153.746992,483.947251),Base.Rotation(0.501810,-0.681797,0.000000,0.532296))
App.ActiveDocument.addObject("Part::Cylinder","C2125")
App.ActiveDocument.C2125.Radius=0.750000
App.ActiveDocument.C2125.Height=15.00
App.ActiveDocument.C2125.Angle=360.00 
App.ActiveDocument.C2125.Placement=Base.Placement(Base.Vector(-73.155392,-152.158664,481.869689),Base.Rotation(0.472298,-0.722838,0.000000,0.504420))
App.ActiveDocument.addObject("Part::Cylinder","C2126")
App.ActiveDocument.C2126.Radius=0.750000
App.ActiveDocument.C2126.Height=15.00
App.ActiveDocument.C2126.Angle=360.00 
App.ActiveDocument.C2126.Placement=Base.Placement(Base.Vector(-73.105357,-150.435313,480.266940),Base.Rotation(0.436461,-0.759612,0.000000,0.482173))
App.ActiveDocument.addObject("Part::Cylinder","C2127")
App.ActiveDocument.C2127.Radius=0.750000
App.ActiveDocument.C2127.Height=15.00
App.ActiveDocument.C2127.Angle=360.00 
App.ActiveDocument.C2127.Placement=Base.Placement(Base.Vector(-72.875232,-148.577026,478.706320),Base.Rotation(0.374209,-0.807205,0.000000,0.456495))
App.ActiveDocument.addObject("Part::Cylinder","C2128")
App.ActiveDocument.C2128.Radius=0.750000
App.ActiveDocument.C2128.Height=15.00
App.ActiveDocument.C2128.Angle=360.00 
App.ActiveDocument.C2128.Placement=Base.Placement(Base.Vector(-71.975925,-146.966667,476.837185),Base.Rotation(0.311034,-0.847498,0.000000,0.430122))
App.ActiveDocument.addObject("Part::Cylinder","C2129")
App.ActiveDocument.C2129.Radius=0.750000
App.ActiveDocument.C2129.Height=15.00
App.ActiveDocument.C2129.Angle=360.00 
App.ActiveDocument.C2129.Placement=Base.Placement(Base.Vector(-70.815482,-145.251225,474.986831),Base.Rotation(0.206992,-0.890711,0.000000,0.404708))
App.ActiveDocument.addObject("Part::Cylinder","C2130")
App.ActiveDocument.C2130.Radius=0.750000
App.ActiveDocument.C2130.Height=15.00
App.ActiveDocument.C2130.Angle=360.00 
App.ActiveDocument.C2130.Placement=Base.Placement(Base.Vector(-69.070937,-143.590422,472.871021),Base.Rotation(0.182840,-0.905393,0.000000,0.383187))
App.ActiveDocument.addObject("Part::Cylinder","C2131")
App.ActiveDocument.C2131.Radius=0.750000
App.ActiveDocument.C2131.Height=15.00
App.ActiveDocument.C2131.Angle=360.00 
App.ActiveDocument.C2131.Placement=Base.Placement(Base.Vector(-67.358465,-142.660205,471.135912),Base.Rotation(0.122689,-0.924212,0.000000,0.361634))
App.ActiveDocument.addObject("Part::Cylinder","C2132")
App.ActiveDocument.C2132.Radius=0.750000
App.ActiveDocument.C2132.Height=15.00
App.ActiveDocument.C2132.Angle=360.00 
App.ActiveDocument.C2132.Placement=Base.Placement(Base.Vector(-73.536521,-144.043694,521.774974),Base.Rotation(0.031398,-0.469017,0.000000,0.882631))
App.ActiveDocument.addObject("Part::Cylinder","C2133")
App.ActiveDocument.C2133.Radius=0.750000
App.ActiveDocument.C2133.Height=15.00
App.ActiveDocument.C2133.Angle=360.00 
App.ActiveDocument.C2133.Placement=Base.Placement(Base.Vector(-73.515898,-147.104639,521.309519),Base.Rotation(0.073074,-0.471347,0.000000,0.878916))
App.ActiveDocument.addObject("Part::Cylinder","C2134")
App.ActiveDocument.C2134.Radius=0.750000
App.ActiveDocument.C2134.Height=15.00
App.ActiveDocument.C2134.Angle=360.00 
App.ActiveDocument.C2134.Placement=Base.Placement(Base.Vector(-73.818346,-149.775279,520.020756),Base.Rotation(0.116993,-0.479193,0.000000,0.869877))
App.ActiveDocument.addObject("Part::Cylinder","C2135")
App.ActiveDocument.C2135.Radius=0.750000
App.ActiveDocument.C2135.Height=15.00
App.ActiveDocument.C2135.Angle=360.00 
App.ActiveDocument.C2135.Placement=Base.Placement(Base.Vector(-74.001714,-152.099941,518.587227),Base.Rotation(0.164299,-0.485572,0.000000,0.858619))
App.ActiveDocument.addObject("Part::Cylinder","C2136")
App.ActiveDocument.C2136.Radius=0.750000
App.ActiveDocument.C2136.Height=15.00
App.ActiveDocument.C2136.Angle=360.00 
App.ActiveDocument.C2136.Placement=Base.Placement(Base.Vector(-74.311368,-153.843079,516.794416),Base.Rotation(0.207631,-0.493978,0.000000,0.844319))
App.ActiveDocument.addObject("Part::Cylinder","C2137")
App.ActiveDocument.C2137.Radius=0.750000
App.ActiveDocument.C2137.Height=15.00
App.ActiveDocument.C2137.Angle=360.00 
App.ActiveDocument.C2137.Placement=Base.Placement(Base.Vector(-74.767524,-154.972333,514.725571),Base.Rotation(0.247394,-0.505655,0.000000,0.826504))
App.ActiveDocument.addObject("Part::Cylinder","C2138")
App.ActiveDocument.C2138.Radius=0.750000
App.ActiveDocument.C2138.Height=15.00
App.ActiveDocument.C2138.Angle=360.00 
App.ActiveDocument.C2138.Placement=Base.Placement(Base.Vector(-75.039270,-155.975562,512.713114),Base.Rotation(0.291953,-0.515242,0.000000,0.805785))
App.ActiveDocument.addObject("Part::Cylinder","C2139")
App.ActiveDocument.C2139.Radius=0.750000
App.ActiveDocument.C2139.Height=15.00
App.ActiveDocument.C2139.Angle=360.00 
App.ActiveDocument.C2139.Placement=Base.Placement(Base.Vector(-75.210802,-156.914996,510.400513),Base.Rotation(0.331154,-0.523823,0.000000,0.784822))
App.ActiveDocument.addObject("Part::Cylinder","C2140")
App.ActiveDocument.C2140.Radius=0.750000
App.ActiveDocument.C2140.Height=15.00
App.ActiveDocument.C2140.Angle=360.00 
App.ActiveDocument.C2140.Placement=Base.Placement(Base.Vector(-75.709921,-157.132834,507.579634),Base.Rotation(0.372041,-0.536742,0.000000,0.757294))
App.ActiveDocument.addObject("Part::Cylinder","C2141")
App.ActiveDocument.C2141.Radius=0.750000
App.ActiveDocument.C2141.Height=15.00
App.ActiveDocument.C2141.Angle=360.00 
App.ActiveDocument.C2141.Placement=Base.Placement(Base.Vector(-75.902910,-157.376955,504.895095),Base.Rotation(0.402915,-0.548163,0.000000,0.732923))
App.ActiveDocument.addObject("Part::Cylinder","C2142")
App.ActiveDocument.C2142.Radius=0.750000
App.ActiveDocument.C2142.Height=15.00
App.ActiveDocument.C2142.Angle=360.00 
App.ActiveDocument.C2142.Placement=Base.Placement(Base.Vector(-75.896582,-157.531394,502.033087),Base.Rotation(0.436052,-0.559128,0.000000,0.705149))
App.ActiveDocument.addObject("Part::Cylinder","C2143")
App.ActiveDocument.C2143.Radius=0.750000
App.ActiveDocument.C2143.Height=15.00
App.ActiveDocument.C2143.Angle=360.00 
App.ActiveDocument.C2143.Placement=Base.Placement(Base.Vector(-75.727352,-157.583332,499.532164),Base.Rotation(0.460923,-0.568495,0.000000,0.681442))
App.ActiveDocument.addObject("Part::Cylinder","C2144")
App.ActiveDocument.C2144.Radius=0.750000
App.ActiveDocument.C2144.Height=15.00
App.ActiveDocument.C2144.Angle=360.00 
App.ActiveDocument.C2144.Placement=Base.Placement(Base.Vector(-76.283905,-156.380002,496.673290),Base.Rotation(0.470054,-0.592879,0.000000,0.653868))
App.ActiveDocument.addObject("Part::Cylinder","C2145")
App.ActiveDocument.C2145.Radius=0.750000
App.ActiveDocument.C2145.Height=15.00
App.ActiveDocument.C2145.Angle=360.00 
App.ActiveDocument.C2145.Placement=Base.Placement(Base.Vector(-76.255259,-155.568946,493.747236),Base.Rotation(0.480522,-0.614669,0.000000,0.625524))
App.ActiveDocument.addObject("Part::Cylinder","C2146")
App.ActiveDocument.C2146.Radius=0.750000
App.ActiveDocument.C2146.Height=15.00
App.ActiveDocument.C2146.Angle=360.00 
App.ActiveDocument.C2146.Placement=Base.Placement(Base.Vector(-76.368587,-154.354156,491.164420),Base.Rotation(0.476361,-0.640475,0.000000,0.602389))
App.ActiveDocument.addObject("Part::Cylinder","C2147")
App.ActiveDocument.C2147.Radius=0.750000
App.ActiveDocument.C2147.Height=15.00
App.ActiveDocument.C2147.Angle=360.00 
App.ActiveDocument.C2147.Placement=Base.Placement(Base.Vector(-76.120271,-153.269374,488.562999),Base.Rotation(0.472473,-0.668633,0.000000,0.574194))
App.ActiveDocument.addObject("Part::Cylinder","C2148")
App.ActiveDocument.C2148.Radius=0.750000
App.ActiveDocument.C2148.Height=15.00
App.ActiveDocument.C2148.Angle=360.00 
App.ActiveDocument.C2148.Placement=Base.Placement(Base.Vector(-75.805534,-151.968480,486.070002),Base.Rotation(0.455404,-0.702291,0.000000,0.547169))
App.ActiveDocument.addObject("Part::Cylinder","C2149")
App.ActiveDocument.C2149.Radius=0.750000
App.ActiveDocument.C2149.Height=15.00
App.ActiveDocument.C2149.Angle=360.00 
App.ActiveDocument.C2149.Placement=Base.Placement(Base.Vector(-75.531562,-150.462084,483.925661),Base.Rotation(0.431073,-0.737318,0.000000,0.520133))
App.ActiveDocument.addObject("Part::Cylinder","C2150")
App.ActiveDocument.C2150.Radius=0.750000
App.ActiveDocument.C2150.Height=15.00
App.ActiveDocument.C2150.Angle=360.00 
App.ActiveDocument.C2150.Placement=Base.Placement(Base.Vector(-75.196311,-148.906680,482.097148),Base.Rotation(0.366902,-0.788517,0.000000,0.493582))
App.ActiveDocument.addObject("Part::Cylinder","C2151")
App.ActiveDocument.C2151.Radius=0.750000
App.ActiveDocument.C2151.Height=15.00
App.ActiveDocument.C2151.Angle=360.00 
App.ActiveDocument.C2151.Placement=Base.Placement(Base.Vector(-74.918001,-147.285971,480.705590),Base.Rotation(0.290664,-0.832009,0.000000,0.472521))
App.ActiveDocument.addObject("Part::Cylinder","C2152")
App.ActiveDocument.C2152.Radius=0.750000
App.ActiveDocument.C2152.Height=15.00
App.ActiveDocument.C2152.Angle=360.00 
App.ActiveDocument.C2152.Placement=Base.Placement(Base.Vector(-74.107944,-145.669996,478.969291),Base.Rotation(0.192818,-0.871921,0.000000,0.450083))
App.ActiveDocument.addObject("Part::Cylinder","C2153")
App.ActiveDocument.C2153.Radius=0.750000
App.ActiveDocument.C2153.Height=15.00
App.ActiveDocument.C2153.Angle=360.00 
App.ActiveDocument.C2153.Placement=Base.Placement(Base.Vector(-73.001179,-144.088488,477.216219),Base.Rotation(0.110507,-0.895778,0.000000,0.430546))
App.ActiveDocument.addObject("Part::Cylinder","C2154")
App.ActiveDocument.C2154.Radius=0.750000
App.ActiveDocument.C2154.Height=15.00
App.ActiveDocument.C2154.Angle=360.00 
App.ActiveDocument.C2154.Placement=Base.Placement(Base.Vector(-71.412991,-143.195139,475.247748),Base.Rotation(0.084730,-0.908162,0.000000,0.409955))
App.ActiveDocument.addObject("Part::Cylinder","C2155")
App.ActiveDocument.C2155.Radius=0.750000
App.ActiveDocument.C2155.Height=15.00
App.ActiveDocument.C2155.Angle=360.00 
App.ActiveDocument.C2155.Placement=Base.Placement(Base.Vector(-75.349833,-144.016299,518.906943),Base.Rotation(0.033270,-0.495169,0.000000,0.868159))
App.ActiveDocument.addObject("Part::Cylinder","C2156")
App.ActiveDocument.C2156.Radius=0.750000
App.ActiveDocument.C2156.Height=15.00
App.ActiveDocument.C2156.Angle=360.00 
App.ActiveDocument.C2156.Placement=Base.Placement(Base.Vector(-75.411716,-146.964700,518.258830),Base.Rotation(0.073744,-0.499266,0.000000,0.863305))
App.ActiveDocument.addObject("Part::Cylinder","C2157")
App.ActiveDocument.C2157.Radius=0.750000
App.ActiveDocument.C2157.Height=15.00
App.ActiveDocument.C2157.Angle=360.00 
App.ActiveDocument.C2157.Placement=Base.Placement(Base.Vector(-75.786582,-149.422386,516.711892),Base.Rotation(0.124290,-0.506846,0.000000,0.853029))
App.ActiveDocument.addObject("Part::Cylinder","C2158")
App.ActiveDocument.C2158.Radius=0.750000
App.ActiveDocument.C2158.Height=15.00
App.ActiveDocument.C2158.Angle=360.00 
App.ActiveDocument.C2158.Placement=Base.Placement(Base.Vector(-76.034764,-151.444954,515.091816),Base.Rotation(0.166600,-0.518526,0.000000,0.838675))
App.ActiveDocument.addObject("Part::Cylinder","C2159")
App.ActiveDocument.C2159.Radius=0.750000
App.ActiveDocument.C2159.Height=15.00
App.ActiveDocument.C2159.Angle=360.00 
App.ActiveDocument.C2159.Placement=Base.Placement(Base.Vector(-76.451713,-152.591162,513.223868),Base.Rotation(0.202056,-0.530179,0.000000,0.823459))
App.ActiveDocument.addObject("Part::Cylinder","C2160")
App.ActiveDocument.C2160.Radius=0.750000
App.ActiveDocument.C2160.Height=15.00
App.ActiveDocument.C2160.Angle=360.00 
App.ActiveDocument.C2160.Placement=Base.Placement(Base.Vector(-76.711184,-153.811974,511.122600),Base.Rotation(0.248523,-0.541416,0.000000,0.803184))
App.ActiveDocument.addObject("Part::Cylinder","C2161")
App.ActiveDocument.C2161.Radius=0.750000
App.ActiveDocument.C2161.Height=15.00
App.ActiveDocument.C2161.Angle=360.00 
App.ActiveDocument.C2161.Placement=Base.Placement(Base.Vector(-76.917647,-154.690541,508.946375),Base.Rotation(0.295737,-0.550763,0.000000,0.780512))
App.ActiveDocument.addObject("Part::Cylinder","C2162")
App.ActiveDocument.C2162.Radius=0.750000
App.ActiveDocument.C2162.Height=15.00
App.ActiveDocument.C2162.Angle=360.00 
App.ActiveDocument.C2162.Placement=Base.Placement(Base.Vector(-77.555205,-154.632334,506.010648),Base.Rotation(0.327333,-0.567462,0.000000,0.755539))
App.ActiveDocument.addObject("Part::Cylinder","C2163")
App.ActiveDocument.C2163.Radius=0.750000
App.ActiveDocument.C2163.Height=15.00
App.ActiveDocument.C2163.Angle=360.00 
App.ActiveDocument.C2163.Placement=Base.Placement(Base.Vector(-77.736276,-154.879124,503.150274),Base.Rotation(0.363867,-0.584427,0.000000,0.725290))
App.ActiveDocument.addObject("Part::Cylinder","C2164")
App.ActiveDocument.C2164.Radius=0.750000
App.ActiveDocument.C2164.Height=15.00
App.ActiveDocument.C2164.Angle=360.00 
App.ActiveDocument.C2164.Placement=Base.Placement(Base.Vector(-77.742766,-154.938647,500.330479),Base.Rotation(0.397284,-0.596808,0.000000,0.697127))
App.ActiveDocument.addObject("Part::Cylinder","C2165")
App.ActiveDocument.C2165.Radius=0.750000
App.ActiveDocument.C2165.Height=15.00
App.ActiveDocument.C2165.Angle=360.00 
App.ActiveDocument.C2165.Placement=Base.Placement(Base.Vector(-77.948653,-154.376511,497.889589),Base.Rotation(0.404933,-0.616514,0.000000,0.675234))
App.ActiveDocument.addObject("Part::Cylinder","C2166")
App.ActiveDocument.C2166.Radius=0.750000
App.ActiveDocument.C2166.Height=15.00
App.ActiveDocument.C2166.Angle=360.00 
App.ActiveDocument.C2166.Placement=Base.Placement(Base.Vector(-78.182546,-153.404293,495.309110),Base.Rotation(0.411849,-0.641211,0.000000,0.647479))
App.ActiveDocument.addObject("Part::Cylinder","C2167")
App.ActiveDocument.C2167.Radius=0.750000
App.ActiveDocument.C2167.Height=15.00
App.ActiveDocument.C2167.Angle=360.00 
App.ActiveDocument.C2167.Placement=Base.Placement(Base.Vector(-78.229888,-152.404847,492.804384),Base.Rotation(0.409145,-0.669065,0.000000,0.620445))
App.ActiveDocument.addObject("Part::Cylinder","C2168")
App.ActiveDocument.C2168.Radius=0.750000
App.ActiveDocument.C2168.Height=15.00
App.ActiveDocument.C2168.Angle=360.00 
App.ActiveDocument.C2168.Placement=Base.Placement(Base.Vector(-78.056775,-151.298382,490.206881),Base.Rotation(0.401320,-0.697370,0.000000,0.593816))
App.ActiveDocument.addObject("Part::Cylinder","C2169")
App.ActiveDocument.C2169.Radius=0.750000
App.ActiveDocument.C2169.Height=15.00
App.ActiveDocument.C2169.Angle=360.00 
App.ActiveDocument.C2169.Placement=Base.Placement(Base.Vector(-77.734961,-150.223813,487.927446),Base.Rotation(0.369199,-0.735972,0.000000,0.567483))
App.ActiveDocument.addObject("Part::Cylinder","C2170")
App.ActiveDocument.C2170.Radius=0.750000
App.ActiveDocument.C2170.Height=15.00
App.ActiveDocument.C2170.Angle=360.00 
App.ActiveDocument.C2170.Placement=Base.Placement(Base.Vector(-77.415069,-148.905768,485.919872),Base.Rotation(0.345432,-0.768496,0.000000,0.538601))
App.ActiveDocument.addObject("Part::Cylinder","C2171")
App.ActiveDocument.C2171.Radius=0.750000
App.ActiveDocument.C2171.Height=15.00
App.ActiveDocument.C2171.Angle=360.00 
App.ActiveDocument.C2171.Placement=Base.Placement(Base.Vector(-76.958247,-147.674202,484.172674),Base.Rotation(0.258847,-0.815389,0.000000,0.517822))
App.ActiveDocument.addObject("Part::Cylinder","C2172")
App.ActiveDocument.C2172.Radius=0.750000
App.ActiveDocument.C2172.Height=15.00
App.ActiveDocument.C2172.Angle=360.00 
App.ActiveDocument.C2172.Placement=Base.Placement(Base.Vector(-76.519913,-146.073107,482.665902),Base.Rotation(0.173382,-0.850134,0.000000,0.497203))
App.ActiveDocument.addObject("Part::Cylinder","C2173")
App.ActiveDocument.C2173.Radius=0.750000
App.ActiveDocument.C2173.Height=15.00
App.ActiveDocument.C2173.Angle=360.00 
App.ActiveDocument.C2173.Placement=Base.Placement(Base.Vector(-75.773874,-144.337721,481.053382),Base.Rotation(0.089965,-0.873727,0.000000,0.478025))
App.ActiveDocument.addObject("Part::Cylinder","C2174")
App.ActiveDocument.C2174.Radius=0.750000
App.ActiveDocument.C2174.Height=15.00
App.ActiveDocument.C2174.Angle=360.00 
App.ActiveDocument.C2174.Placement=Base.Placement(Base.Vector(-74.431556,-143.150392,478.974963),Base.Rotation(0.055018,-0.890133,0.000000,0.452367))
App.ActiveDocument.addObject("Part::Cylinder","C2175")
App.ActiveDocument.C2175.Radius=0.750000
App.ActiveDocument.C2175.Height=15.00
App.ActiveDocument.C2175.Angle=360.00 
App.ActiveDocument.C2175.Placement=Base.Placement(Base.Vector(-76.978517,-143.866061,515.951046),Base.Rotation(0.033870,-0.523463,0.000000,0.851375))
App.ActiveDocument.addObject("Part::Cylinder","C2176")
App.ActiveDocument.C2176.Radius=0.750000
App.ActiveDocument.C2176.Height=15.00
App.ActiveDocument.C2176.Angle=360.00 
App.ActiveDocument.C2176.Placement=Base.Placement(Base.Vector(-77.131725,-146.668041,515.060992),Base.Rotation(0.075151,-0.529582,0.000000,0.844923))
App.ActiveDocument.addObject("Part::Cylinder","C2177")
App.ActiveDocument.C2177.Radius=0.750000
App.ActiveDocument.C2177.Height=15.00
App.ActiveDocument.C2177.Angle=360.00 
App.ActiveDocument.C2177.Placement=Base.Placement(Base.Vector(-77.511942,-148.860275,513.349125),Base.Rotation(0.119835,-0.541703,0.000000,0.831984))
App.ActiveDocument.addObject("Part::Cylinder","C2178")
App.ActiveDocument.C2178.Radius=0.750000
App.ActiveDocument.C2178.Height=15.00
App.ActiveDocument.C2178.Angle=360.00 
App.ActiveDocument.C2178.Placement=Base.Placement(Base.Vector(-77.908063,-150.309494,511.441102),Base.Rotation(0.160020,-0.553941,0.000000,0.817033))
App.ActiveDocument.addObject("Part::Cylinder","C2179")
App.ActiveDocument.C2179.Radius=0.750000
App.ActiveDocument.C2179.Height=15.00
App.ActiveDocument.C2179.Angle=360.00 
App.ActiveDocument.C2179.Placement=Base.Placement(Base.Vector(-78.170939,-151.554179,509.456325),Base.Rotation(0.204491,-0.567035,0.000000,0.797906))
App.ActiveDocument.addObject("Part::Cylinder","C2180")
App.ActiveDocument.C2180.Radius=0.750000
App.ActiveDocument.C2180.Height=15.00
App.ActiveDocument.C2180.Angle=360.00 
App.ActiveDocument.C2180.Placement=Base.Placement(Base.Vector(-78.402178,-152.349591,507.454257),Base.Rotation(0.238470,-0.579266,0.000000,0.779476))
App.ActiveDocument.addObject("Part::Cylinder","C2181")
App.ActiveDocument.C2181.Radius=0.750000
App.ActiveDocument.C2181.Height=15.00
App.ActiveDocument.C2181.Angle=360.00 
App.ActiveDocument.C2181.Placement=Base.Placement(Base.Vector(-78.998456,-152.217316,504.522089),Base.Rotation(0.257660,-0.607465,0.000000,0.751397))
App.ActiveDocument.addObject("Part::Cylinder","C2182")
App.ActiveDocument.C2182.Radius=0.750000
App.ActiveDocument.C2182.Height=15.00
App.ActiveDocument.C2182.Angle=360.00 
App.ActiveDocument.C2182.Placement=Base.Placement(Base.Vector(-79.199606,-152.386951,501.589961),Base.Rotation(0.297784,-0.622906,0.000000,0.723404))
App.ActiveDocument.addObject("Part::Cylinder","C2183")
App.ActiveDocument.C2183.Radius=0.750000
App.ActiveDocument.C2183.Height=15.00
App.ActiveDocument.C2183.Angle=360.00 
App.ActiveDocument.C2183.Placement=Base.Placement(Base.Vector(-79.345968,-152.120963,499.008914),Base.Rotation(0.322004,-0.644345,0.000000,0.693637))
App.ActiveDocument.addObject("Part::Cylinder","C2184")
App.ActiveDocument.C2184.Radius=0.750000
App.ActiveDocument.C2184.Height=15.00
App.ActiveDocument.C2184.Angle=360.00 
App.ActiveDocument.C2184.Placement=Base.Placement(Base.Vector(-79.524127,-151.357752,496.532530),Base.Rotation(0.321430,-0.669620,0.000000,0.669546))
App.ActiveDocument.addObject("Part::Cylinder","C2185")
App.ActiveDocument.C2185.Radius=0.750000
App.ActiveDocument.C2185.Height=15.00
App.ActiveDocument.C2185.Angle=360.00 
App.ActiveDocument.C2185.Placement=Base.Placement(Base.Vector(-79.552184,-150.485304,494.154372),Base.Rotation(0.308785,-0.702323,0.000000,0.641401))
App.ActiveDocument.addObject("Part::Cylinder","C2186")
App.ActiveDocument.C2186.Radius=0.750000
App.ActiveDocument.C2186.Height=15.00
App.ActiveDocument.C2186.Angle=360.00 
App.ActiveDocument.C2186.Placement=Base.Placement(Base.Vector(-79.388542,-149.527759,491.743111),Base.Rotation(0.286929,-0.736181,0.000000,0.612951))
App.ActiveDocument.addObject("Part::Cylinder","C2187")
App.ActiveDocument.C2187.Radius=0.750000
App.ActiveDocument.C2187.Height=15.00
App.ActiveDocument.C2187.Angle=360.00 
App.ActiveDocument.C2187.Placement=Base.Placement(Base.Vector(-79.111281,-148.535002,489.654531),Base.Rotation(0.246139,-0.770525,0.000000,0.587968))
App.ActiveDocument.addObject("Part::Cylinder","C2188")
App.ActiveDocument.C2188.Radius=0.750000
App.ActiveDocument.C2188.Height=15.00
App.ActiveDocument.C2188.Angle=360.00 
App.ActiveDocument.C2188.Placement=Base.Placement(Base.Vector(-78.628919,-147.409422,487.483272),Base.Rotation(0.206098,-0.801407,0.000000,0.561489))
App.ActiveDocument.addObject("Part::Cylinder","C2189")
App.ActiveDocument.C2189.Radius=0.750000
App.ActiveDocument.C2189.Height=15.00
App.ActiveDocument.C2189.Angle=360.00 
App.ActiveDocument.C2189.Placement=Base.Placement(Base.Vector(-78.224056,-146.103096,485.899270),Base.Rotation(0.148184,-0.827736,0.000000,0.541198))
App.ActiveDocument.addObject("Part::Cylinder","C2190")
App.ActiveDocument.C2190.Radius=0.750000
App.ActiveDocument.C2190.Height=15.00
App.ActiveDocument.C2190.Angle=360.00 
App.ActiveDocument.C2190.Placement=Base.Placement(Base.Vector(-77.795732,-144.461485,484.568380),Base.Rotation(0.083933,-0.847827,0.000000,0.523589))
App.ActiveDocument.addObject("Part::Cylinder","C2191")
App.ActiveDocument.C2191.Radius=0.750000
App.ActiveDocument.C2191.Height=15.00
App.ActiveDocument.C2191.Angle=360.00 
App.ActiveDocument.C2191.Placement=Base.Placement(Base.Vector(-78.400819,-143.735923,512.889080),Base.Rotation(0.034328,-0.553592,0.000000,0.832080))
App.ActiveDocument.addObject("Part::Cylinder","C2192")
App.ActiveDocument.C2192.Radius=0.750000
App.ActiveDocument.C2192.Height=15.00
App.ActiveDocument.C2192.Angle=360.00 
App.ActiveDocument.C2192.Placement=Base.Placement(Base.Vector(-78.655646,-146.174621,511.685398),Base.Rotation(0.074202,-0.563299,0.000000,0.822915))
App.ActiveDocument.addObject("Part::Cylinder","C2193")
App.ActiveDocument.C2193.Radius=0.750000
App.ActiveDocument.C2193.Height=15.00
App.ActiveDocument.C2193.Angle=360.00 
App.ActiveDocument.C2193.Placement=Base.Placement(Base.Vector(-79.090773,-147.889154,509.686833),Base.Rotation(0.111258,-0.580148,0.000000,0.806877))
App.ActiveDocument.addObject("Part::Cylinder","C2194")
App.ActiveDocument.C2194.Radius=0.750000
App.ActiveDocument.C2194.Height=15.00
App.ActiveDocument.C2194.Angle=360.00 
App.ActiveDocument.C2194.Placement=Base.Placement(Base.Vector(-79.356808,-149.299634,507.703990),Base.Rotation(0.153038,-0.595874,0.000000,0.788362))
App.ActiveDocument.addObject("Part::Cylinder","C2195")
App.ActiveDocument.C2195.Radius=0.750000
App.ActiveDocument.C2195.Height=15.00
App.ActiveDocument.C2195.Angle=360.00 
App.ActiveDocument.C2195.Placement=Base.Placement(Base.Vector(-79.507739,-150.311221,505.801654),Base.Rotation(0.192939,-0.609602,0.000000,0.768869))
App.ActiveDocument.addObject("Part::Cylinder","C2196")
App.ActiveDocument.C2196.Radius=0.750000
App.ActiveDocument.C2196.Height=15.00
App.ActiveDocument.C2196.Angle=360.00 
App.ActiveDocument.C2196.Placement=Base.Placement(Base.Vector(-80.159912,-149.600100,502.901086),Base.Rotation(0.191389,-0.639518,0.000000,0.744572))
App.ActiveDocument.addObject("Part::Cylinder","C2197")
App.ActiveDocument.C2197.Radius=0.750000
App.ActiveDocument.C2197.Height=15.00
App.ActiveDocument.C2197.Angle=360.00 
App.ActiveDocument.C2197.Placement=Base.Placement(Base.Vector(-80.316646,-149.733829,500.136333),Base.Rotation(0.216984,-0.666149,0.000000,0.713556))
App.ActiveDocument.addObject("Part::Cylinder","C2198")
App.ActiveDocument.C2198.Radius=0.750000
App.ActiveDocument.C2198.Height=15.00
App.ActiveDocument.C2198.Angle=360.00 
App.ActiveDocument.C2198.Placement=Base.Placement(Base.Vector(-80.447194,-149.224042,497.659508),Base.Rotation(0.217707,-0.695113,0.000000,0.685144))
App.ActiveDocument.addObject("Part::Cylinder","C2199")
App.ActiveDocument.C2199.Radius=0.750000
App.ActiveDocument.C2199.Height=15.00
App.ActiveDocument.C2199.Angle=360.00 
App.ActiveDocument.C2199.Placement=Base.Placement(Base.Vector(-80.458821,-148.427682,495.298178),Base.Rotation(0.197059,-0.723614,0.000000,0.661476))
App.ActiveDocument.addObject("Part::Cylinder","C2200")
App.ActiveDocument.C2200.Radius=0.750000
App.ActiveDocument.C2200.Height=15.00
App.ActiveDocument.C2200.Angle=360.00 
App.ActiveDocument.C2200.Placement=Base.Placement(Base.Vector(-80.315727,-147.497780,493.059538),Base.Rotation(0.174948,-0.750515,0.000000,0.637276))
App.ActiveDocument.addObject("Part::Cylinder","C2201")
App.ActiveDocument.C2201.Radius=0.750000
App.ActiveDocument.C2201.Height=15.00
App.ActiveDocument.C2201.Angle=360.00 
App.ActiveDocument.C2201.Placement=Base.Placement(Base.Vector(-80.033263,-146.492479,491.021700),Base.Rotation(0.136373,-0.781907,0.000000,0.608296))
App.ActiveDocument.addObject("Part::Cylinder","C2202")
App.ActiveDocument.C2202.Radius=0.750000
App.ActiveDocument.C2202.Height=15.00
App.ActiveDocument.C2202.Angle=360.00 
App.ActiveDocument.C2202.Placement=Base.Placement(Base.Vector(-79.541182,-145.337320,488.883961),Base.Rotation(0.101363,-0.808031,0.000000,0.580355))
App.ActiveDocument.addObject("Part::Cylinder","C2203")
App.ActiveDocument.C2203.Radius=0.750000
App.ActiveDocument.C2203.Height=15.00
App.ActiveDocument.C2203.Angle=360.00 
App.ActiveDocument.C2203.Placement=Base.Placement(Base.Vector(-79.154276,-143.370812,487.408218),Base.Rotation(0.044193,-0.826582,0.000000,0.561079))
App.ActiveDocument.addObject("Part::Cylinder","C2204")
App.ActiveDocument.C2204.Radius=0.750000
App.ActiveDocument.C2204.Height=15.00
App.ActiveDocument.C2204.Angle=360.00 
App.ActiveDocument.C2204.Placement=Base.Placement(Base.Vector(-79.594194,-143.501909,509.724642),Base.Rotation(0.032687,-0.585770,0.000000,0.809818))
App.ActiveDocument.addObject("Part::Cylinder","C2205")
App.ActiveDocument.C2205.Radius=0.750000
App.ActiveDocument.C2205.Height=15.00
App.ActiveDocument.C2205.Angle=360.00 
App.ActiveDocument.C2205.Placement=Base.Placement(Base.Vector(-79.969180,-145.314722,508.031118),Base.Rotation(0.063101,-0.602659,0.000000,0.795500))
App.ActiveDocument.addObject("Part::Cylinder","C2206")
App.ActiveDocument.C2206.Radius=0.750000
App.ActiveDocument.C2206.Height=15.00
App.ActiveDocument.C2206.Angle=360.00 
App.ActiveDocument.C2206.Placement=Base.Placement(Base.Vector(-80.279555,-146.776705,506.010419),Base.Rotation(0.096886,-0.621285,0.000000,0.777572))
App.ActiveDocument.addObject("Part::Cylinder","C2207")
App.ActiveDocument.C2207.Radius=0.750000
App.ActiveDocument.C2207.Height=15.00
App.ActiveDocument.C2207.Angle=360.00 
App.ActiveDocument.C2207.Placement=Base.Placement(Base.Vector(-80.424625,-147.958216,504.097782),Base.Rotation(0.132913,-0.637631,0.000000,0.758789))
App.ActiveDocument.addObject("Part::Cylinder","C2208")
App.ActiveDocument.C2208.Radius=0.750000
App.ActiveDocument.C2208.Height=15.00
App.ActiveDocument.C2208.Angle=360.00 
App.ActiveDocument.C2208.Placement=Base.Placement(Base.Vector(-80.919395,-146.819999,501.568518),Base.Rotation(0.111264,-0.668943,0.000000,0.734940))
App.ActiveDocument.addObject("Part::Cylinder","C2209")
App.ActiveDocument.C2209.Radius=0.750000
App.ActiveDocument.C2209.Height=15.00
App.ActiveDocument.C2209.Angle=360.00 
App.ActiveDocument.C2209.Placement=Base.Placement(Base.Vector(-81.021947,-146.902320,498.935722),Base.Rotation(0.122155,-0.696956,0.000000,0.706633))
App.ActiveDocument.addObject("Part::Cylinder","C2210")
App.ActiveDocument.C2210.Radius=0.750000
App.ActiveDocument.C2210.Height=15.00
App.ActiveDocument.C2210.Angle=360.00 
App.ActiveDocument.C2210.Placement=Base.Placement(Base.Vector(-81.067569,-146.048181,496.587949),Base.Rotation(0.102578,-0.726721,0.000000,0.679231))
App.ActiveDocument.addObject("Part::Cylinder","C2211")
App.ActiveDocument.C2211.Radius=0.750000
App.ActiveDocument.C2211.Height=15.00
App.ActiveDocument.C2211.Angle=360.00 
App.ActiveDocument.C2211.Placement=Base.Placement(Base.Vector(-80.948712,-145.101252,494.485800),Base.Rotation(0.083752,-0.753179,0.000000,0.652462))
App.ActiveDocument.addObject("Part::Cylinder","C2212")
App.ActiveDocument.C2212.Radius=0.750000
App.ActiveDocument.C2212.Height=15.00
App.ActiveDocument.C2212.Angle=360.00 
App.ActiveDocument.C2212.Placement=Base.Placement(Base.Vector(-80.657602,-144.017044,492.375791),Base.Rotation(0.058228,-0.777165,0.000000,0.626597))
App.ActiveDocument.addObject("Part::Cylinder","C2213")
App.ActiveDocument.C2213.Radius=0.750000
App.ActiveDocument.C2213.Height=15.00
App.ActiveDocument.C2213.Angle=360.00 
App.ActiveDocument.C2213.Placement=Base.Placement(Base.Vector(-80.153732,-143.376465,490.272626),Base.Rotation(0.044081,-0.799939,0.000000,0.598461))
App.ActiveDocument.addObject("Part::Cylinder","C2214")
App.ActiveDocument.C2214.Radius=0.750000
App.ActiveDocument.C2214.Height=15.00
App.ActiveDocument.C2214.Angle=360.00 
App.ActiveDocument.C2214.Placement=Base.Placement(Base.Vector(-80.695201,-143.267896,505.704731),Base.Rotation(0.031879,-0.629818,0.000000,0.776088))
App.ActiveDocument.addObject("Part::Cylinder","C2215")
App.ActiveDocument.C2215.Radius=0.750000
App.ActiveDocument.C2215.Height=15.00
App.ActiveDocument.C2215.Angle=360.00 
App.ActiveDocument.C2215.Placement=Base.Placement(Base.Vector(-80.983375,-144.721281,503.447821),Base.Rotation(0.059543,-0.653173,0.000000,0.754864))
App.ActiveDocument.addObject("Part::Cylinder","C2216")
App.ActiveDocument.C2216.Radius=0.750000
App.ActiveDocument.C2216.Height=15.00
App.ActiveDocument.C2216.Angle=360.00 
App.ActiveDocument.C2216.Placement=Base.Placement(Base.Vector(-81.328948,-143.782302,500.622317),Base.Rotation(0.043880,-0.686138,0.000000,0.726147))
App.ActiveDocument.addObject("Part::Cylinder","C2217")
App.ActiveDocument.C2217.Radius=0.750000
App.ActiveDocument.C2217.Height=15.00
App.ActiveDocument.C2217.Angle=360.00 
App.ActiveDocument.C2217.Placement=Base.Placement(Base.Vector(-81.396714,-143.332595,498.089253),Base.Rotation(0.036959,-0.716075,0.000000,0.697044))
App.ActiveDocument.addObject("Part::Cylinder","C2218")
App.ActiveDocument.C2218.Radius=0.750000
App.ActiveDocument.C2218.Height=15.00
App.ActiveDocument.C2218.Angle=360.00 
App.ActiveDocument.C2218.Placement=Base.Placement(Base.Vector(-81.234300,-143.148807,495.595563),Base.Rotation(0.035036,-0.744592,0.000000,0.666599))
App.ActiveDocument.recompute()
